/*
 * Copyright (c) 2025 Juniper Networks, Inc.
 * All rights reserved.
 */
 module junos-rpc-class-of-service {
   namespace "http://yang.juniper.net/junos/rpc/class-of-service";

   prefix class-of-service;

   import junos-common-types {
     prefix jt;
     revision-date 2025-01-01;
   }

   organization "Juniper Networks, Inc.";

   contact "yang-support@juniper.net";

   description "Junos RPC YANG module for class-of-service command(s)";

   revision 2025-01-01 {
     description "Junos: 25.4R1.12";
   }

   rpc get-cos-information {
     description "Show class-of-service (CoS) information";
     input {
       leaf control-plane-instance {
         type string;
       }
     }
     output {
       container cos-information {
         uses cos-information-block;
       }
     }
   }
   rpc get-appqos-counter {
     description "Show the application traffic control counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appqos-counter-information {
         uses appqos-counter-information-block;
       }
     }
   }
   rpc get-appqos-rule-statistics {
     description "Show the application traffic control rule hit statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appqos-rule-statistics-information {
         uses appqos-rule-statistics-information-block;
       }
     }
   }
   rpc get-appqos-rate-limiter-statistics {
     description "Show the application traffic control rate limiter statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appqos-rate-limiter-statistics-information {
         uses appqos-rate-limiter-statistics-information-block;
       }
     }
   }
   rpc get-appqos-swrl-stat-summary {
     description "Show the application traffic control rate-limiters summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appqos-swrl-stat-summary-information {
         uses appqos-swrl-stat-summary-information-block;
       }
     }
   }
   rpc get-appqos-swrl-stat-all {
     description "Show all application traffic control rate-limiters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appqos-swrl-stat-all-information {
         uses appqos-swrl-stat-all-information-block;
       }
     }
   }
   rpc get-appqos-swrl-stat-name {
     description "Show application traffic control rate-limiter by name";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf rl-name {
         description "Rate-limiter name";
         type string;
         mandatory true;
       }
       leaf level {
         default "brief";
         type enumeration {
           enum "brief" {
             description "Show brief output (default)";
           }
           enum "extensive" {
             description "Show detailed output";
           }
         }
       }
     }
     output {
       container appqos-swrl-stat-id-information {
         uses appqos-swrl-stat-id-information-block;
       }
     }
   }
   rpc get-cos-forwarding-class-information {
     description "Show mapping of forwarding class names to queue numbers";
     input {
       leaf control-plane-instance {
         type string;
       }
       leaf forwarding-class-map-name {
         description "Name of forwarding class map";
         type string;
       }
     }
     output {
       container cos-forwarding-class-information {
         uses cos-forwarding-class-information-block;
       }
     }
   }
   rpc get-cos-forwarding-class-set-information {
     description "Show forwarding-class-sets that are active";
     input {
       leaf control-plane-instance {
         type string;
       }
       leaf forwarding-class-set-name {
         description "Name of forwarding class set";
         type string;
       }
     }
     output {
       container cos-forwarding-class-set-information {
         uses cos-forwarding-class-set-information-block;
       }
     }
   }
   rpc get-cos-drop-profile-information {
     description "Show interpolated data points of named drop profile";
     input {
       leaf control-plane-instance {
         type string;
       }
       leaf profile-name {
         description "Name of drop profile";
         type string;
       }
     }
     output {
       container cos-drop-profile-information {
         uses cos-drop-profile-information-block;
       }
     }
   }
   rpc get-cos-monitoring-profile-information {
     description "Show data points of named monitoring profile";
     input {
       leaf get-monitoring-profile-name {
         description "Name of monitoring profile";
         type string;
       }
     }
     output {
       container cos-monitoring-profile-information {
         uses cos-monitoring-profile-information-block;
       }
     }
   }
   rpc get-cos-adaptive-shaper-information {
     description "Show trigger types and associated rate for adaptive shaper";
     input {
       leaf adaptive-shaper-name {
         description "Name of adaptive shaper";
         type string;
       }
     }
     output {
       container cos-adaptive-shaper-information {
         uses cos-adaptive-shaper-information-block;
       }
     }
   }
   rpc get-cos-virtual-channel-information {
     description "Show virtual channel names";
     input {
       leaf virtual-channel-name {
         description "Name of virtual channel";
         type string;
       }
     }
     output {
       container cos-virtual-channel-information {
         uses cos-virtual-channel-information-block;
       }
     }
   }
   rpc get-cos-virtual-channel-group-information {
     description "Show virtual channel group information";
     input {
       leaf virtual-channel-group-name {
         description "Name of virtual channel group";
         type string;
       }
     }
     output {
       container cos-virtual-channel-group-information {
         uses cos-virtual-channel-group-information-block;
       }
     }
   }
   rpc get-cos-classifier-information {
     description "Show mapping of code point to forwarding class/loss priority";
     input {
       leaf control-plane-instance {
         type string;
       }
       leaf classifier-name {
         description "Name of classifier";
         type string;
       }
       leaf type {
         description "Type of classifier";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "inet6-precedence" {
             description "IPv6 precedence code point";
           }
         }
       }
     }
     output {
       container cos-classifier-information {
         uses cos-classifier-information-block;
       }
     }
   }
   rpc get-cos-tcm-information {
     description "Show mapping of code point to input traffic-class";
     input {
       leaf tcm-name {
         description "Name of traffic-class-map";
         type string;
       }
       leaf type {
         description "Type of traffic-class-map";
         type enumeration {
           enum "inet-precedence" {
             description "IPv4 INET-Precedence code point";
           }
           enum "dscp" {
             description "Differentiated Services code point (DSCP)";
           }
           enum "exp" {
             description "MPLS experimental code point";
           }
           enum "ieee-802.1" {
             description "IEEE-802.1 code point";
           }
           enum "ieee-802.1ad" {
             description "IEEE-802.1ad (DEI) code point";
           }
         }
       }
     }
     output {
       container cos-tcm-information {
         uses cos-tcm-information-block;
       }
     }
   }
   rpc get-cos-policy-map-information {
     description "Show Policy-map code point";
     input {
       leaf policy-map-name {
         description "Name of Policy-map";
         type string;
       }
       leaf type {
         description "Type of Policy-map";
         type enumeration {
           enum "configured" {
             description "Show user configured policy-map";
           }
           enum "reserved" {
             description "Show reserved policy-map";
           }
         }
       }
     }
     output {
       container cos-policy-map-information {
         uses cos-policy-map-information-block;
       }
     }
   }
   rpc get-cos-l2tp-session-map-information {
     description "Show mapping of CoS objects to L2TP sessions";
     input {
       leaf session-id {
         description "Session Index";
         type union {
           type uint16;
           type string {
             pattern "<.*>|$.*";
           }
         }
       }
     }
     output {
       container cos-l2tp-session-information {
         uses cos-l2tp-session-information-block;
       }
     }
   }
   rpc get-cos-loss-priority-map-information {
     description "Show mapping of code point to loss priority";
     input {
       leaf loss-priority-map-name {
         description "Name of loss priority map";
         type string;
       }
       leaf type {
         type enumeration {
           enum "frame-relay-de" {
             description "Frame Relay discard eligible code point";
           }
         }
       }
     }
     output {
       container cos-loss-priority-map-information {
         uses cos-loss-priority-map-information-block;
       }
     }
   }
   rpc get-cos-loss-priority-rewrite-information {
     description "Show mapping of loss priority to code point";
     input {
       leaf loss-priority-rewrite-name {
         description "Name of loss priority rewrite";
         type string;
       }
       leaf type {
         type enumeration {
           enum "frame-relay-de" {
             description "Frame Relay discard eligible code point";
           }
         }
       }
     }
     output {
       container cos-loss-priority-rewrite-information {
         uses cos-loss-priority-rewrite-information-block;
       }
     }
   }
   rpc get-cos-rewrite-information {
     description "Show mapping of forwarding class/loss priority to code point";
     input {
       leaf control-plane-instance {
         type string;
       }
       leaf rewrite-rule-name {
         description "Name of rewrite rule";
         type string;
       }
       leaf type {
         description "Type of rewrite rule";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "frame-relay-de" {
             description "Frame relay discard eligible bit code point";
           }
           enum "ieee-802.1ad" {
             description "IEEE-802.1ad (DEI) code point";
           }
           enum "inet6-precedence" {
             description "IPv6 precedence code point";
           }
         }
       }
     }
     output {
       container cos-rewrite-information {
         uses cos-rewrite-information-block;
       }
     }
   }
   rpc get-cos-multi-destination-information {
     description "Show multi destination";
     output {
       container cos-multi-destination-information {
         uses cos-multi-destination-information-block;
       }
     }
   }
   rpc get-cos-multi-destination-classifier-binding-information {
     description "Multi-destination classifier bindings";
     output {
       container cos-multi-destination-classifier-binding-information {
         uses cos-multi-destination-classifier-binding-information-block;
       }
     }
   }
   rpc get-cos-system-defaults-information {
     description "Show system defaults";
     output {
       container cos-system-defaults-information {
         uses cos-system-defaults-information-block;
       }
     }
   }
   rpc get-cos-code-point-map-information {
     description "Show mapping of symbolic name to code point bit pattern";
     input {
       leaf control-plane-instance {
         type string;
       }
       leaf type {
         description "Type of code point alias";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "inet6-precedence" {
             description "IPv6 precedence code point";
           }
         }
       }
     }
     output {
       container cos-code-point-map-information {
         uses cos-code-point-map-information-block;
       }
     }
   }
   rpc get-cos-scheduler-map-information {
     description "Show mapping of forwarding classes to schedulers";
     input {
       leaf control-plane-instance {
         type string;
       }
       leaf scheduler-map-name {
         description "Name of scheduler map";
         type string;
       }
       leaf user-plane {
         description "User plane name";
         type string;
       }
       leaf static-only {
         description "Display static configuration on CP";
         type empty;
       }
     }
     output {
       container cos-scheduler-map-information {
         uses cos-scheduler-map-information-block;
       }
     }
   }
   rpc get-cos-traffic-control-profile-information {
     description "Show traffic control profiles";
     input {
       leaf control-plane-instance {
         type string;
       }
       leaf traffic-control-profile-name {
         description "Name of traffic control profile";
         type string;
       }
       leaf user-plane {
         description "User plane name";
         type string;
       }
       leaf static-only {
         description "Display static configuration on CP";
         type empty;
       }
     }
     output {
       container cos-traffic-control-profile-information {
         uses cos-traffic-control-profile-information-block;
       }
     }
   }
   rpc get-cos-fragmentation-map-information {
     description "Show mapping of forwarding classes to fragmentation options";
     input {
       leaf fragmentation-map-name {
         description "Name of fragmentation map";
         type string;
       }
     }
     output {
       container cos-fragmentation-map-information {
         uses cos-fragmentation-map-information-block;
       }
     }
   }
   rpc get-cos-slice-information {
     description "Show mapping of slices to interfaces";
     input {
       leaf slice-name {
         description "Name of slice";
         type string;
       }
       leaf interface {
         description "Name of interface or logical interface";
         type string;
         mandatory true;
       }
     }
     output {
       container cos-slice-information {
         uses cos-slice-information-block;
       }
     }
   }
   rpc get-cos-interface-map-information {
     description "Show mapping of CoS objects to interfaces";
     input {
       leaf interface-name {
         description "Name of interface";
         type string;
       }
       leaf level {
         type enumeration {
           enum "comprehensive" {
             description "Show interface, filter, policer and CoS information comprehensively";
           }
           enum "detail" {
             description "Show interface information, filter, policer and CoS object names";
           }
         }
       }
     }
     output {
       container cos-interface-information {
         uses cos-interface-information-block;
       }
     }
   }
   rpc get-cos-interface-set-map-information {
     description "Show mapping of CoS objects to interface-set";
     input {
       leaf control-plane-instance {
         type string;
       }
       leaf interface-set-name {
         description "Name of interface set";
         type string;
       }
     }
     output {
       container cos-interface-set-information {
         uses cos-interface-set-information-block;
       }
     }
   }
   rpc get-cos-routing-instance-map-information {
     description "Show mapping of CoS objects to routing instance";
     input {
       leaf routing-instance-name {
         description "Name of routing instance";
         type string;
       }
     }
     output {
       container cos-routing-instance-information {
         uses cos-routing-instance-information-block;
       }
     }
   }
   rpc get-cos-table-information {
     description "Show forwarding table information";
     input {
       uses command-forwarding;
     }
     output {
       container cos-table-information {
         uses cos-table-information-block;
       }
     }
   }
   rpc get-cos-classifier-table-information {
     description "Show classifier information";
     output {
       container cos-classifier-table-information {
         uses cos-classifier-table-information-block;
       }
     }
   }
   rpc get-cos-classifier-table-map-information {
     description "Show mapping of interfaces to classifiers";
     output {
       container cos-classifier-table-map-information {
         uses cos-classifier-table-map-information-block;
       }
     }
   }
   rpc get-cos-tcm-table-information {
     description "Show traffic-class-map information";
     output {
       container cos-tcm-table-information {
         uses cos-tcm-table-information-block;
       }
     }
   }
   rpc get-cos-tcm-table-map-information {
     description "Show mapping of interfaces to traffic-class-map";
     output {
       container cos-tcm-table-map-information {
         uses cos-tcm-table-map-information-block;
       }
     }
   }
   rpc get-cos-policy-map-table-information {
     description "Show Policy-map information";
     output {
       container cos-policy-map-table-information {
         uses cos-policy-map-table-information-block;
       }
     }
   }
   rpc get-cos-policy-map-table-map-information {
     description "Show mapping of interfaces to Policy-map";
     output {
       container cos-policy-map-table-mapping-information {
         uses cos-policy-map-table-mapping-information-block;
       }
     }
   }
   rpc get-cos-loss-priority-map-table-information {
     description "Show loss priority map table";
     output {
       container cos-loss-priority-map-table-information {
         uses cos-loss-priority-map-table-information-block;
       }
     }
   }
   rpc get-cos-loss-priority-map-table-binding-information {
     description "Show interface to loss priority map binding";
     output {
       container cos-loss-priority-map-table-binding-information {
         uses cos-loss-priority-map-table-binding-information-block;
       }
     }
   }
   rpc get-cos-loss-priority-rewrite-table-information {
     description "Show loss priority rewrite table";
     output {
       container cos-loss-priority-rewrite-table-information {
         uses cos-loss-priority-rewrite-table-information-block;
       }
     }
   }
   rpc get-cos-loss-priority-rewrite-table-binding-information {
     description "Show interface to loss priority rewrite binding";
     output {
       container cos-loss-priority-rewrite-table-binding-information {
         uses cos-loss-priority-rewrite-table-binding-information-block;
       }
     }
   }
   rpc get-cos-slice-table-information {
     description "Show slice information";
     output {
       container cos-slice-table-information {
         uses cos-slice-table-information-block;
       }
     }
   }
   rpc get-slice-table-information {
     description "Show mapping of traffic control profiles to slices";
     output {
       container cos-scheduler-map-table-information {
         uses cos-scheduler-map-table-information-block;
       }
     }
   }
   rpc get-cos-scheduler-map-table-information {
     description "Show scheduler map";
     output {
       container cos-scheduler-map-table-information {
         uses cos-scheduler-map-table-information-block;
       }
     }
   }
   rpc get-scheduler-map-table-map-information {
     description "Show mapping of scheduler-maps to interfaces";
     output {
       container cos-scheduler-map-table-information {
         uses cos-scheduler-map-table-information-block;
       }
     }
   }
   rpc get-cos-policer-table-map-information {
     description "Show policer";
     output {
       container cos-policer-table-map-information {
         uses cos-policer-table-map-information-block;
       }
     }
   }
   rpc get-cos-shaper-table-map-information {
     description "Show shaper";
     output {
       container cos-shaper-table-map-information {
         uses cos-shaper-table-map-information-block;
       }
     }
   }
   rpc get-cos-red-information {
     description "Show random early detection drop profile";
     output {
       container cos-red-information {
         uses cos-red-information-block;
       }
     }
   }
   rpc get-cos-rewrite-table-information {
     description "Show rewrite information";
     output {
       container cos-rewrite-table-information {
         uses cos-rewrite-table-information-block;
       }
     }
   }
   rpc get-cos-rewrite-table-map-information {
     description "Show interface to rewrite rule mapping";
     output {
       container cos-rewrite-table-map-information {
         uses cos-rewrite-table-map-information-block;
       }
     }
   }
   rpc get-cos-forwarding-class-map-table-information {
     description "Show forwarding class map information";
     output {
       container cos-forwarding-class-map-table-information {
         uses cos-forwarding-class-map-table-information-block;
       }
     }
   }
   rpc get-cos-forwarding-class-map-interface-table-information {
     description "Show interface to forwarding class mapping";
     output {
       container cos-forwarding-class-map-interface-table-information {
         uses cos-forwarding-class-map-interface-table-information-block;
       }
     }
   }
   rpc get-cos-fwtab-fabric-scheduler-map-information {
     description "Show fabric scheduler map";
     output {
       container cos-fabric-scheduler-map-table-information {
         uses cos-fabric-scheduler-map-table-information-block;
       }
     }
   }
   rpc get-cos-translation-table-information {
     description "Show translation table information";
     output {
       container cos-translation-table-information {
         uses cos-translation-table-information-block;
       }
     }
   }
   rpc get-cos-translation-table-mapping-information {
     description "Show mapping of interfaces to translation table";
     output {
       container cos-translation-table-mapping-information {
         uses cos-translation-table-mapping-information-block;
       }
     }
   }
   rpc get-fabric-queue-information {
     description "Show fabric queue statistics";
     input {
       leaf destination {
         description "Destination FPC for which to show details";
         type union {
           type string {
             pattern "<.*>|$.*";
           }
           type int32;
         }
       }
       leaf source {
         description "Source FPC for which to show details";
         type union {
           type string {
             pattern "<.*>|$.*";
           }
           type int32;
         }
       }
       leaf summary {
         description "Display summary output";
         type empty;
       }
     }
     output {
       container fabric-queue-information {
         uses fabric-queue-information-block;
       }
     }
   }
   rpc get-fabric-queue-detailed-information {
     description "Display detailed pfe level statistics";
     input {
       leaf destination-fpc {
         description "Destination FPC for which to show details";
         type union {
           type string {
             pattern "<.*>|$.*";
           }
           type int32;
         }
       }
       leaf destination-pfe {
         description "Destination pfe for which to show details";
         type union {
           type string {
             pattern "<.*>|$.*";
           }
           type int32;
         }
       }
       leaf source-fpc {
         description "Source FPC for which to show details";
         type union {
           type string {
             pattern "<.*>|$.*";
           }
           type int32;
         }
       }
       leaf source-pfe {
         description "Source pfe for which to show details";
         type union {
           type string {
             pattern "<.*>|$.*";
           }
           type int32;
         }
       }
     }
     output {
       container fabric-queue-detailed-information {
         uses fabric-queue-detailed-information-block;
       }
     }
   }
   rpc get-cos-fabric-scheduler-map-information {
     description "Show fabric scheduler map information";
     input {
       leaf control-plane-instance {
         type string;
       }
     }
     output {
       container cos-fabric-scheduler-map-information {
         uses cos-fabric-scheduler-map-information-block;
       }
     }
   }
   rpc get-cos-translation-table-map-information {
     description "Show mapping of code point to code point";
     input {
       leaf translation-table-name {
         description "Name of translation table";
         type string;
       }
       leaf type {
         description "Type of translation table";
         type enumeration {
           enum "to-inet-precedence-from-inet-precedence" {
             description "INET PRECEDENCE to INET PRECEDENCE translation table";
           }
           enum "to-dscp-from-dscp" {
             description "DSCP to DSCP translation table";
           }
           enum "to-dscp-ipv6-from-dscp-ipv6" {
             description "DSCP IPV6 to DSCP IPV6 translation table";
           }
           enum "to-exp-from-exp" {
             description "EXP to EXP translation table";
           }
         }
       }
     }
     output {
       container cos-translation-table-map-information {
         uses cos-translation-table-map-information-block;
       }
     }
   }
   rpc get-cos-congestion-notification-information {
     description "Show congestion-notification information";
     input {
       leaf control-plane-instance {
         type string;
       }
       leaf cnp-name {
         description "Name of congestion notification profile";
         type string;
       }
     }
     output {
       container cos-congestion-notification-information {
         uses cos-congestion-notification-information-block;
       }
     }
   }
   rpc get-cos-adjustment-control-profile-information {
     description "Show adjustment control profile information";
     input {
       leaf control-plane-instance {
         type string;
       }
       leaf adjustment-control-profile-name {
         description "Name of the adjustment control profile";
         type string;
       }
     }
     output {
       container cos-adjustment-control-profile-information {
         uses cos-adjustment-control-profile-information-block;
       }
     }
   }
   rpc get-fpc-scheduler-hierarchy-information {
     description "Show scheduler hierarchy information for FPC slot";
     input {
       leaf slot {
         description "FPC slot number";
         type union {
           type string {
             pattern "<.*>|$.*";
           }
           type uint32;
         }
         mandatory true;
       }
       leaf level {
         type enumeration {
           enum "detail" {
             description "Show detailed scheduler hierarchy";
           }
           enum "terse" {
             description "Show terse scheduler hierarchy";
           }
         }
       }
       leaf direction {
         type enumeration {
           enum "ingress" {
             description "Show ingress scheduler hierarchy";
           }
           enum "egress" {
             description "Show egress scheduler hierarchy";
           }
         }
       }
     }
     output {
       container scheduler-hierarchy-information {
         uses scheduler-hierarchy-information-block;
       }
     }
   }
   rpc get-interface-scheduler-hierarchy-information {
     description "Show scheduler hierarchy view for a specific interface";
     input {
       leaf interface-name {
         description "Name of physical or logical interface";
         type string;
         mandatory true;
       }
       leaf level {
         type enumeration {
           enum "detail" {
             description "Show detailed interface scheduler hierarchy";
           }
           enum "terse" {
             description "Show terse interface scheduler hierarchy";
           }
         }
       }
       leaf direction {
         type enumeration {
           enum "ingress" {
             description "Show ingress scheduler hierarchy";
           }
           enum "egress" {
             description "Show egress scheduler hierarchy";
           }
         }
       }
     }
     output {
       container scheduler-hierarchy-information {
         uses scheduler-hierarchy-information-block;
       }
     }
   }
   rpc get-interface-set-scheduler-hierarchy-information {
     description "Show scheduler hierarchy view for a specific interface-set";
     input {
       leaf interface-set-name {
         description "Name of interface set";
         type string;
         mandatory true;
       }
       leaf level {
         type enumeration {
           enum "detail" {
             description "Show detailed interface-set scheduler hierarchy";
           }
           enum "terse" {
             description "Show terse interface-set scheduler hierarchy";
           }
         }
       }
       leaf direction {
         type enumeration {
           enum "ingress" {
             description "Show ingress scheduler hierarchy";
           }
           enum "egress" {
             description "Show egress scheduler hierarchy";
           }
         }
       }
     }
     output {
       container scheduler-hierarchy-information {
         uses scheduler-hierarchy-information-block;
       }
     }
   }
   rpc get-scheduler-resources-information {
     description "Show scheduler resources information for FPC";
     output {
       container scheduler-resources-information {
         uses scheduler-resources-information-block;
       }
     }
   }
   rpc get-scheduler-resources-fpc-slot-information {
     description "Show scheduler resources information for FPC slot";
     input {
       leaf slot {
         description "FPC slot number";
         type union {
           type string {
             pattern "<.*>|$.*";
           }
           type uint32;
         }
         mandatory true;
       }
     }
     output {
       container scheduler-resources-information {
         uses scheduler-resources-information-block;
       }
     }
   }
   rpc get-cos-junos-client-information {
     description "Show COS clients information";
     input {
       choice client-id-choice {
         case name {
           leaf client-name {
             description "Name of client";
             type string;
           }
         }
         case internal-id {
           leaf internal-id {
             description "Internal identifier of a client";
             type union {
               type uint32;
               type string {
                 pattern "<.*>|$.*";
               }
             }
           }
         }
       }
       leaf classifier {
         description "Name of classifier. Use 'all' to show entire list";
         type string;
       }
       leaf classifier-type {
         description "Type of classifier";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "ieee-802.1ad" {
             description "IEEE-802.1ad (DEI) code point";
           }
           enum "any" {
             description "Any code point type";
           }
         }
       }
       leaf rewrite-rule {
         description "Name of rewrite rule. Use 'all' to show entire list";
         type string;
       }
       leaf rewrite-type {
         description "Type of rewrite rule";
         type enumeration {
           enum "dscp" {
             description "Differentiated Services code point (DSCP)";
           }
           enum "dscp-ipv6" {
             description "Differentiated Services code point (DSCP) for IPv6";
           }
           enum "exp" {
             description "MPLS experimental code point";
           }
           enum "ieee-802.1" {
             description "IEEE-802.1 code point";
           }
           enum "inet-precedence" {
             description "IPv4 precedence code point";
           }
           enum "frame-relay-de" {
             description "Frame relay discard eligible bit code point";
           }
           enum "ieee-802.1ad" {
             description "IEEE-802.1ad (DEI) code point";
           }
           enum "inet6-precedence" {
             description "IPv6 precedence code point";
           }
           enum "any" {
             description "Any code point type";
           }
         }
       }
       leaf interface {
         description "Name of interface. Use 'all' to show all interfaces";
         type string;
       }
       leaf routing-instance {
         description "Name of routing instance. Use 'all' to show all instances";
         type string;
       }
     }
     output {
       container cos-information {
         uses cos-information-block;
       }
     }
   }
   rpc get-cos-junos-client-summary {
     description "Show COS clients summary";
     input {
       leaf control-plane-instance {
         type string;
       }
     }
     output {
       container cos-client-information {
         uses cos-client-information-block;
       }
     }
   }
   rpc get-cos-bind-point-ownership-summary {
     description "Show cos bind point ownership summary";
     output {
       container cos-client-information {
         uses cos-client-information-block;
       }
     }
   }
   rpc get-host-outbound-traffic-information {
     description "Show host outbound traffic information";
     output {
       container cos-host-outbound-info {
         uses cos-host-outbound-info-block;
       }
     }
   }
   rpc get-host-outbound-protocol-traffic-information {
     description "Show protocol specific host outbound traffic information";
     input {
       leaf control-plane-instance {
         type string;
       }
       leaf protocol-name {
         description "Name of protocol";
         type enumeration {
           enum "isis-over-gre" {
             description "ISIS over GRE";
           }
           enum "default" {
             description "Default values";
           }
         }
         mandatory true;
       }
     }
     output {
       container cos-host-outbound-info {
         uses cos-host-outbound-info-block;
       }
     }
   }
   rpc get-cos-packet-buffer-information {
     description "Show packet Buffer Information";
   }
   rpc get-cos-packet-buffer-usage-information {
     description "Show packet Buffer Usage Information";
     output {
       container cos-packet-buffer-usage-information {
         uses cos-packet-buffer-usage-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping cos-information-block {
     list cos-stream-information {
       description "Information about the traffic stream";
     }
     container cos-forwarding-class-information {
       container fc-map {
         description "Class-of-service forwarding class to queue mapping";
         list fc-map-item {
           leaf fc-name {
             type string;
             description "Class-of-service forwarding class name";
           }
           leaf fc-number {
             type uint32;
             description "Identifier for Class-of-service forwarding class";
           }
           leaf fc-queue-number {
             type uint32;
             description "Class-of-service forwarding class queue number";
           }
           leaf fc-rqueue-number {
             type uint32;
             description "Class-of-service forwarding class restricted queue number";
           }
           leaf fc-priority {
             type string;
             description "Class-of-service forwarding class queue priority";
           }
           leaf fc-policing-priority {
             type string;
             description "Class-of-service forwarding class policing priority";
           }
           leaf fc-spu-priority {
             type string;
             description "Class-of-service forwarding class spu priority";
           }
           leaf fc-no-loss {
             type string;
             description "Class-of-service forwarding class no-loss";
           }
           leaf fc-pfc-priority {
             type uint32;
             description "Class-of-service forwarding class pfc-priority";
           }
           leaf fc-multicast {
             type string;
             description "Class-of-service forwarding class multicast";
           }
         }
       }
     }
     container cos-forwarding-class-map-information {
       container fc-map {
         description "Class-of-service forwarding class to queue mapping";
         list fc-map-item {
           leaf fc-name {
             type string;
             description "Class-of-service forwarding class name";
           }
           leaf fc-number {
             type uint32;
             description "Identifier for Class-of-service forwarding class";
           }
           leaf fc-queue-number {
             type uint32;
             description "Class-of-service forwarding class queue number";
           }
           leaf fc-rqueue-number {
             type uint32;
             description "Class-of-service forwarding class restricted queue number";
           }
           leaf fc-priority {
             type string;
             description "Class-of-service forwarding class queue priority";
           }
           leaf fc-policing-priority {
             type string;
             description "Class-of-service forwarding class policing priority";
           }
           leaf fc-spu-priority {
             type string;
             description "Class-of-service forwarding class spu priority";
           }
           leaf fc-no-loss {
             type string;
             description "Class-of-service forwarding class no-loss";
           }
           leaf fc-pfc-priority {
             type uint32;
             description "Class-of-service forwarding class pfc-priority";
           }
           leaf fc-multicast {
             type string;
             description "Class-of-service forwarding class multicast";
           }
         }
       }
     }
     container cos-classifier-information {
       list classifier {
         description "Class-of-service code point classifier";
         leaf classifier-name {
           type string;
           description "Class-of-service classifier name";
         }
         leaf code-point-type {
           type string;
           description "Class-of-service code point type";
         }
         leaf table-index {
           type uint32;
           description "Table index";
         }
         container classifier-map {
           list classifier-map-item {
             leaf code-point {
               type string;
               description "Class-of-service code point alias name or bits";
             }
             leaf fc-name {
               type string;
               description "Class-of-service forwarding class name";
             }
             leaf loss-priority {
               type string;
               description "Class-of-service loss priority";
             }
             leaf cntag-present {
               type string;
               description "Class-of-service cntag present";
             }
           }
         }
       }
     }
     container cos-loss-priority-map-information {
       list loss-priority-map {
         description "Class-of-service code point loss priority map";
         leaf loss-priority-map-name {
           type string;
           description "Name of class-of-service loss priority map";
         }
         leaf code-point-type {
           type string;
           description "Class-of-service code point type";
         }
         leaf table-index {
           type uint32;
           description "Table index";
         }
         list loss-priority-map-table {
           list loss-priority-map-item {
             leaf code-point {
               type string;
               description "Class-of-service code point alias name or bits";
             }
             leaf loss-priority {
               type string;
               description "Class-of-service loss priority";
             }
           }
           list loss-priority-map-table-entry {
             leaf table-index {
               type uint32;
               description "Table index";
             }
             leaf code-point {
               type string;
               description "Class-of-service code point alias name or bits";
             }
             leaf loss-priority {
               type string;
               description "Class-of-service loss priority";
             }
           }
         }
       }
     }
     container cos-drop-profile-information {
       list drop-profile {
         description "Class-of-service drop profile";
         leaf profile-name {
           type string;
           description "Class-of-service drop profile name";
         }
         leaf profile-type {
           type string;
           description "Class-of-service drop profile type";
         }
         leaf table-index {
           type uint32;
           description "Table index";
         }
         container profile-map {
           container profile-map-item {
             leaf fill-level {
               type uint32;
               description "Class-of-service drop profile fill level value";
             }
             leaf probability {
               type uint32;
               description "Class-of-service drop profile probability value";
             }
           }
         }
       }
     }
     container cos-mpls-ecn-map-information {
       list cos-mpls-ecn-map-info {
         description "Class-of-service mpls-ecn-map information";
         leaf ecn-capable-exp {
           type int32;
           description "ECN capable exp";
         }
         leaf congestion-experienced-exp {
           type int32;
           description "Congestion Expereienced exp";
         }
       }
     }
     container cos-monitoring-profile-information {
       list monitoring-profile {
         description "Class-of-service monitoring profile";
         leaf monitoring-profile-name {
           type string;
           description "Class-of-service monitoring profile name";
         }
         container export-filters {
           container export-filter {
             leaf filter-name {
               type string;
               description "Class-of-service monitoring profile filter name";
             }
             leaf monitoring-queue-number {
               type uint32;
               description "Class-of-service monitoring profile filter queue value";
             }
             leaf peak-queue-length-value {
               type uint32;
               description "Class-of-service monitoring profile peak queue length value";
             }
           }
         }
       }
     }
     container cos-rewrite-information {
       list rewrite {
         description "Class-of-service drop profile";
         leaf rewrite-name {
           type string;
           description "Class-of-service rewrite rule name";
         }
         leaf code-point-type {
           type string;
           description "Class-of-service code point type";
         }
         leaf table-index {
           type uint32;
           description "Table index";
         }
         container rewrite-map {
           list rewrite-map-item {
             leaf fc-name {
               type string;
               description "Class-of-service forwarding class name";
             }
             leaf loss-priority {
               type string;
               description "Class-of-service loss priority";
             }
             leaf code-point {
               type string;
               description "Class-of-service code point alias name or bits";
             }
           }
         }
       }
     }
     container cos-loss-priority-rewrite-information {
       list loss-priority-rewrite {
         description "Class-of-service loss priority to code point rewrite";
         leaf loss-priority-rewrite-name {
           type string;
           description "Name of class-of-service loss priority rewrite";
         }
         leaf code-point-type {
           type string;
           description "Class-of-service code point type";
         }
         leaf table-index {
           type uint32;
           description "Table index";
         }
         list loss-priority-rewrite-table {
           list loss-priority-rewrite-item {
             leaf loss-priority {
               type string;
               description "Class-of-service loss priority";
             }
             leaf code-point {
               type string;
               description "Class-of-service code point alias name or bits";
             }
           }
           list loss-priority-rewrite-table-entry {
             leaf table-index {
               type uint32;
               description "Table index";
             }
             leaf loss-priority {
               type string;
               description "Class-of-service loss priority";
             }
             leaf code-point {
               type string;
               description "Class-of-service code point alias name or bits";
             }
           }
         }
       }
     }
     container cos-code-point-map-information {
       list code-point-map {
         description "Class-of-service code point alias map";
         leaf code-point-type {
           type string;
           description "Class-of-service code point type";
         }
         container alias-map {
           list alias-map-item {
             leaf code-point-alias {
               type string;
               description "Class-of-service code point alias name";
             }
             leaf code-point-bits {
               type string;
               description "Class-of-service code point bit sequence";
             }
           }
         }
       }
     }
     container cos-fragmentation-map-information {
       list fragmentation-map {
         description "Class-of-service fragmentation map";
         leaf fragmentation-map-name {
           type string;
           description "Class-of-service fragmentation map name";
         }
         leaf fragmentation-map-index {
           type uint32;
           description "Index number for Class-of-service fragmentation map";
         }
         list fragment-map {
           leaf fc-name {
             type string;
             description "Class-of-service forwarding class name";
           }
           leaf no-fragmentation {
             type empty;
             description "Do not fragment packets of this class";
           }
           leaf fragment-threshold {
             type string;
             description "Fragmentation threshold";
           }
           leaf fragment-multilink-class {
             type int32;
             description "Identifier for multilink class";
           }
         }
       }
     }
     container cos-translation-table-map-information {
       list translation-table {
         description "Class-of-service code point translation table";
         leaf translation-table-name {
           type string;
           description "Class-of-service translation table name";
         }
         leaf translation-table-type {
           type string;
           description "Class-of-service translation table type";
         }
         leaf table-index {
           type uint32;
           description "Table index";
         }
         container translation-table-map {
           container translation-table-map-item {
             leaf from-code-point {
               type string;
               description "Class-of-service code point alias name or bits";
             }
             leaf to-code-point {
               type string;
               description "Class-of-service code point alias name or bits";
             }
           }
         }
         list translation-table-entry {
           leaf table-index {
             type uint32;
             description "Table index";
           }
           leaf from-code-point {
             type string;
             description "Class-of-service code point alias name or bits";
           }
           leaf to-code-point {
             type string;
             description "Class-of-service code point alias name or bits";
           }
         }
       }
     }
     container cos-multi-destination-information {
       container sm-md-map {
         leaf scheduler-map-name {
           type string;
           description "Class-of-service scheduler map name";
         }
         leaf scheduler-map-index {
           type uint64;
           description "Class-of-service scheduler map index";
         }
       }
       container fc-md-map {
         leaf fc-name {
           type string;
           description "Class-of-service forwarding class name";
         }
         leaf fc-queue-number {
           type uint32;
           description "Class-of-service forwarding class queue number";
         }
       }
       container cls-md-map {
         leaf multidest-classifier-name {
           type string;
           description "Multi destination classifier name";
         }
         leaf multidest-classifier-type {
           type string;
           description "Multi destination classifier type";
         }
         leaf multidest-classifier-index {
           type uint32;
           description "Multi destination classifier id";
         }
       }
     }
     container cos-forwarding-class-set-information {
       list forwarding-class-set {
         description "Class-of-service forwarding class set information";
         list forwarding-class-set-entry {
           leaf forwarding-class-set-name {
             type string;
             description "Class-of-service forwarding class set name";
           }
           leaf forwarding-class-set-type {
             type string;
             description "Identifier for Class-of-service forwarding class set type";
           }
           leaf forwarding-class-set-index {
             type uint32;
             description "Identifier for Class-of-service forwarding class set";
           }
           container fc-map {
             list fc-map-item {
               leaf fc-name {
                 type string;
                 description "Class-of-service forwarding class name";
               }
               leaf fc-number {
                 type uint32;
                 description "Identifier for Class-of-service forwarding class";
               }
               leaf fc-queue-number {
                 type uint32;
                 description "Class-of-service forwarding class queue number";
               }
               leaf fc-rqueue-number {
                 type uint32;
                 description "Class-of-service forwarding class restricted queue number";
               }
               leaf fc-priority {
                 type string;
                 description "Class-of-service forwarding class queue priority";
               }
               leaf fc-policing-priority {
                 type string;
                 description "Class-of-service forwarding class policing priority";
               }
               leaf fc-spu-priority {
                 type string;
                 description "Class-of-service forwarding class spu priority";
               }
               leaf fc-no-loss {
                 type string;
                 description "Class-of-service forwarding class no-loss";
               }
               leaf fc-pfc-priority {
                 type uint32;
                 description "Class-of-service forwarding class pfc-priority";
               }
               leaf fc-multicast {
                 type string;
                 description "Class-of-service forwarding class multicast";
               }
             }
           }
         }
       }
     }
     container cos-policy-map-information {
       list policy-map {
         description "Class-of-service Policy-map";
         leaf policy-map-name {
           type string;
           description "Class-of-service Policy-map name";
         }
         leaf table-index {
           type uint32;
           description "Table index";
         }
         leaf policy-map-user-attribute {
           type uint32;
           description "User-defined attribute";
         }
         container policy-map-cp-entries {
           leaf code-point-type {
             type string;
             description "Class-of-service code point type";
           }
           leaf code-point {
             type string;
             description "Class-of-service code point alias name or bits";
           }
           leaf code-point-option {
             type string;
             description "Class-of-service code point option flag";
           }
         }
       }
     }
     container cos-client-info {
       list cos-client {
         description "Class-of-service Junos client information";
         leaf cos-client-info-internal-id {
           type uint32;
           description "Junos client internal identifier";
         }
         leaf cos-client-info-requests {
           type uint32;
           description "Number of requests from Junos client";
         }
         leaf cos-client-info-responses {
           type uint32;
           description "Number of responses to Junos client";
         }
         leaf cos-client-info-failures {
           type uint32;
           description "Number of failures while handling Junos client requests";
         }
         leaf cos-client-info-identifier {
           type string;
           description "Junos client identifier";
         }
         leaf cos-client-name {
           type string;
           description "Junos client name";
         }
         leaf cos-client-state {
           type string;
           description "Junos client state information";
         }
         leaf cos-client-internal-name {
           type string;
           description "Junos client internal name";
         }
         leaf cos-client-stats {
           type string;
           description "Junos client statistics";
         }
         leaf cos-client-failure-stats {
           type string;
           description "Junos client failure/error statistics";
         }
         leaf cos-client-validate-failures {
           type uint32;
           description "Junos client request validation failures";
         }
         leaf cos-client-ownership-failures {
           type uint32;
           description "Junos client ownership validation failures";
         }
         leaf cos-client-info-name {
           type string;
           description "CoS client name";
         }
         leaf cos-client-internal-id {
           type uint32;
           description "Junos client internal identifier";
         }
         leaf cos-client-requests {
           type uint64;
           description "Number of requests from Junos client";
         }
         leaf cos-client-responses {
           type uint64;
           description "Number of responses to Junos client";
         }
         leaf cos-client-failures {
           type uint64;
           description "Number of failures while handling Junos client requests";
         }
         leaf cos-client-identifier {
           type string;
           description "Junos client identifier";
         }
         leaf cos-client-status {
           type string;
           description "Junos client status";
         }
         leaf cos-client-connected-time {
           type string;
           description "Junos client time of connect";
         }
         leaf cos-client-reconnected-time {
           type string;
           description "Junos client time of reconnect";
         }
         leaf cos-client-disconnected-time {
           type string;
           description "Junos client time of disconnect";
         }
         leaf cos-client-message-type {
           type string;
           description "Junos client message type";
         }
         leaf cos-client-operation-type {
           type string;
           description "Junos client operation type";
         }
         leaf-list cos-bind-point-type {
           type string;
           description "Class-of-service bind point type";
         }
         leaf-list cos-bind-point-owner-type {
           type string;
           description "Class-of-service bind point owner type";
         }
         leaf-list cos-bind-point-owner-internal-id {
           type uint32;
           description "Junos client internal identifier";
         }
         leaf-list cos-bind-point-name {
           type string;
           description "Class-of-service bind point name";
         }
         leaf cos-bind-point-feature {
           type string;
           description "Class-of-service bind point feature name";
         }
         leaf cos-bind-point-feature-object-name {
           type string;
           description "Class-of-service bind point feature object name";
         }
       }
     }
     container cos-host-outbound-info {
       list cos-host-outbound-traffic-info {
         description "Class-of-service host-outbound-traffic information";
         leaf cos-host-outbound-traffic-protocol-name {
           type string;
           description "CoS host outbound traffic protocol name";
         }
         leaf cos-host-outbound-traffic-dscp {
           type string;
           description "CoS host outbound traffic dscp";
         }
         leaf cos-host-outbound-traffic-dot1p {
           type string;
           description "CoS host outbound traffic ieee 802.1p";
         }
         leaf cos-host-outbound-traffic-fc-id {
           type string;
           description "CoS host outbound traffic forwarding class id";
         }
         leaf cos-host-outbound-traffic-queue-id {
           type string;
           description "CoS host outbound traffic queue id";
         }
         leaf cos-host-outbound-traffic-restrict-queue-id {
           type string;
           description "CoS host outbound traffic restrict queue id";
         }
         leaf cos-host-outbound-traffic-override-firewall {
           type string;
           description "CoS host outbound traffic override firwall action";
         }
         leaf cos-host-outbound-traffic-rw-dot1p {
           type string;
           description "CoS host outbound traffic - use ieee 802.1p rewrite rules";
         }
       }
     }
     container cos-drop-congestion-notification-information {
       list cos-drop-congestion-notification-info {
         description "Class-of-service drop-congestion-notification information";
         leaf cos-dcn-fc-name {
           type string;
           description "Cos DCN forwarding class";
         }
         leaf cos-dcn-udp-port {
           type int32;
           description "Cos DCN udp port number";
         }
       }
     }
     container cos-dedicated-buffer-profile-information {
       list dedicated-buffer-profile {
         description "Class-of-service dedicated buffer profile";
         leaf dedicated-buffer-profile-name {
           type string;
           description "Class-of-service dedicated buffer profile name";
         }
         leaf dedicated-buffer-profile-index {
           type int32;
           description "Class-of-service dedicated buffer profile index";
         }
         leaf ingress-buffer-size {
           type string;
           description "Ingress per port dedicated buffer in cells";
         }
         leaf egress-buffer-size {
           type string;
           description "Egress per port dedicated buffer in cells";
         }
       }
     }
     container cos-dynamic-threshold-profile-information {
       list dynamic-threshold-profile {
         description "Class-of-service dynamic threshold profile";
         leaf dynamic-threshold-profile-name {
           type string;
           description "Class-of-service dynamic threshold profile name";
         }
         leaf dynamic-threshold-profile-index {
           type uint64;
           description "Class-of-service dynamic threshold profile index";
         }
         list dynamic-threshold-profile-entry {
           description "Class-of-service dynamic threshold profile entry";
           leaf dynamic-threshold-profile-priority-group {
             type string;
             description "Class-of-service dynamic threshold profile priority group";
           }
           leaf dynamic-threshold-profile-threshold-value {
             type uint32;
             description "Class-of-service dynamic threshold profile threshold value";
           }
         }
       }
     }
     container cos-decn-profile-information {
       list decn-profile {
         description "Class-of-service decn profile";
         leaf decn-profile-name {
           type string;
           description "Class-of-service decn profile name";
         }
         leaf decn-profile-index {
           type uint64;
           description "Class-of-service decn profile index";
         }
         list decn-profile-queue {
           description "Class-of-service decn profile queue";
           leaf dynamic-explicit-congestion-notification-queue {
             type uint32;
             description "Class-of-service DECN queue";
           }
           leaf dynamic-explicit-congestion-notification-offset {
             type uint32;
             description "Class-of-service DECN offset";
           }
           leaf dynamic-explicit-congestion-notification-floor {
             type uint32;
             description "Class-of-service DECN floor";
           }
         }
       }
     }
     container cos-scheduler-map-information {
       list scheduler-map {
         description "Class-of-service scheduler map";
         leaf scheduler-map-name {
           type string;
           description "Class-of-service scheduler map name";
         }
         leaf scheduler-map-index {
           type uint64;
           description "Class-of-service scheduler map index";
         }
         leaf user-plane-name {
           type string;
           description "Class-of-service user-plane name for XDA";
         }
         list scheduler {
           leaf scheduler-name {
             type string;
             description "Class-of-service scheduler name";
           }
           leaf fc-name {
             type string;
             description "Class-of-service forwarding class name";
           }
           leaf scheduler-index {
             type uint64;
             description "Class of service scheduler index";
           }
           leaf scheduler-tx-rate {
             type string;
             description "Class-of-service scheduler transmit rate";
           }
           leaf scheduler-tx-limit {
             type string;
             description "Class-of-service scheduler transmit limit";
           }
           leaf scheduler-buffer-size {
             type string;
             description "Class-of-service scheduler buffer size";
           }
           leaf scheduler-buffer-multicast-share {
             type uint32;
             description "Class-of-service scheduler multicast buffer share";
           }
           leaf scheduler-buffer-limit {
             type string;
             description "Class-of-service scheduler buffer limit";
           }
           leaf scheduler-buffer-rate {
             type string;
             description "Class-of-service scheduler buffer rate";
           }
           leaf scheduler-shared-buffer-maximum-percentage {
             type uint32;
             description "Shared Buffer maximum percentage";
           }
           leaf scheduler-shared-buffer-multicast-maximum-percentage {
             type uint32;
             description "Shared Buffer multicast maximum percentage";
           }
           leaf scheduler-buffer-dynamic-threshold {
             type uint32;
             description "Queue shared-buffer dynamic threshold";
           }
           leaf scheduler-priority {
             type string;
             description "Class-of-service scheduler priority";
           }
           leaf scheduler-shaping-rate {
             type string;
             description "Class-of-service scheduler shaping rate";
           }
           leaf scheduler-shaping-rate-burst {
             type string;
             description "Class-of-service scheduler shaping rate burst";
           }
           leaf scheduler-adjust-minimum {
             type int32;
             description "Class-of-service scheduler adjustment minimum rate";
           }
           leaf scheduler-adjust-percent {
             type int32;
             description "Class-of-service scheduler percent adjustment for a queue";
           }
           leaf scheduler-excess-priority {
             type string;
             description "Class-of-service scheduler excess priority";
           }
           leaf scheduler-excess-rate {
             type string;
             description "Class-of-service scheduler excess rate";
           }
           leaf scheduler-explicit-congestion-notification {
             type string;
             description "Class-of-service ECN status of queue";
           }
           leaf scheduler-ecn-rtlog-rate-limit {
             type uint32;
             description "Class-of-service ECN Security Log Rate Limit";
           }
           leaf scheduler-ecn-no-pfc-assist {
             type string;
             description "Class-of-service ECN no pfc assist";
           }
           leaf scheduler-queue-monitoring {
             type string;
             description "Class-of-service queue depth monitoring of queue";
           }
           leaf scheduler-drop-profile-ln-index {
             type uint32;
             description "Class-of-service scheduler drop profile index low, non-TCP";
           }
           leaf scheduler-drop-profile-ln {
             type string;
             description "Class-of-service scheduler drop profile low, non-TCP";
           }
           leaf scheduler-drop-profile-lt-index {
             type uint32;
             description "Class-of-service scheduler drop profile index low, TCP";
           }
           leaf scheduler-drop-profile-lt {
             type string;
             description "Class-of-service scheduler drop profile low, TCP";
           }
           leaf scheduler-drop-profile-hn-index {
             type uint32;
             description "Class-of-service scheduler drop profile index high, non-TCP";
           }
           leaf scheduler-drop-profile-hn {
             type string;
             description "Class-of-service scheduler drop profile high, non-TCP";
           }
           leaf scheduler-drop-profile-ht-index {
             type uint32;
             description "Class-of-service scheduler drop profile index high, TCP";
           }
           leaf scheduler-drop-profile-ht {
             type string;
             description "Class-of-service scheduler drop profile high, TCP";
           }
           leaf scheduler-drop-profile-la-index {
             type uint32;
             description "Class-of-service scheduler drop profile index low";
           }
           leaf scheduler-drop-profile-la {
             type string;
             description "Class-of-service scheduler drop profile low";
           }
           leaf scheduler-drop-profile-ma-index {
             type uint32;
             description "Class-of-service scheduler drop profile index medium";
           }
           leaf scheduler-drop-profile-ma {
             type string;
             description "Class-of-service scheduler drop profile medium";
           }
           leaf scheduler-drop-profile-mla-index {
             type uint32;
             description "Class-of-service scheduler drop profile index medium-low";
           }
           leaf scheduler-drop-profile-mla {
             type string;
             description "Class-of-service scheduler drop profile medium-low";
           }
           leaf scheduler-drop-profile-mha-index {
             type uint32;
             description "Class-of-service scheduler drop profile index medium-high";
           }
           leaf scheduler-drop-profile-mha {
             type string;
             description "Class-of-service scheduler drop profile medium-high";
           }
           leaf scheduler-drop-profile-ha-index {
             type uint32;
             description "Class-of-service scheduler drop profile index high";
           }
           leaf scheduler-drop-profile-ha {
             type string;
             description "Class-of-service scheduler drop profile high";
           }
         }
       }
     }
     container cos-traffic-control-profile-information {
       list traffic-control-profile {
         description "Information about one or more traffic control profiles";
         leaf traffic-control-profile-name {
           type string;
           description "Class-of-service traffic control profile name";
         }
         leaf traffic-control-profile-index {
           type uint64;
           description "Index number for Class-of-service traffic control profile";
         }
         leaf user-plane-name {
           type string;
           description "Class-of-service user-plane name for XDA";
         }
         leaf scheduler-map-name {
           type string;
           description "Class-of-service scheduler map name";
         }
         leaf atm-service {
           type string;
           description "Class-of-service traffic control profile atm service";
         }
         leaf shaping-rate {
           type uint64;
           description "Class-of-service shaping rate";
         }
         leaf shaping-rate-burst {
           type uint32;
           description "Class-of-service shaping rate burst, in bytes";
         }
         leaf low-granularity {
           type uint32;
           description "Class-of-service low-granularity mode support";
         }
         leaf queue-mode-4q {
           type uint32;
           description "Class-of-service tcp-voq-mode(4Q) mode support";
         }
         leaf shaping-rate-priority-strict-high {
           type uint64;
           description "Class-of-service shaping rate for priority strict high";
         }
         leaf shaping-rate-priority-strict-high-burst {
           type uint32;
           description "Class-of-service shaping rate burst for priority strict-high";
         }
         leaf shaping-rate-priority-high {
           type uint64;
           description "Class-of-service shaping rate for priority high";
         }
         leaf shaping-rate-priority-high-burst {
           type uint32;
           description "Class-of-service shaping rate for priority high burst";
         }
         leaf shaping-rate-priority-medium {
           type uint64;
           description "Class-of-service shaping rate for priority medium";
         }
         leaf shaping-rate-priority-medium-burst {
           type uint32;
           description "Class-of-service shaping rate for priority medium burst";
         }
         leaf shaping-rate-priority-medium-low {
           type uint64;
           description "Class-of-service shaping rate for priority medium-low";
         }
         leaf shaping-rate-priority-medium-low-burst {
           type uint32;
           description "Class-of-service shaping rate burst for priority medium-low";
         }
         leaf shaping-rate-priority-low {
           type uint64;
           description "Class-of-service shaping rate for priority low";
         }
         leaf shaping-rate-priority-low-burst {
           type uint32;
           description "Class-of-service shaping rate for priority low burst";
         }
         leaf shaping-rate-excess-high {
           type uint64;
           description "Class-of-service shaping rate for excess high";
         }
         leaf shaping-rate-excess-high-burst {
           type uint32;
           description "Class-of-service shaping rate for excess high burst";
         }
         leaf shaping-rate-excess-medium-high {
           type uint64;
           description "Class-of-service shaping rate for excess medium-high";
         }
         leaf shaping-rate-excess-medium-high-burst {
           type uint32;
           description "Class-of-service shaping rate burst for excess medium-high";
         }
         leaf shaping-rate-excess-medium-low {
           type uint64;
           description "Class-of-service shaping rate for excess medium-low";
         }
         leaf shaping-rate-excess-medium-low-burst {
           type uint32;
           description "Class-of-service shaping rate burst for excess medium-low";
         }
         leaf shaping-rate-excess-low {
           type uint64;
           description "Class-of-service shaping rate for excess low";
         }
         leaf shaping-rate-excess-low-burst {
           type uint32;
           description "Class-of-service shaping rate for excess low burst";
         }
         leaf guaranteed-rate {
           type uint64;
           description "Class-of-service guaranteed rate";
         }
         leaf guaranteed-rate-burst {
           type uint32;
           description "Class-of-service guaranteed rate burst, in bytes";
         }
         leaf delay-buffer-rate {
           type uint64;
           description "Class-of-service delay buffer rate";
         }
         leaf excess-rate {
           type uint32;
           description "Class-of-service excess rate";
         }
         leaf excess-rate-high {
           type uint32;
           description "Class-of-service excess rate for excess-high priority traffic";
         }
         leaf excess-rate-medium-high {
           type uint32;
           description "Class-of-service excess rate for excess-medium-high priority traffic";
         }
         leaf excess-rate-medium-low {
           type uint32;
           description "Class-of-service excess rate for excess-medium-low priority traffic";
         }
         leaf excess-rate-low {
           type uint32;
           description "Class-of-service excess rate for excess-low priority traffic";
         }
         leaf adjust-minimum {
           type uint64;
           description "Class-of-service adjustment minimum rate";
         }
         leaf overhead-bytes {
           type int32;
           description "Class-of-service Overhead bytes";
         }
         leaf frame-mode-bytes {
           type int32;
           description "Class-of-service overhead bytes when in frame-mode";
         }
         leaf cell-mode-bytes {
           type int32;
           description "Class-of-service overhead bytes when in cell-mode";
         }
         leaf overhead-accounting-mode {
           type string;
           description "Class-of-service Overhead Accounting Mode";
         }
         list traffic-control-profile-instance {
           description "Class-of-service traffic control profile instance";
           leaf traffic-control-profile-instance-name {
             type string;
             description "Class-of-service traffic control profile instance";
           }
           leaf traffic-control-profile-instance-index {
             type uint32;
             description "Index number for Class-of-service traffic control profile instance";
           }
           leaf instance-reference-count {
             type uint32;
             description "Instance reference count";
           }
         }
       }
     }
     container cos-routing-instance-information {
       list routing-instance-map {
         description "Mapping between class-of-service objects and routing instances";
         leaf routing-instance-name {
           type string;
           description "Name of class-of-service routing instance";
         }
         list i-logical-map {
           leaf i-logical-name {
             type string;
             description "Class-of-service logical interface name";
           }
           leaf i-logical-index {
             type uint32;
             description "Class-of-service logical interface index";
           }
           leaf monitoring-profile-map-name {
             type string;
             description "Monitoring Profile Name";
           }
           list cos-objects {
             description "Class-of-service object  mappings";
             leaf cos-object-type {
               type string;
               description "Class-of-service object type";
             }
             leaf cos-object-name {
               type string;
               description "Class-of-service object name";
             }
             leaf cos-object-subtype {
               type string;
               description "Class-of-service object subtype";
             }
             leaf cos-object-index {
               type uint64;
               description "Class-of-service object index";
             }
           }
         }
       }
     }
     container cos-fabric-scheduler-map-information {
       container fabric-scheduler-map {
         list fabric-scheduler {
           leaf fabric-scheduler-name {
             type string;
             description "Class-of-service scheduler name";
           }
           leaf fabric-scheduler-index {
             type uint32;
             description "Class of service scheduler index";
           }
           leaf fabric-scheduler-drop-profile-ln-index {
             type uint32;
             description "Class-of-service scheduler drop profile index low, non-TCP";
           }
           leaf fabric-scheduler-drop-profile-ln {
             type string;
             description "Class-of-service scheduler drop profile low, non-TCP";
           }
           leaf fabric-scheduler-drop-profile-lt-index {
             type uint32;
             description "Class-of-service scheduler drop profile index low, TCP";
           }
           leaf fabric-scheduler-drop-profile-lt {
             type string;
             description "Class-of-service scheduler drop profile low, TCP";
           }
           leaf fabric-scheduler-drop-profile-hn-index {
             type uint32;
             description "Class-of-service scheduler drop profile index high, non-TCP";
           }
           leaf fabric-scheduler-drop-profile-hn {
             type string;
             description "Class-of-service scheduler drop profile high, non-TCP";
           }
           leaf fabric-scheduler-drop-profile-ht-index {
             type uint32;
             description "Class-of-service scheduler drop profile index high, TCP";
           }
           leaf fabric-scheduler-drop-profile-ht {
             type string;
             description "Class-of-service scheduler drop profile high, TCP";
           }
           leaf fabric-scheduler-priority {
             type string;
           }
         }
       }
     }
     container cos-tcm-information {
       list tcm {
         description "Class-of-service traffic-class-map";
         leaf tcm-name {
           type string;
           description "Class-of-service traffic-class-map name";
         }
         leaf tcm-type {
           type string;
           description "Class-of-service traffic-class-map type";
         }
         leaf table-index {
           type uint32;
           description "Table index";
         }
         container tcm-map {
           list tcm-map-item {
             leaf code-point {
               type string;
               description "Class-of-service code point alias name or bits";
             }
             leaf tc-name {
               type string;
               description "Class-of-service traffic-class-map traffic-class name";
             }
           }
         }
       }
     }
   }
   grouping appqos-counter-information-block {
     container logical-system-appqos-counter {
       leaf logical-system {
         type uint32;
         description "Logical system name";
       }
     }
     list pic {
       leaf name {
         type string;
         description "FPC name/PIC name";
       }
       list appqos-counter {
         leaf counter-name {
           type string;
           description "Counter name";
         }
         leaf counter-value {
           type uint32;
           description "Counter value";
         }
       }
       list appqos-rule-statistics {
         leaf ruleset-name {
           type string;
           description "Ruleset name";
         }
         leaf rule-name {
           type string;
           description "Rule name";
         }
         leaf rule-hits {
           type uint32;
           description "Rule hits";
         }
       }
       list appqos-rate-limiter-statistics {
         leaf application-ruleset-name {
           type string;
           description "Application ruleset name";
         }
         leaf application-name {
           type string;
           description "Application name";
         }
         leaf cts-rate-limiter {
           type string;
           description "Client-to-server rate limiter";
         }
         leaf cts-rate {
           type uint32;
           description "Client-to-server rate";
         }
         leaf stc-rate-limiter {
           type string;
           description "Server-to-client rate limiter";
         }
         leaf stc-rate {
           type uint32;
           description "Server-to-client rate";
         }
       }
     }
   }
   grouping appqos-rule-statistics-information-block {
     container logical-system-appqos-rule-stats {
       leaf logical-system {
         type uint32;
         description "Logical system name";
       }
     }
     list pic {
       leaf name {
         type string;
         description "FPC name/PIC name";
       }
       list appqos-counter {
         leaf counter-name {
           type string;
           description "Counter name";
         }
         leaf counter-value {
           type uint32;
           description "Counter value";
         }
       }
       list appqos-rule-statistics {
         leaf ruleset-name {
           type string;
           description "Ruleset name";
         }
         leaf rule-name {
           type string;
           description "Rule name";
         }
         leaf rule-hits {
           type uint32;
           description "Rule hits";
         }
       }
       list appqos-rate-limiter-statistics {
         leaf application-ruleset-name {
           type string;
           description "Application ruleset name";
         }
         leaf application-name {
           type string;
           description "Application name";
         }
         leaf cts-rate-limiter {
           type string;
           description "Client-to-server rate limiter";
         }
         leaf cts-rate {
           type uint32;
           description "Client-to-server rate";
         }
         leaf stc-rate-limiter {
           type string;
           description "Server-to-client rate limiter";
         }
         leaf stc-rate {
           type uint32;
           description "Server-to-client rate";
         }
       }
     }
   }
   grouping appqos-rate-limiter-statistics-information-block {
     container logical-system-appqos-rate-limiter-stats {
       leaf logical-system {
         type uint32;
         description "Logical system name";
       }
     }
     list pic {
       leaf name {
         type string;
         description "FPC name/PIC name";
       }
       list appqos-counter {
         leaf counter-name {
           type string;
           description "Counter name";
         }
         leaf counter-value {
           type uint32;
           description "Counter value";
         }
       }
       list appqos-rule-statistics {
         leaf ruleset-name {
           type string;
           description "Ruleset name";
         }
         leaf rule-name {
           type string;
           description "Rule name";
         }
         leaf rule-hits {
           type uint32;
           description "Rule hits";
         }
       }
       list appqos-rate-limiter-statistics {
         leaf application-ruleset-name {
           type string;
           description "Application ruleset name";
         }
         leaf application-name {
           type string;
           description "Application name";
         }
         leaf cts-rate-limiter {
           type string;
           description "Client-to-server rate limiter";
         }
         leaf cts-rate {
           type uint32;
           description "Client-to-server rate";
         }
         leaf stc-rate-limiter {
           type string;
           description "Server-to-client rate limiter";
         }
         leaf stc-rate {
           type uint32;
           description "Server-to-client rate";
         }
       }
     }
   }
   grouping appqos-swrl-stat-summary-information-block {
     container logical-system-appqos-swrl-stat-summary-information {
       leaf logical-system {
         type uint32;
         description "Logical system name";
       }
     }
     list appqos-swrl-stat-summary {
       leaf swrl-summary-name {
         type string;
         description "Swrl summary name";
       }
       leaf swrl-summary-value {
         type uint32;
         description "Swrl summary value";
       }
     }
     list appqos-swrl-stat-summary1 {
       leaf swrl-summary1-name {
         type string;
         description "Swrl summary name";
       }
       leaf swrl-summary1-value {
         type uint64;
         description "Swrl summary value";
       }
     }
   }
   grouping appqos-swrl-stat-all-information-block {
     list appqos-swrl-stat-all {
       leaf lsys-name {
         type string;
         description "LSYS/tenant name";
       }
       leaf swrl-id {
         type uint32;
         description "Perapp rl-id";
       }
       leaf swrl-rate {
         type uint32;
         description "Perapp rate-limit";
       }
       leaf swrl-perip-num {
         type uint32;
         description "Perip rl num";
       }
       leaf swrl-session {
         type uint32;
         description "Perapp active session";
       }
       leaf swrl-transmit {
         type uint64;
         description "Perapp pkt transmitted";
       }
       leaf swrl-drop {
         type uint64;
         description "Perapp pkt drop";
       }
       leaf swrl-lp {
         type uint64;
         description "Perapp loss priority";
       }
       leaf swrl-rate-transmit {
         type uint64;
         description "Perapp pkt transmit rate";
       }
       leaf swrl-rate-drop {
         type uint64;
         description "Perapp pkt drop rate";
       }
       leaf swrl-rate-lp {
         type uint64;
         description "Perapp loss priority rate";
       }
       leaf swrl-name {
         type string;
         description "Perapp rate-limiter";
       }
     }
   }
   grouping appqos-swrl-stat-id-information-block {
     container logical-system-appqos-swrl-stat-id-information {
       leaf logical-system {
         type uint32;
         description "Logical system name";
       }
     }
     list appqos-swrl-stat-id {
       leaf swrl-stat-name {
         type string;
         description "Swrl stat name";
       }
       leaf swrl-stat-value {
         type uint32;
         description "Swrl stat value";
       }
     }
     list appqos-swrl-stat-ext-id {
       leaf swrl-stat-ext-name {
         type string;
         description "Swrl stat ext name";
       }
       leaf swrl-stat-ext-value {
         type uint64;
         description "Swrl stat ext value";
       }
     }
     list appqos-swrl-stat-ext1-id {
       leaf swrl-stat-ext1-name {
         type string;
         description "Swrl stat ext1 name";
       }
       leaf swrl-stat-ext1-value {
         type string;
         description "Swrl stat ext1 value";
       }
     }
     list appqos-swrl-stat-perip-all {
       leaf swrl-perip-id {
         type uint32;
         description "Perapp rl-id";
       }
       leaf swrl-perip-rate {
         type uint32;
         description "Perapp rate-limit";
       }
       leaf swrl-perip-session {
         type uint32;
         description "Perapp active session";
       }
       leaf swrl-perip-transmit {
         type uint64;
         description "Perapp pkt transmitted";
       }
       leaf swrl-perip-drop {
         type uint64;
         description "Perapp pkt drop";
       }
       leaf swrl-perip-lp {
         type uint64;
         description "Perapp loss priority";
       }
       leaf swrl-perip-rate-transmit {
         type uint64;
         description "Perapp pkt transmit rate";
       }
       leaf swrl-perip-rate-drop {
         type uint64;
         description "Perapp pkt drop rate";
       }
       leaf swrl-perip-rate-lp {
         type uint64;
         description "Perapp loss priority rate";
       }
       leaf swrl-ipv6-address {
         type jt:ipv6addr;
         description "IPv6 address ";
       }
       leaf swrl-ip-address {
         type jt:ipaddr;
         description "IPv4 address";
       }
     }
   }
   grouping cos-forwarding-class-information-block {
     container fc-map {
       description "Class-of-service forwarding class to queue mapping";
       list fc-map-item {
         leaf fc-name {
           type string;
           description "Class-of-service forwarding class name";
         }
         leaf fc-number {
           type uint32;
           description "Identifier for Class-of-service forwarding class";
         }
         leaf fc-queue-number {
           type uint32;
           description "Class-of-service forwarding class queue number";
         }
         leaf fc-rqueue-number {
           type uint32;
           description "Class-of-service forwarding class restricted queue number";
         }
         leaf fc-priority {
           type string;
           description "Class-of-service forwarding class queue priority";
         }
         leaf fc-policing-priority {
           type string;
           description "Class-of-service forwarding class policing priority";
         }
         leaf fc-spu-priority {
           type string;
           description "Class-of-service forwarding class spu priority";
         }
         leaf fc-no-loss {
           type string;
           description "Class-of-service forwarding class no-loss";
         }
         leaf fc-pfc-priority {
           type uint32;
           description "Class-of-service forwarding class pfc-priority";
         }
         leaf fc-multicast {
           type string;
           description "Class-of-service forwarding class multicast";
         }
       }
     }
   }
   grouping cos-forwarding-class-set-information-block {
     list forwarding-class-set {
       description "Class-of-service forwarding class set information";
       list forwarding-class-set-entry {
         leaf forwarding-class-set-name {
           type string;
           description "Class-of-service forwarding class set name";
         }
         leaf forwarding-class-set-type {
           type string;
           description "Identifier for Class-of-service forwarding class set type";
         }
         leaf forwarding-class-set-index {
           type uint32;
           description "Identifier for Class-of-service forwarding class set";
         }
         container fc-map {
           list fc-map-item {
             leaf fc-name {
               type string;
               description "Class-of-service forwarding class name";
             }
             leaf fc-number {
               type uint32;
               description "Identifier for Class-of-service forwarding class";
             }
             leaf fc-queue-number {
               type uint32;
               description "Class-of-service forwarding class queue number";
             }
             leaf fc-rqueue-number {
               type uint32;
               description "Class-of-service forwarding class restricted queue number";
             }
             leaf fc-priority {
               type string;
               description "Class-of-service forwarding class queue priority";
             }
             leaf fc-policing-priority {
               type string;
               description "Class-of-service forwarding class policing priority";
             }
             leaf fc-spu-priority {
               type string;
               description "Class-of-service forwarding class spu priority";
             }
             leaf fc-no-loss {
               type string;
               description "Class-of-service forwarding class no-loss";
             }
             leaf fc-pfc-priority {
               type uint32;
               description "Class-of-service forwarding class pfc-priority";
             }
             leaf fc-multicast {
               type string;
               description "Class-of-service forwarding class multicast";
             }
           }
         }
       }
     }
   }
   grouping cos-drop-profile-information-block {
     list drop-profile {
       description "Class-of-service drop profile";
       leaf profile-name {
         type string;
         description "Class-of-service drop profile name";
       }
       leaf profile-type {
         type string;
         description "Class-of-service drop profile type";
       }
       leaf table-index {
         type uint32;
         description "Table index";
       }
       container profile-map {
         container profile-map-item {
           leaf fill-level {
             type uint32;
             description "Class-of-service drop profile fill level value";
           }
           leaf probability {
             type uint32;
             description "Class-of-service drop profile probability value";
           }
         }
       }
     }
   }
   grouping cos-monitoring-profile-information-block {
     list monitoring-profile {
       description "Class-of-service monitoring profile";
       leaf monitoring-profile-name {
         type string;
         description "Class-of-service monitoring profile name";
       }
       container export-filters {
         container export-filter {
           leaf filter-name {
             type string;
             description "Class-of-service monitoring profile filter name";
           }
           leaf monitoring-queue-number {
             type uint32;
             description "Class-of-service monitoring profile filter queue value";
           }
           leaf peak-queue-length-value {
             type uint32;
             description "Class-of-service monitoring profile peak queue length value";
           }
         }
       }
     }
   }
   grouping cos-adaptive-shaper-information-block {
     list adaptive-shaper {
       description "Class-of-service adaptive shaper";
       leaf adaptive-shaper-name {
         type string;
         description "Class-of-service adaptive shaper name";
       }
       leaf table-index {
         type uint32;
         description "Table index";
       }
       container trigger-item {
         leaf trigger-type {
           type string;
           description "Class-of-service adaptive shaper trigger type";
         }
         leaf adaptive-shaping-rate {
           type string;
           description "Class-of-service adaptive shaping rate";
         }
       }
     }
   }
   grouping cos-virtual-channel-information-block {
     list virtual-channel {
       description "Class-of-service virtual channel";
       leaf virtual-channel-name {
         type string;
         description "Class-of-service virtual channel name";
       }
       leaf table-index {
         type uint32;
         description "Table index";
       }
     }
   }
   grouping cos-virtual-channel-group-information-block {
     list virtual-channel-group {
       description "Class-of-service virtual channel group";
       leaf virtual-channel-group-name {
         type string;
         description "Class-of-service virtual channel group name";
       }
       leaf table-index {
         type uint32;
         description "Table index";
       }
       container channel {
         leaf virtual-channel-name {
           type string;
           description "Class-of-service virtual channel name";
         }
         leaf scheduler-map-name {
           type string;
           description "Class-of-service scheduler map name";
         }
         leaf channel-shaping-rate {
           type string;
           description "Class-of-service channel shaping rate";
         }
         leaf adjustment-shape-value {
           type uint64;
           description "Class-of-service adjusted shaping rate value";
         }
       }
     }
   }
   grouping cos-classifier-information-block {
     list classifier {
       description "Class-of-service code point classifier";
       leaf classifier-name {
         type string;
         description "Class-of-service classifier name";
       }
       leaf code-point-type {
         type string;
         description "Class-of-service code point type";
       }
       leaf table-index {
         type uint32;
         description "Table index";
       }
       container classifier-map {
         list classifier-map-item {
           leaf code-point {
             type string;
             description "Class-of-service code point alias name or bits";
           }
           leaf fc-name {
             type string;
             description "Class-of-service forwarding class name";
           }
           leaf loss-priority {
             type string;
             description "Class-of-service loss priority";
           }
           leaf cntag-present {
             type string;
             description "Class-of-service cntag present";
           }
         }
       }
     }
   }
   grouping cos-tcm-information-block {
     list tcm {
       description "Class-of-service traffic-class-map";
       leaf tcm-name {
         type string;
         description "Class-of-service traffic-class-map name";
       }
       leaf tcm-type {
         type string;
         description "Class-of-service traffic-class-map type";
       }
       leaf table-index {
         type uint32;
         description "Table index";
       }
       container tcm-map {
         list tcm-map-item {
           leaf code-point {
             type string;
             description "Class-of-service code point alias name or bits";
           }
           leaf tc-name {
             type string;
             description "Class-of-service traffic-class-map traffic-class name";
           }
         }
       }
     }
   }
   grouping cos-policy-map-information-block {
     list policy-map {
       description "Class-of-service Policy-map";
       leaf policy-map-name {
         type string;
         description "Class-of-service Policy-map name";
       }
       leaf table-index {
         type uint32;
         description "Table index";
       }
       leaf policy-map-user-attribute {
         type uint32;
         description "User-defined attribute";
       }
       container policy-map-cp-entries {
         leaf code-point-type {
           type string;
           description "Class-of-service code point type";
         }
         leaf code-point {
           type string;
           description "Class-of-service code point alias name or bits";
         }
         leaf code-point-option {
           type string;
           description "Class-of-service code point option flag";
         }
       }
     }
   }
   grouping cos-l2tp-session-information-block {
     list l2tp-session-map {
       description "Class-of-service L2TP session mappings";
       leaf l2tp-session-username {
         type string;
         description "Class-of-service session username";
       }
       leaf l2tp-session-index {
         type uint32;
         description "Class-of-service session index";
       }
       leaf interface-name {
         type string;
         description "Class-of-service interface name";
       }
       leaf interface-index {
         type uint32;
         description "Class-of-service interface index";
       }
       leaf interface-queues-supported {
         type uint32;
         description "Number of queues supported on this interface";
       }
       leaf interface-queues-in-use {
         type uint32;
         description "Number of queues in use on this interface";
       }
       leaf traffic-control-profile-name {
         type string;
         description "Class-of-service traffic control profile name";
       }
       leaf traffic-control-profile-index {
         type uint64;
         description "Index number for Class-of-service traffic control profile";
       }
       leaf scheduler-map-name {
         type string;
         description "Class-of-service scheduler map name";
       }
       leaf scheduler-map-index {
         type uint64;
         description "Class-of-service scheduler map index";
       }
       leaf shaping-rate {
         type uint64;
         description "Class-of-service shaping rate";
       }
       leaf guaranteed-rate {
         type uint64;
         description "Class-of-service guaranteed rate";
       }
       leaf delay-buffer-rate {
         type uint64;
         description "Class-of-service delay buffer rate";
       }
       leaf encapsulation-overhead {
         type int32;
         description "Class-of-service Encapsulation Overhead";
       }
       leaf cell-overhead {
         type string;
         description "Class-of-service Cell Overhead";
       }
     }
   }
   grouping cos-loss-priority-map-information-block {
     list loss-priority-map {
       description "Class-of-service code point loss priority map";
       leaf loss-priority-map-name {
         type string;
         description "Name of class-of-service loss priority map";
       }
       leaf code-point-type {
         type string;
         description "Class-of-service code point type";
       }
       leaf table-index {
         type uint32;
         description "Table index";
       }
       list loss-priority-map-table {
         list loss-priority-map-item {
           leaf code-point {
             type string;
             description "Class-of-service code point alias name or bits";
           }
           leaf loss-priority {
             type string;
             description "Class-of-service loss priority";
           }
         }
         list loss-priority-map-table-entry {
           leaf table-index {
             type uint32;
             description "Table index";
           }
           leaf code-point {
             type string;
             description "Class-of-service code point alias name or bits";
           }
           leaf loss-priority {
             type string;
             description "Class-of-service loss priority";
           }
         }
       }
     }
   }
   grouping cos-loss-priority-rewrite-information-block {
     list loss-priority-rewrite {
       description "Class-of-service loss priority to code point rewrite";
       leaf loss-priority-rewrite-name {
         type string;
         description "Name of class-of-service loss priority rewrite";
       }
       leaf code-point-type {
         type string;
         description "Class-of-service code point type";
       }
       leaf table-index {
         type uint32;
         description "Table index";
       }
       list loss-priority-rewrite-table {
         list loss-priority-rewrite-item {
           leaf loss-priority {
             type string;
             description "Class-of-service loss priority";
           }
           leaf code-point {
             type string;
             description "Class-of-service code point alias name or bits";
           }
         }
         list loss-priority-rewrite-table-entry {
           leaf table-index {
             type uint32;
             description "Table index";
           }
           leaf loss-priority {
             type string;
             description "Class-of-service loss priority";
           }
           leaf code-point {
             type string;
             description "Class-of-service code point alias name or bits";
           }
         }
       }
     }
   }
   grouping cos-rewrite-information-block {
     list rewrite {
       description "Class-of-service drop profile";
       leaf rewrite-name {
         type string;
         description "Class-of-service rewrite rule name";
       }
       leaf code-point-type {
         type string;
         description "Class-of-service code point type";
       }
       leaf table-index {
         type uint32;
         description "Table index";
       }
       container rewrite-map {
         list rewrite-map-item {
           leaf fc-name {
             type string;
             description "Class-of-service forwarding class name";
           }
           leaf loss-priority {
             type string;
             description "Class-of-service loss priority";
           }
           leaf code-point {
             type string;
             description "Class-of-service code point alias name or bits";
           }
         }
       }
     }
   }
   grouping cos-multi-destination-information-block {
     container sm-md-map {
       leaf scheduler-map-name {
         type string;
         description "Class-of-service scheduler map name";
       }
       leaf scheduler-map-index {
         type uint64;
         description "Class-of-service scheduler map index";
       }
     }
     container fc-md-map {
       leaf fc-name {
         type string;
         description "Class-of-service forwarding class name";
       }
       leaf fc-queue-number {
         type uint32;
         description "Class-of-service forwarding class queue number";
       }
     }
     container cls-md-map {
       leaf multidest-classifier-name {
         type string;
         description "Multi destination classifier name";
       }
       leaf multidest-classifier-type {
         type string;
         description "Multi destination classifier type";
       }
       leaf multidest-classifier-index {
         type uint32;
         description "Multi destination classifier id";
       }
     }
   }
   grouping cos-multi-destination-classifier-binding-information-block {
     list classifier-md-bind {
       leaf logical-interface-name {
         type string;
         description "Logical interface name";
       }
       leaf multidest-classifier-index {
         type uint32;
         description "Multi destination classifier id";
       }
       leaf multidest-classifier-type {
         type string;
         description "Multi destination classifier type";
       }
     }
   }
   grouping cos-system-defaults-information-block {
     list cos-objects {
       description "Class-of-service object  mappings";
       leaf cos-object-type {
         type string;
         description "Class-of-service object type";
       }
       leaf cos-object-name {
         type string;
         description "Class-of-service object name";
       }
       leaf cos-object-subtype {
         type string;
         description "Class-of-service object subtype";
       }
       leaf cos-object-index {
         type uint64;
         description "Class-of-service object index";
       }
     }
   }
   grouping cos-code-point-map-information-block {
     list code-point-map {
       description "Class-of-service code point alias map";
       leaf code-point-type {
         type string;
         description "Class-of-service code point type";
       }
       container alias-map {
         list alias-map-item {
           leaf code-point-alias {
             type string;
             description "Class-of-service code point alias name";
           }
           leaf code-point-bits {
             type string;
             description "Class-of-service code point bit sequence";
           }
         }
       }
     }
   }
   grouping cos-scheduler-map-information-block {
     list scheduler-map {
       description "Class-of-service scheduler map";
       leaf scheduler-map-name {
         type string;
         description "Class-of-service scheduler map name";
       }
       leaf scheduler-map-index {
         type uint64;
         description "Class-of-service scheduler map index";
       }
       leaf user-plane-name {
         type string;
         description "Class-of-service user-plane name for XDA";
       }
       list scheduler {
         leaf scheduler-name {
           type string;
           description "Class-of-service scheduler name";
         }
         leaf fc-name {
           type string;
           description "Class-of-service forwarding class name";
         }
         leaf scheduler-index {
           type uint64;
           description "Class of service scheduler index";
         }
         leaf scheduler-tx-rate {
           type string;
           description "Class-of-service scheduler transmit rate";
         }
         leaf scheduler-tx-limit {
           type string;
           description "Class-of-service scheduler transmit limit";
         }
         leaf scheduler-buffer-size {
           type string;
           description "Class-of-service scheduler buffer size";
         }
         leaf scheduler-buffer-multicast-share {
           type uint32;
           description "Class-of-service scheduler multicast buffer share";
         }
         leaf scheduler-buffer-limit {
           type string;
           description "Class-of-service scheduler buffer limit";
         }
         leaf scheduler-buffer-rate {
           type string;
           description "Class-of-service scheduler buffer rate";
         }
         leaf scheduler-shared-buffer-maximum-percentage {
           type uint32;
           description "Shared Buffer maximum percentage";
         }
         leaf scheduler-shared-buffer-multicast-maximum-percentage {
           type uint32;
           description "Shared Buffer multicast maximum percentage";
         }
         leaf scheduler-buffer-dynamic-threshold {
           type uint32;
           description "Queue shared-buffer dynamic threshold";
         }
         leaf scheduler-priority {
           type string;
           description "Class-of-service scheduler priority";
         }
         leaf scheduler-shaping-rate {
           type string;
           description "Class-of-service scheduler shaping rate";
         }
         leaf scheduler-shaping-rate-burst {
           type string;
           description "Class-of-service scheduler shaping rate burst";
         }
         leaf scheduler-adjust-minimum {
           type int32;
           description "Class-of-service scheduler adjustment minimum rate";
         }
         leaf scheduler-adjust-percent {
           type int32;
           description "Class-of-service scheduler percent adjustment for a queue";
         }
         leaf scheduler-excess-priority {
           type string;
           description "Class-of-service scheduler excess priority";
         }
         leaf scheduler-excess-rate {
           type string;
           description "Class-of-service scheduler excess rate";
         }
         leaf scheduler-explicit-congestion-notification {
           type string;
           description "Class-of-service ECN status of queue";
         }
         leaf scheduler-ecn-rtlog-rate-limit {
           type uint32;
           description "Class-of-service ECN Security Log Rate Limit";
         }
         leaf scheduler-ecn-no-pfc-assist {
           type string;
           description "Class-of-service ECN no pfc assist";
         }
         leaf scheduler-queue-monitoring {
           type string;
           description "Class-of-service queue depth monitoring of queue";
         }
         leaf scheduler-drop-profile-ln-index {
           type uint32;
           description "Class-of-service scheduler drop profile index low, non-TCP";
         }
         leaf scheduler-drop-profile-ln {
           type string;
           description "Class-of-service scheduler drop profile low, non-TCP";
         }
         leaf scheduler-drop-profile-lt-index {
           type uint32;
           description "Class-of-service scheduler drop profile index low, TCP";
         }
         leaf scheduler-drop-profile-lt {
           type string;
           description "Class-of-service scheduler drop profile low, TCP";
         }
         leaf scheduler-drop-profile-hn-index {
           type uint32;
           description "Class-of-service scheduler drop profile index high, non-TCP";
         }
         leaf scheduler-drop-profile-hn {
           type string;
           description "Class-of-service scheduler drop profile high, non-TCP";
         }
         leaf scheduler-drop-profile-ht-index {
           type uint32;
           description "Class-of-service scheduler drop profile index high, TCP";
         }
         leaf scheduler-drop-profile-ht {
           type string;
           description "Class-of-service scheduler drop profile high, TCP";
         }
         leaf scheduler-drop-profile-la-index {
           type uint32;
           description "Class-of-service scheduler drop profile index low";
         }
         leaf scheduler-drop-profile-la {
           type string;
           description "Class-of-service scheduler drop profile low";
         }
         leaf scheduler-drop-profile-ma-index {
           type uint32;
           description "Class-of-service scheduler drop profile index medium";
         }
         leaf scheduler-drop-profile-ma {
           type string;
           description "Class-of-service scheduler drop profile medium";
         }
         leaf scheduler-drop-profile-mla-index {
           type uint32;
           description "Class-of-service scheduler drop profile index medium-low";
         }
         leaf scheduler-drop-profile-mla {
           type string;
           description "Class-of-service scheduler drop profile medium-low";
         }
         leaf scheduler-drop-profile-mha-index {
           type uint32;
           description "Class-of-service scheduler drop profile index medium-high";
         }
         leaf scheduler-drop-profile-mha {
           type string;
           description "Class-of-service scheduler drop profile medium-high";
         }
         leaf scheduler-drop-profile-ha-index {
           type uint32;
           description "Class-of-service scheduler drop profile index high";
         }
         leaf scheduler-drop-profile-ha {
           type string;
           description "Class-of-service scheduler drop profile high";
         }
       }
     }
   }
   grouping cos-traffic-control-profile-information-block {
     list traffic-control-profile {
       description "Information about one or more traffic control profiles";
       leaf traffic-control-profile-name {
         type string;
         description "Class-of-service traffic control profile name";
       }
       leaf traffic-control-profile-index {
         type uint64;
         description "Index number for Class-of-service traffic control profile";
       }
       leaf user-plane-name {
         type string;
         description "Class-of-service user-plane name for XDA";
       }
       leaf scheduler-map-name {
         type string;
         description "Class-of-service scheduler map name";
       }
       leaf atm-service {
         type string;
         description "Class-of-service traffic control profile atm service";
       }
       leaf shaping-rate {
         type uint64;
         description "Class-of-service shaping rate";
       }
       leaf shaping-rate-burst {
         type uint32;
         description "Class-of-service shaping rate burst, in bytes";
       }
       leaf low-granularity {
         type uint32;
         description "Class-of-service low-granularity mode support";
       }
       leaf queue-mode-4q {
         type uint32;
         description "Class-of-service tcp-voq-mode(4Q) mode support";
       }
       leaf shaping-rate-priority-strict-high {
         type uint64;
         description "Class-of-service shaping rate for priority strict high";
       }
       leaf shaping-rate-priority-strict-high-burst {
         type uint32;
         description "Class-of-service shaping rate burst for priority strict-high";
       }
       leaf shaping-rate-priority-high {
         type uint64;
         description "Class-of-service shaping rate for priority high";
       }
       leaf shaping-rate-priority-high-burst {
         type uint32;
         description "Class-of-service shaping rate for priority high burst";
       }
       leaf shaping-rate-priority-medium {
         type uint64;
         description "Class-of-service shaping rate for priority medium";
       }
       leaf shaping-rate-priority-medium-burst {
         type uint32;
         description "Class-of-service shaping rate for priority medium burst";
       }
       leaf shaping-rate-priority-medium-low {
         type uint64;
         description "Class-of-service shaping rate for priority medium-low";
       }
       leaf shaping-rate-priority-medium-low-burst {
         type uint32;
         description "Class-of-service shaping rate burst for priority medium-low";
       }
       leaf shaping-rate-priority-low {
         type uint64;
         description "Class-of-service shaping rate for priority low";
       }
       leaf shaping-rate-priority-low-burst {
         type uint32;
         description "Class-of-service shaping rate for priority low burst";
       }
       leaf shaping-rate-excess-high {
         type uint64;
         description "Class-of-service shaping rate for excess high";
       }
       leaf shaping-rate-excess-high-burst {
         type uint32;
         description "Class-of-service shaping rate for excess high burst";
       }
       leaf shaping-rate-excess-medium-high {
         type uint64;
         description "Class-of-service shaping rate for excess medium-high";
       }
       leaf shaping-rate-excess-medium-high-burst {
         type uint32;
         description "Class-of-service shaping rate burst for excess medium-high";
       }
       leaf shaping-rate-excess-medium-low {
         type uint64;
         description "Class-of-service shaping rate for excess medium-low";
       }
       leaf shaping-rate-excess-medium-low-burst {
         type uint32;
         description "Class-of-service shaping rate burst for excess medium-low";
       }
       leaf shaping-rate-excess-low {
         type uint64;
         description "Class-of-service shaping rate for excess low";
       }
       leaf shaping-rate-excess-low-burst {
         type uint32;
         description "Class-of-service shaping rate for excess low burst";
       }
       leaf guaranteed-rate {
         type uint64;
         description "Class-of-service guaranteed rate";
       }
       leaf guaranteed-rate-burst {
         type uint32;
         description "Class-of-service guaranteed rate burst, in bytes";
       }
       leaf delay-buffer-rate {
         type uint64;
         description "Class-of-service delay buffer rate";
       }
       leaf excess-rate {
         type uint32;
         description "Class-of-service excess rate";
       }
       leaf excess-rate-high {
         type uint32;
         description "Class-of-service excess rate for excess-high priority traffic";
       }
       leaf excess-rate-medium-high {
         type uint32;
         description "Class-of-service excess rate for excess-medium-high priority traffic";
       }
       leaf excess-rate-medium-low {
         type uint32;
         description "Class-of-service excess rate for excess-medium-low priority traffic";
       }
       leaf excess-rate-low {
         type uint32;
         description "Class-of-service excess rate for excess-low priority traffic";
       }
       leaf adjust-minimum {
         type uint64;
         description "Class-of-service adjustment minimum rate";
       }
       leaf overhead-bytes {
         type int32;
         description "Class-of-service Overhead bytes";
       }
       leaf frame-mode-bytes {
         type int32;
         description "Class-of-service overhead bytes when in frame-mode";
       }
       leaf cell-mode-bytes {
         type int32;
         description "Class-of-service overhead bytes when in cell-mode";
       }
       leaf overhead-accounting-mode {
         type string;
         description "Class-of-service Overhead Accounting Mode";
       }
       list traffic-control-profile-instance {
         description "Class-of-service traffic control profile instance";
         leaf traffic-control-profile-instance-name {
           type string;
           description "Class-of-service traffic control profile instance";
         }
         leaf traffic-control-profile-instance-index {
           type uint32;
           description "Index number for Class-of-service traffic control profile instance";
         }
         leaf instance-reference-count {
           type uint32;
           description "Instance reference count";
         }
       }
     }
   }
   grouping cos-fragmentation-map-information-block {
     list fragmentation-map {
       description "Class-of-service fragmentation map";
       leaf fragmentation-map-name {
         type string;
         description "Class-of-service fragmentation map name";
       }
       leaf fragmentation-map-index {
         type uint32;
         description "Index number for Class-of-service fragmentation map";
       }
       list fragment-map {
         leaf fc-name {
           type string;
           description "Class-of-service forwarding class name";
         }
         leaf no-fragmentation {
           type empty;
           description "Do not fragment packets of this class";
         }
         leaf fragment-threshold {
           type string;
           description "Fragmentation threshold";
         }
         leaf fragment-multilink-class {
           type int32;
           description "Identifier for multilink class";
         }
       }
     }
   }
   grouping cos-slice-information-block {
     list slice-map {
       leaf slice-name {
         type string;
         description "Class-of-service slice name";
       }
       leaf slice-index {
         type uint32;
         description "Class-of-service slice index";
       }
       leaf output-traffic-control-profile-name {
         type string;
         description "Class-of-service output traffic control profile name";
       }
       leaf output-traffic-control-profile-index {
         type uint64;
         description "Index number for Class-of-service output traffic control profile";
       }
       leaf slice-sf {
         type uint32;
         description "Scale factor";
       }
       leaf scheduler-map-name {
         type string;
         description "Class-of-service scheduler map name";
       }
       leaf scheduler-map-index {
         type uint64;
         description "Class-of-service scheduler map index";
       }
       leaf shaping-rate {
         type uint64;
         description "Class-of-service shaping rate";
       }
       leaf shaping-rate-burst {
         type uint32;
         description "Class-of-service shaping rate burst, in bytes";
       }
       leaf guaranteed-rate {
         type uint64;
         description "Class-of-service guaranteed rate";
       }
       leaf guaranteed-rate-burst {
         type uint32;
         description "Class-of-service guaranteed rate burst, in bytes";
       }
       leaf delay-buffer-rate {
         type uint64;
         description "Class-of-service delay buffer rate";
       }
       leaf queue-mode-4q {
         type uint32;
         description "Class-of-service tcp-voq-mode(4Q) mode support";
       }
       leaf low-granularity {
         type uint32;
         description "Class-of-service low-granularity mode support";
       }
     }
   }
   grouping cos-interface-information-block {
     list interface-information {
       list physical-interface {
         leaf cascade-port-satellite-device-slot-identifier {
           type int32;
           description "Slot id of a Satellite Device on a Cascade Port";
         }
         leaf lcp-state {
           type string;
           description "State of the Line Control Protocol";
         }
         leaf chap-state {
           type string;
           description "State of the Challenge Handshake Authentication Protocol";
         }
         leaf pap-state {
           type string;
           description "State of the Password Authentication Protocol";
         }
         leaf name {
           type string;
           description "Name of this item";
         }
         leaf mc-ae-status {
           type string;
         }
         leaf admin-status {
           type string;
           description "Desired state of the interface";
         }
         leaf oper-status {
           type string;
           description "Current operational state of the interface";
         }
         leaf extended-port-multi-homed {
           type string;
           description "EP Mutli-homed information";
         }
         leaf local-index {
           type int32;
           description "Local kernel index for this interface";
         }
         leaf snmp-index {
           type int32;
           description "SNMP ifIndex for this interface";
         }
         leaf generation {
           type int32;
           description "Generation number used to distinguish between successive instances of this interface";
         }
         leaf description {
           type string;
           description "Description of this interface";
         }
         leaf if-type {
           type string;
         }
         leaf link-level-type {
           type string;
           description "Encapsulation being used on the physical interface";
         }
         leaf link-media-type {
           type string;
           description "PHY Medium type on the physical interface";
         }
         leaf mtu {
           type string;
           description "MTU size on this interface";
         }
         leaf mru {
           type string;
           description "MRU size on this interface";
         }
         leaf clocking {
           type string;
           description "Reference clock source";
         }
         leaf max-speed {
           type string;
           description "Maximum speed at which interface can run";
         }
         leaf sonet-mode {
           type string;
           description "Whether the interface is in SDH or SONET mode";
         }
         leaf physical-mode {
           type string;
           description "Physical mode";
         }
         leaf l2circuit-mode {
           type string;
           description "Indicates if the interface is in L2 circuit AAL5 or Cell mode";
         }
         leaf ifd-cell-bundle-size {
           type string;
           description "Cell bundle size for physical interface";
         }
         leaf ifd-cell-bundle-timeout {
           type string;
           description "Cell bundle timeout for physical interface";
         }
         leaf link-mode {
           type string;
           description "Link mode of the interface";
         }
         leaf mac-mode {
           type string;
           description "MAC Mode of the interface";
         }
         leaf speed {
           type string;
           description "Speed at which the interface is running";
         }
         leaf duplex {
           type string;
           description "Duplex at which the interface is running";
         }
         leaf if-unidirectional {
           type string;
         }
         leaf bpdu-error {
           type string;
         }
         leaf ld-pdu-error {
           type string;
         }
         leaf eth-switch-error {
           type string;
         }
         leaf l2pt-error {
           type string;
         }
         leaf loopback {
           type string;
           description "Whether loopback is enabled and the type of loopback";
         }
         leaf optics-loopback {
           type string;
           description "Whether optical loopback is enabled";
         }
         leaf sonet-loopback {
           type string;
           description "SONET loopback setting on channelized OC12 interface";
         }
         leaf crc {
           type string;
           description "Frame checksum on the interface (either 16 or 32)";
         }
         leaf payload-scrambler {
           type string;
           description "Whether payload scrambling is enabled";
         }
         leaf source-filtering {
           type string;
           description "Whether source filtering is enabled or disabled";
         }
         leaf if-flow-control {
           type string;
         }
         leaf if-speed-cfg {
           type string;
         }
         leaf if-configured-flow-control-rx-buffers {
           type string;
         }
         leaf if-configured-flow-control-tx-buffers {
           type string;
         }
         leaf if-auto-negotiation {
           type string;
           description "Status of auto-negotiation";
         }
         leaf if-remote-fault {
           type string;
           description "Status of remote fault";
         }
         leaf if-media-type {
           type string;
           description "Media-type copper or fiber";
         }
         leaf if-speed-auto-negotiation {
           type string;
           description "Status of Speed auto-negotiation";
         }
         leaf ieee-802-3az-eee {
           type string;
           description "IEEE 802.3az Energy Efficient Ethernet";
         }
         leaf if-auto-mdix {
           type string;
           description "Status of Auto MDIX";
         }
         leaf ingress-rate-limit {
           type int32;
           description "Layer 2 rate limit on ingress traffic for the port";
         }
         leaf minimum-links-in-aggregate {
           type int32;
           description "Minimum number of links needed for the bundle to be up";
         }
         leaf minimum-bandwidth-in-aggregate {
           type int32;
           description "Minimum bandwidth needed for the bundle to be up";
         }
         leaf ds3-mode {
           type string;
         }
         leaf ds3-long-buildout {
           type string;
         }
         leaf e3-framing {
           type string;
         }
         leaf ds1-framing {
           type string;
         }
         leaf atm-line-build-out {
           type int32;
           description "Line buildout";
         }
         leaf atm-encapsulation {
           type string;
           description "Type of ATM encapsulation";
         }
         leaf atm-e3-framing {
           type string;
           description "Type of framing";
         }
         leaf ih-parent {
           type string;
           description "Controller parent";
         }
         leaf physical-information {
           type string;
         }
         leaf link-type {
           type string;
         }
         leaf up-hold-time {
           type int32;
           description "Up hold-time for this interface (milliseconds)";
         }
         leaf down-hold-time {
           type int32;
           description "Down hold-time for this interface (milliseconds)";
         }
         leaf damp-half-life {
           type int32;
           description "Dampening half-life time for this interface (seconds)";
         }
         leaf damp-max-suppress {
           type int32;
           description "Dampening max suppress time for this interface (seconds)";
         }
         leaf damp-reuse-level {
           type int32;
           description "Reuse threshold";
         }
         leaf damp-suppress-level {
           type int32;
           description "Suppress threshold";
         }
         leaf damp-suppress-state {
           type string;
           description "Suppress state";
         }
         leaf current-physical-address {
           type string;
           description "Configured physical address for this interface";
         }
         leaf hardware-physical-address {
           type string;
           description "Hardware physical address for this interface";
         }
         leaf esi-value {
           type string;
           description "Ethernet segment identifier for this interface";
         }
         leaf esi-mode {
           type string;
           description "Ethernet segment mode for this interface";
         }
         leaf alternate-physical-address {
           type string;
           description "Alternate physical address for this interface";
         }
         leaf input-error-count {
           type int32;
           description "Sum of all input errors on this interface";
         }
         leaf output-error-count {
           type int32;
           description "Sum of all output errors on this interface";
         }
         leaf interface-flapped {
           type string;
           description "Time when the interface last flapped";
         }
         leaf statistics-cleared {
           type string;
           description "Time when statistics were last cleared";
         }
         leaf fec-mode {
           type string;
           description "Optics FEC mode";
         }
         leaf laser-enable {
           type string;
           description "Optics laser status";
         }
         leaf high-polarization {
           type string;
           description "Optics high polarization";
         }
         leaf interface-transmit-statistics {
           type string;
           description "Interface statistics based on transmitted packets";
         }
         leaf pad-to-minimum-frame-size {
           type string;
           description "Pad Tx vlan tagged frame to minimum of 68 bytes";
         }
         leaf preserve-interface {
           type string;
           description "Whether interface preservation is enabled or disabled";
         }
         leaf sonet-rx-overhead {
           type string;
         }
         leaf sonet-tx-overhead {
           type string;
         }
         leaf sonet-rx-path-trace {
           type string;
           description "Received SONET path trace";
         }
         leaf sonet-tx-path-trace {
           type string;
           description "Transmitted SONET path trace";
         }
         leaf otn-rx-overhead {
           type string;
         }
         leaf otn-tx-overhead {
           type string;
         }
         leaf otn-stats-counter {
           type string;
         }
         leaf otn-rx-tti {
           type string;
         }
         leaf otn-tx-tti {
           type string;
         }
         leaf port-forwarding-mode {
           type string;
           description "Port forwarding mode";
         }
         leaf cos-header {
           type empty;
         }
         leaf precl-header {
           type empty;
         }
         leaf esi-source-bmac {
           type jt:mac-addr;
           description "Ethernet segment source B-MAC for this interface";
         }
         leaf sonet-payload-pointer-curptr {
           type string;
           description "Value of the SONET/SDH payload pointer, derived from the H1 and H2 overhead bytes";
         }
         leaf sonet-payload-pointer-ptrinc-count {
           type string;
           description "Number of times the value of the SONET/SDH payload pointer had positive justification";
         }
         leaf sonet-payload-pointer-ptrdec-count {
           type string;
           description "Number of times the value of the SONET/SDH payload pointer had negative justification";
         }
         leaf sonet-payload-pointer-newptr-ndf-count {
           type string;
           description "Number of times a new payload pointer was created with the New Data Found flag set";
         }
         leaf link-partner-status {
           type string;
           description "Auto-negotiation status of link partner";
         }
         container if-device-flags {
           leaf ifdf-none {
             type empty;
           }
           leaf ifdf-present {
             type empty;
           }
           leaf ifdf-running {
             type empty;
           }
           leaf ifdf-duplex {
             type empty;
           }
           leaf ifdf-down {
             type empty;
           }
           leaf ifdf-no-carrier {
             type empty;
           }
           leaf ifdf-error1 {
             type empty;
           }
           leaf ifdf-error2 {
             type empty;
           }
           leaf ifdf-no-multicast {
             type empty;
           }
           leaf ifdf-loopback {
             type empty;
           }
           leaf ifdf-quench {
             type empty;
           }
           leaf ifdf-recv-all-multicasts {
             type empty;
           }
           leaf ifdf-promiscuous {
             type empty;
           }
           leaf ifdf-link-layer-down {
             type empty;
           }
           leaf ifdf-loop-detected {
             type empty;
           }
           leaf ifdf-pfe-gone {
             type empty;
           }
           leaf generic-value {
             type int32;
             description "Hexadecimal value of unknown flag bits";
           }
         }
         container if-config-flags {
           leaf iff-none {
             type empty;
           }
           leaf iff-hardware-down {
             type empty;
           }
           leaf iff-down {
             type empty;
           }
           leaf iff-up {
             type empty;
           }
           leaf iff-admin-down {
             type empty;
           }
           leaf iff-admin-up {
             type empty;
           }
           leaf iff-link-down {
             type empty;
           }
           leaf iff-device-down {
             type empty;
           }
           leaf iff-point-to-point {
             type empty;
           }
           leaf iff-point-to-multipoint {
             type empty;
           }
           leaf plp-to-clp {
             type empty;
           }
           leaf iff-multiaccess {
             type empty;
           }
           leaf iff-change {
             type empty;
           }
           leaf iff-inverse-arp {
             type empty;
           }
           leaf iff-no-multicast {
             type empty;
           }
           leaf iff-multicast {
             type empty;
           }
           leaf iff-promiscuous {
             type empty;
           }
           leaf iff-all-multicast {
             type empty;
           }
           leaf iff-snmp-traps {
             type empty;
           }
           leaf iff-rx-passive {
             type empty;
           }
           leaf iff-tx-passive {
             type empty;
           }
           leaf iff-ccc-down {
             type empty;
           }
           leaf iff-clear-df {
             type empty;
           }
           leaf iff-tunnel-reassembly {
             type empty;
           }
           leaf iff-acfc {
             type empty;
           }
           leaf iff-pfc {
             type empty;
           }
           leaf iff-rdd {
             type empty;
           }
           leaf iff-looped {
             type empty;
           }
           leaf iff-framing-conflict {
             type empty;
           }
           leaf internal-flags {
             type int32;
             description "Hexadecimal value of internal flag bits";
           }
         }
         container ifd-specific-config-flags {
           leaf ifdspf-none {
             type empty;
           }
           leaf ifdspf-multicast-statistics {
             type empty;
           }
           leaf ifdspf-oam-on-svlan {
             type empty;
           }
           leaf internal-flags {
             type int32;
             description "Hexadecimal value of internal flag bits";
           }
         }
         container shared-interface-physical-interface {
           leaf ownership {
             type string;
             description "Shared interface physical interface ownership";
           }
         }
         container if-media-flags {
           leaf ifmf-none {
             type empty;
           }
           leaf ifmf-autoselect {
             type empty;
           }
           leaf ifmf-scheduler {
             type empty;
           }
           leaf ifmf-shared-scheduler {
             type empty;
           }
           leaf ifmf-vlan-offload {
             type empty;
           }
           leaf ifmf-keepalives {
             type empty;
           }
           leaf ifmf-no-keepalives {
             type empty;
           }
           leaf ifmf-give-up {
             type empty;
           }
           leaf ifmf-loose-lcp {
             type empty;
           }
           leaf ifmf-loose-ncp {
             type empty;
           }
           leaf ifmf-ppp-acfc {
             type empty;
           }
           leaf ifmf-ppp-pfc {
             type empty;
           }
           leaf ifmf-loose-lmi {
             type empty;
           }
           leaf ifmf-dce {
             type empty;
           }
           leaf ifmf-dte {
             type empty;
           }
           leaf generic-value {
             type int32;
             description "Hexadecimal value of unknown flag bits";
           }
           leaf internal-flags {
             type int32;
             description "Hexadecimal value of internal flag bits";
           }
         }
         container optics-properties {
           leaf wavelength {
             type string;
             description "Wavelength of optics in nanometers";
           }
           leaf frequency {
             type string;
             description "Frequency of optics in terahertz";
           }
         }
         container keepalive-config {
           leaf keepalive-interval {
             type int32;
           }
           leaf keepalive-up-count {
             type int32;
           }
           leaf keepalive-down-count {
             type int32;
           }
         }
         container lmi-dce-config {
           leaf lmi-type {
             type string;
           }
           leaf lmi-n392dce {
             type int32;
           }
           leaf lmi-n393dce {
             type int32;
           }
           leaf lmi-t392dce {
             type int32;
           }
         }
         container lmi-dte-config {
           leaf lmi-type {
             type string;
           }
           leaf lmi-n391dte {
             type int32;
           }
           leaf lmi-n392dte {
             type int32;
           }
           leaf lmi-n393dte {
             type int32;
           }
           leaf lmi-t391dte {
             type int32;
           }
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container voq-counters {
           leaf voq-counters-error-message {
             type string;
             description "VOQ statistics not available for this interface";
           }
           container voq {
             container fpc {
               leaf fpc-no {
                 type int32;
                 description "FPC number";
               }
               container pfe {
                 leaf-list pfe-no {
                   type int32;
                   description "PFE number";
                 }
                 leaf voq-counters-tail-drop-packets {
                   type int32;
                   description "Tail DROP packet count";
                 }
                 leaf voq-counters-tail-drop-packets-rate {
                   type int32;
                   description "Rate at which tail packets are dropped";
                 }
                 leaf voq-counters-tail-drop-bytes {
                   type int32;
                   description "Tail DROP bytes count";
                 }
                 leaf voq-counters-tail-drop-bytes-rate {
                   type int32;
                   description "Rate at which tail bytes are dropped";
                 }
                 leaf voq-counters-drop-packets {
                   type int32;
                   description "DROP packet count";
                 }
                 leaf voq-counters-drop-packets-rate {
                   type int32;
                   description "Rate at which packets are dropped";
                 }
                 leaf voq-counters-drop-bytes {
                   type int32;
                   description "DROP bytes count";
                 }
                 leaf voq-counters-drop-bytes-rate {
                   type int32;
                   description "Rate at which bytes are dropped";
                 }
               }
             }
             leaf queue-number {
               type int32;
               description "Queue number";
             }
             leaf forwarding-class-name {
               type string;
               description "Forwarding class name associated with queue";
             }
           }
         }
         container smart-sfp-av-titan-statistics {
           leaf smart-sfp-av-titan-error-message {
             type string;
             description "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           container smart-sfp-av-titan-defect-list {
             leaf sfp-tdm-defects {
               type string;
             }
             leaf sfp-system-defects {
               type string;
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container ppp-flags {
           leaf iff-ppp-flags-acfc {
             type empty;
           }
           leaf iff-ppp-flags-pfc {
             type empty;
           }
         }
         list ncp-information {
           leaf ncp-protocol {
             type string;
             description "Network protocol for this NCP instance";
           }
           leaf ncp-state {
             type string;
             description "State of this NCP instance";
           }
         }
         container es-ifd-stats {
           leaf total-anti-replay-count {
             type int32;
             description "Number of antireplay failures";
           }
           leaf total-authentication-failure-count {
             type int32;
             description "Number of authentication failures";
           }
         }
         container optics-bit-rate {
           leaf bit-rate {
             type string;
             description " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container preserve-interface-statistics {
           leaf if-switchover-total {
             type int32;
             description "Total number of interface switchovers";
           }
           leaf if-switchover-last-attempt {
             type string;
             description "Interface on which the last switchover was attempted";
           }
           leaf if-switchover-last-time {
             type string;
             description "Time at which last interface switchover was attempted";
           }
           leaf if-switchover-min-max-avg-time {
             type string;
             description "Minimum, maximum and average interface switchover time";
           }
         }
         container extended-port-information {
           leaf local-port-id {
             type uint32;
             description "EP Local port id";
           }
           leaf internal-mc-ae-id {
             type uint32;
             description "Internal MC-AE id";
           }
           leaf internal-lacp-port-id {
             type uint32;
             description "Internal LACP port id";
           }
           leaf internal-mc-ae-redundancy-group {
             type uint32;
             description "Internal MC-AE Redundancy group";
           }
           leaf internal-mc-ae-mode {
             type string;
             description "Internal MC-AE Mode";
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container multilink-interface-errors {
           leaf oversized-frames {
             type int32;
             description "Number of oversized frames detected";
           }
           leaf input-error-frames {
             type int32;
             description "Number of frames for which an error occurred on input";
           }
           leaf input-disabled-bundle {
             type int32;
             description "Count of packets received on a disabled link or bundle";
           }
           leaf output-disabled-bundle {
             type int32;
             description "Count of packets transmitted on a disabled link or bundle";
           }
           leaf queuing-drops {
             type int32;
             description "Count of packets dropped by the output queue of the I/O Manager ASIC";
           }
           leaf packet-buffer-overflow {
             type int32;
             description "Number of times the packet data buffer overflowed";
           }
           leaf fragment-buffer-overflow {
             type int32;
             description "Number of times the fragment data buffer overflowed";
           }
           leaf fragment-timeout {
             type int32;
             description "Fragments timed out during assembly";
           }
           leaf sequence-number-missing {
             type int32;
             description "Gap detected in sequence numbers";
           }
           leaf out-of-order-sequence-number {
             type int32;
             description "Fragments with an out-of-order sequence number";
           }
           leaf out-of-range-sequence-number {
             type int32;
             description "Fragments with an out-of-range sequence number";
           }
           leaf data-memory-error {
             type int32;
             description "Errors detected in data memory";
           }
           leaf control-memory-error {
             type int32;
             description "Errors detected in control memory";
           }
         }
         container mlfr-uni-nni-bundle-options {
           leaf mlfr-uni-nni-device-type {
             type string;
             description "LMI device type of this multilink Frame Relay UNI NNI bundle instance";
           }
           leaf mlfr-uni-nni-mrru {
             type int32;
             description "Maximum RRU size of this multilink Frame Relay UNI NNI bundle instance";
           }
           leaf mlfr-uni-nni-bandwidth {
             type string;
             description "Bandwidth of this multilink Frame Relay UNI NNI bundle";
           }
           leaf red-differential-delay {
             type int32;
             description "Maximum allowable differential delay of this multilink Frame Relay UNI NNI bundle instance";
           }
           leaf red-differential-delay-action {
             type string;
             description "Action to perform (remove link from bundle or disable transmit) when exceeding red limit";
           }
           leaf yellow-differential-delay {
             type int32;
             description "Maximum allowable differential delay of this multilink Frame Relay UNI NNI bundle instance";
           }
           leaf mlfr-uni-nni-fragment-threshold {
             type int32;
             description "Fragment size of this multilink Frame Relay UNI NNI bundle instance";
           }
           leaf mlfr-uni-nni-minimum-links {
             type int32;
             description "Minimum number of links to sustain this multilink Frame Relay UNI NNI bundle instance";
           }
           leaf lip-hello-timer {
             type int32;
             description "Timer for sending periodic hello messages to the remote endpoint";
           }
           leaf lip-ack-timer {
             type int32;
             description "How long to wait for a HELLO_ACK, ADD_LINK_ACK, or REMOVE_LINK_ACK";
           }
           leaf lip-ack-retries {
             type int32;
             description "Maximum number of retransmissions for HELLO and LINK_ADD";
           }
           leaf bundle-class {
             type int32;
             description "Type of bundle class: A, B or C";
           }
           leaf mlfr-uni-nni-drop-timeout {
             type int32;
             description "How long to wait for all fragments of a complete packet to arrive";
           }
           leaf mlfr-uni-nni-link-layer-overhead {
             type string;
             description "Multilink Frame Relay UNI NNI bundle link layer overhead";
           }
           leaf mlfr-uni-nni-lmi-type {
             type string;
             description "LMI type (ANSI or Q.933A) of this multilink Frame Relay UNI NNI bundle instance";
           }
           leaf t391 {
             type int32;
             description "Multilink Frame Relay UNI NNI link integrity verify polling timer";
           }
           leaf t392 {
             type int32;
             description "Multilink Frame Relay UNI NNI polling verification timer";
           }
           leaf n391 {
             type int32;
             description "Multilink Frame Relay UNI NNI full status polling counter";
           }
           leaf n392 {
             type int32;
             description "Multilink Frame Relay UNI NNI LMI error threshold";
           }
           leaf n393 {
             type int32;
             description "Multilink Frame Relay UNI NNI LMI monitored event count";
           }
         }
         container multilink-bundle-errors {
           leaf packet-drops {
             type int32;
             description "Number of packets dropped";
           }
           leaf packet-drop-bytes {
             type int32;
             description "Number of bytes in dropped packets";
           }
           leaf fragment-drops {
             type int32;
             description "Number of fragments dropped";
           }
           leaf fragment-drop-bytes {
             type int32;
             description "Number of bytes in dropped fragments";
           }
           leaf mrru-exceeded {
             type int32;
             description "Number of assembled packets that exceeded MRRU";
           }
           leaf processing-errors {
             type int32;
             description "Number of errors encountered in assembling packets";
           }
         }
         container input-error-list {
           leaf input-errors {
             type int32;
           }
           leaf input-drops {
             type int32;
           }
           leaf invalid-vcs {
             type int32;
           }
           leaf framing-errors {
             type int32;
           }
           leaf input-runts {
             type int32;
           }
           leaf input-giants {
             type int32;
           }
           leaf input-bucket-drops {
             type int32;
           }
           leaf input-discards {
             type int32;
           }
           leaf input-l3-incompletes {
             type int32;
           }
           leaf input-l2-channel-errors {
             type int32;
           }
           leaf input-l2-mismatch-timeouts {
             type int32;
           }
           leaf input-fifo-errors {
             type int32;
           }
           leaf input-dma-errors {
             type int32;
           }
           leaf hs-link-crc-errors {
             type int32;
           }
           leaf hs-link-fifo-overflows {
             type int32;
           }
           leaf sram-errors {
             type int32;
           }
           leaf input-resource-errors {
             type int32;
           }
         }
         container output-error-list {
           leaf carrier-transitions {
             type int32;
           }
           leaf output-errors {
             type int32;
           }
           leaf output-drops {
             type int32;
           }
           leaf output-collisions {
             type int32;
           }
           leaf output-hs-link-fifo-overflows {
             type int32;
           }
           leaf aged-packets {
             type int32;
           }
           leaf output-fifo-errors {
             type int32;
           }
           leaf output-dma-errors {
             type int32;
           }
           leaf hs-link-fifo-underflows {
             type int32;
           }
           leaf hs-link-crc-errors {
             type int32;
           }
           leaf mtu-errors {
             type int32;
           }
           leaf output-resource-errors {
             type int32;
           }
           leaf output-bucket-drops {
             type int32;
           }
           leaf ecn-marked-packets {
             type int32;
           }
         }
         container ber-threshold {
           leaf ber-sf {
             type string;
             description "BER-SF threshold";
           }
           leaf ber-sd {
             type string;
             description "BER-SD threshold";
           }
         }
         container ds1-crc-alarm-threshold {
           leaf ds1-crc-alarm-threshold-major {
             type string;
             description "Threshold for CRC Major alarm";
           }
           leaf ds1-crc-alarm-threshold-minor {
             type string;
             description "Threshold for CRC Minor alarm";
           }
         }
         container active-alarms {
           leaf type {
             type string;
             description "Media type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container active-defects {
           leaf type {
             type string;
             description "Media type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container media-state-information {
           leaf media-type {
             type string;
             description "Type of media this information is for";
           }
           list media-state {
             leaf media-state-name {
               type string;
               description "Media state category";
             }
             leaf media-state-state {
               type string;
               description "Current state for this category";
             }
           }
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-payload-pointer-information {
           leaf sonet-payload-pointer-curptr {
             type string;
             description "Value of the SONET/SDH payload pointer, derived from the H1 and H2 overhead bytes";
           }
           leaf sonet-payload-pointer-ptrinc-count {
             type string;
             description "Number of times the value of the SONET/SDH payload pointer had positive justification";
           }
           leaf sonet-payload-pointer-ptrdec-count {
             type string;
             description "Number of times the value of the SONET/SDH payload pointer had negative justification";
           }
           leaf sonet-payload-pointer-newptr-ndf-count {
             type string;
             description "Number of times a new payload pointer was created with the New Data Found flag set";
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description "Optics laser status";
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         container ethernet-pcs-statistics {
           leaf bit-error-seconds {
             type int32;
             description "Bit error duration";
           }
           leaf errored-blocks-seconds {
             type int32;
             description "Errored blocks duration";
           }
         }
         container link-degrade-information {
           leaf lnk-degrd-mon {
             type string;
             description "Link degrade feature is enable/disable for this interface";
           }
           leaf lnk-degrd-set-thr {
             type uint32;
             description "BER At Which Link Considered Improved";
           }
           leaf lnk-degrd-clr-thr {
             type uint32;
             description "BER At Which Link Considered Degraded";
           }
           leaf lnk-degrd-war-set-thr {
             type uint32;
             description "BER At Which Warning Will Be Trigged";
           }
           leaf lnk-degrd-war-clr-thr {
             type uint32;
             description "BER At Which Warning Will Be Cleared";
           }
           leaf lnk-degrd-est-ber {
             type uint32;
             description "Link Degrade Estimated BER";
           }
           leaf lnk-degrd-seconds {
             type uint64;
             description "Link Degrade ";
           }
           leaf lnk-degrd-count {
             type uint64;
             description "Link Degrade ";
           }
           leaf lnk-degrd-state {
             type string;
             description "Link Degrade ";
           }
         }
         container ethernet-fec-mode {
           leaf enabled_fec_mode {
             type string;
             description "Enabled FEC mode: <NONE/FEC74/FEC91/FEC108>";
           }
         }
         container ethernet-fec-statistics {
           leaf fec_ccw_count {
             type int32;
             description "FEC Corrected Error Count";
           }
           leaf fec_nccw_count {
             type int32;
             description "FEC Uncorrected Error Count";
           }
           leaf fec_ccw_error_rate {
             type int32;
             description "FEC Corrected Error Rate (errors/sec)";
           }
           leaf fec_nccw_error_rate {
             type int32;
             description "FEC Uncorrected Error Rate (errors/sec)";
           }
         }
         container ctle {
           leaf ctle_value {
             type int32;
             description "Ctle value";
           }
         }
         container pre-emphasis {
           leaf pre_emphasis_value {
             type int32;
             description "Pre-emphasis value";
           }
         }
         container differential-amplitude {
           leaf differential_amplitude_value {
             type int32;
             description "Differential-amplitude value";
           }
         }
         container ethernet-mac-statistics {
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container sriov-vf-statistics {
           leaf vf-number {
             type uint32;
           }
           leaf pci-address {
             type string;
           }
           leaf mapped-to {
             type string;
           }
           leaf input-bytes {
             type int32;
           }
           leaf input-packets {
             type int32;
           }
           leaf output-bytes {
             type int32;
           }
           leaf output-packets {
             type int32;
           }
           leaf mc-packets {
             type int32;
           }
         }
         container ethernet-prbs-mode {
           leaf prbs-mode {
             type string;
             description "PRBS Mode: <Enabled/Disabled>";
           }
         }
         container ethernet-prbs-statistics {
           leaf prbs-lane {
             type int32;
             description "PRBS Lane";
           }
           leaf prbs-state {
             type string;
             description "PRBS State";
           }
           leaf prbs-error-count {
             type int32;
             description "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           leaf fibrechannel-port-flow-control-mode {
             type string;
           }
           list fibrechannel-port-flow-control-credits {
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
           leaf autonegotiation-status {
             type string;
           }
           leaf link-partner-duplexity {
             type string;
           }
           leaf flow-control {
             type string;
           }
           leaf link-partner-status {
             type string;
             description "Auto-negotiation status of link partner";
           }
           leaf link-partner-speed {
             type string;
             description "Link partner speed";
           }
           leaf link-partner-reason {
             type string;
             description "Reason link partner is down";
           }
           container local-info {
             leaf local-flow-control {
               type string;
               description "Local interface flow control type";
             }
             leaf local-flow-control-tx {
               type string;
               description "Local interface flow control tx type";
             }
             leaf local-flow-control-rx {
               type string;
               description "Local interface flow control rx type";
             }
             leaf local-remote-fault {
               type string;
               description "Local interface remote fault type";
             }
             leaf local-link-speed {
               type string;
               description "Local link speed";
             }
             leaf local-link-duplexity {
               type string;
             }
           }
         }
         container mac-database {
           leaf number-of-mac-record {
             type int32;
           }
           list mac-record {
             leaf mac-address {
               type jt:mac-addr;
             }
             leaf receive-frames {
               type int32;
             }
             leaf receive-bytes {
               type int32;
             }
             leaf transmit-frames {
               type int32;
             }
             leaf transmit-bytes {
               type int32;
             }
           }
         }
         container dsl-information {
           leaf dsl-line-status {
             type string;
             description "Status of modem";
           }
           leaf dsl-line-operating-mode {
             type string;
             description "Line type of digital subscriber line";
           }
           leaf dsl-line-type {
             type string;
             description "Line type of digital subscriber line";
           }
           leaf adsl-annex-type {
             type string;
             description "Type of ADSL annex";
           }
           leaf adsl-last-fail-code {
             type string;
             description "Reason for the last line-open failure";
           }
           leaf adsl-subfunction {
             type int32;
             description "Specified analog front-end chip and discrete front end";
           }
           leaf adsl-seconds-in-showtime {
             type int32;
             description "Number of seconds the ADSL connection is in showtime state";
           }
           container dsl-chipset-information {
             leaf atu-r-country-code {
               type int32;
               description "Country code for ATU-R chipset vendor";
             }
             leaf atu-c-country-code {
               type int32;
               description "Country code for ATU-C chipset vendor";
             }
             leaf atu-r-vendor-id {
               type string;
               description "ATU-R ITU chipset vendor ID";
             }
             leaf atu-c-vendor-id {
               type string;
               description "ATU-C ITU chipset vendor ID";
             }
             leaf atu-r-vendor-specific {
               type int32;
               description "ATU-R vendor-specific data";
             }
             leaf atu-c-vendor-specific {
               type int32;
               description "ATU-C vendor-specific data";
             }
           }
           container dsl-statistics {
             leaf near-end-attainable-bitrate {
               type int32;
               description "Near-end attainable bit rate";
             }
             leaf far-end-attainable-bitrate {
               type int32;
               description "Far-end attainable bit rate";
             }
             leaf near-end-attenuation {
               type string;
               description "Near-end attenuation";
             }
             leaf far-end-attenuation {
               type string;
               description "Far-end attenuation";
             }
             leaf near-end-capacity-used {
               type int32;
               description "Near-end capacity used";
             }
             leaf far-end-capacity-used {
               type int32;
               description "Far-end capacity used";
             }
             leaf near-end-noise-margin {
               type string;
               description "Near-end noise margin";
             }
             leaf far-end-noise-margin {
               type string;
               description "Far-end noise margin";
             }
             leaf near-end-output-power {
               type string;
               description "Near-end output power";
             }
             leaf far-end-output-power {
               type string;
               description "Far-end output power";
             }
             leaf near-end-interleaved-bitrate {
               type int32;
               description "Near-end interleaved bit rate";
             }
             leaf near-end-fast-bitrate {
               type int32;
               description "Near-end fast bit rate";
             }
             leaf far-end-interleaved-bitrate {
               type int32;
               description "Far-end interleaved bit rate";
             }
             leaf far-end-fast-bitrate {
               type int32;
               description "Far-end fast bit rate";
             }
             leaf near-end-interleaved-crc {
               type int32;
               description "Near-end interleaved cyclic redundancy check correction";
             }
             leaf near-end-fast-crc {
               type int32;
               description "Near-end fast cyclic redundancy check correction";
             }
             leaf far-end-interleaved-crc {
               type int32;
               description "Far-end interleaved cyclic redundancy check correction";
             }
             leaf far-end-fast-crc {
               type int32;
               description "Far-end fast cyclic redundancy check";
             }
             leaf near-end-interleaved-fec {
               type int32;
               description "Near-end interleaved footer error correction";
             }
             leaf near-end-fast-fec {
               type int32;
               description "Near-end fast footer error correction";
             }
             leaf far-end-interleaved-fec {
               type int32;
               description "Far-end interleaved footer error correction";
             }
             leaf far-end-fast-fec {
               type int32;
               description "Far-end fast footer error correction";
             }
             leaf near-end-interleaved-hec {
               type int32;
               description "Near-end interleaved header error correction";
             }
             leaf near-end-fast-hec {
               type int32;
               description "Near-end fast header error correction";
             }
             leaf far-end-interleaved-hec {
               type int32;
               description "Far-end interleaved header error correction";
             }
             leaf far-end-fast-hec {
               type int32;
               description "Far-end fast header error correction";
             }
             leaf near-end-interleaved-rx-cells {
               type int32;
               description "Near-end interleaved receiver cells";
             }
             leaf near-end-fast-rx-cells {
               type int32;
               description "Near-end fast receiver cells";
             }
             leaf near-end-interleaved-tx-cells {
               type int32;
               description "Near-end interleaved transmitter cells";
             }
             leaf near-end-fast-tx-cells {
               type int32;
               description "Near-end fast transmitter cells";
             }
             leaf interleaved-rx-cells {
               type int32;
               description "Interleaved receiver cells";
             }
             leaf fast-rx-cells {
               type int32;
               description "Fast receiver cells";
             }
             leaf interleaved-tx-cells {
               type int32;
               description "Interleaved transmitter cells";
             }
             leaf fast-tx-cells {
               type int32;
               description "Fast transmitter cells";
             }
           }
         }
         container vdsl-information {
           leaf vdsl-line-status {
             type string;
             description "Status of modem";
           }
           leaf vdsl-line-profile-type {
             type string;
             description "Line type of digital subscriber line";
           }
           leaf vdsl-line-type {
             type string;
             description "Line type of digital subscriber line";
           }
           leaf vdsl-annex-type {
             type string;
             description "Type of VDSL annex";
           }
           leaf vdsl-last-fail-code {
             type string;
             description "Reason for the last line-open failure";
           }
           leaf vdsl-subfunction {
             type int32;
             description "Specified analog front-end chip and discrete front end";
           }
           leaf vdsl-seconds-in-showtime {
             type int32;
             description "Number of seconds the VDSL connection is in showtime state";
           }
           container vdsl-chipset-information {
             leaf vtu-r-country-code {
               type int32;
               description "Country code for VTU-R chipset vendor";
             }
             leaf vtu-c-country-code {
               type int32;
               description "Country code for VTU-C chipset vendor";
             }
             leaf vtu-r-vendor-id {
               type string;
               description "VTU-R ITU chipset vendor ID";
             }
             leaf vtu-c-vendor-id {
               type string;
               description "VTU-C ITU chipset vendor ID";
             }
             leaf vtu-r-vendor-specific {
               type int32;
               description "VTU-R vendor-specific data";
             }
             leaf vtu-c-vendor-specific {
               type int32;
               description "VTU-C vendor-specific data";
             }
           }
           container vdsl-statistics {
             leaf vdsl-near-end-attainable-bitrate {
               type int32;
               description "Near end attainable bit rate ";
             }
             leaf vdsl-far-end-attainable-bitrate {
               type int32;
               description "Far-end attainable bit rate";
             }
             leaf vdsl-near-end-attenuation {
               type string;
               description "Near-end attenuation";
             }
             leaf vdsl-far-end-attenuation {
               type string;
               description "Far-end attenuation";
             }
             leaf vdsl-near-end-capacity-used {
               type int32;
               description "Near-end capacity used";
             }
             leaf vdsl-far-end-capacity-used {
               type int32;
               description "Far-end capacity used";
             }
             leaf vdsl-near-end-noise-margin {
               type string;
               description "Near-end noise margin";
             }
             leaf vdsl-far-end-noise-margin {
               type string;
               description "Far-end noise margin";
             }
             leaf vdsl-near-end-output-power {
               type string;
               description "Near-end output power";
             }
             leaf vdsl-far-end-output-power {
               type string;
               description "Far-end output power";
             }
             leaf vdsl-near-end-interleaved-bitrate {
               type int32;
               description "Near-end interleaved bit rate";
             }
             leaf vdsl-near-end-fast-bitrate {
               type int32;
               description "Near-end fast bit rate";
             }
             leaf vdsl-far-end-interleaved-bitrate {
               type int32;
               description "Far-end interleaved bit rate";
             }
             leaf vdsl-far-end-fast-bitrate {
               type int32;
               description "Far-end fast bit rate";
             }
             leaf vdsl-near-end-interleaved-crc {
               type int32;
               description "Near-end interleaved cyclic redundancy check correction";
             }
             leaf vdsl-near-end-fast-crc {
               type int32;
               description "Near-end fast cyclic redundancy check correction";
             }
             leaf vdsl-far-end-interleaved-crc {
               type int32;
               description "Far-end interleaved cyclic redundancy check correction";
             }
             leaf vdsl-far-end-fast-crc {
               type int32;
               description "Far-end fast cyclic redundancy check";
             }
             leaf vdsl-near-end-interleaved-fec {
               type int32;
               description "Near-end interleaved footer error correction";
             }
             leaf vdsl-near-end-fast-fec {
               type int32;
               description "Near-end fast footer error correction";
             }
             leaf vdsl-far-end-interleaved-fec {
               type int32;
               description "Far-end interleaved footer error correction";
             }
             leaf vdsl-far-end-fast-fec {
               type int32;
               description "Far-end fast footer error correction";
             }
             leaf vdsl-near-end-interleaved-hec {
               type int32;
               description "Near-end interleaved header error correction";
             }
             leaf vdsl-near-end-fast-hec {
               type int32;
               description "Near-end fast header error correction";
             }
             leaf vdsl-far-end-interleaved-hec {
               type int32;
               description "Far-end interleaved header error correction";
             }
             leaf vdsl-far-end-fast-hec {
               type int32;
               description "Far-end fast header error correction";
             }
             leaf vdsl-near-end-interleaved-rx-cells {
               type int32;
               description "Near-end interleaved receiver cells";
             }
             leaf vdsl-near-end-fast-rx-cells {
               type int32;
               description "Near-end fast receiver cells";
             }
             leaf vdsl-near-end-interleaved-tx-cells {
               type int32;
               description "Near-end interleaved transmitter cells";
             }
             leaf vdsl-near-end-fast-tx-cells {
               type int32;
               description "Near-end fast transmitter cells";
             }
           }
         }
         container shdsl-information {
           leaf shdsl-line-termination {
             type string;
             description "Line termination remote or central";
           }
           leaf shdsl-annex {
             type string;
             description "Type of SHDSL annex";
           }
           leaf shdsl-line-mode {
             type string;
             description "Two or four wire mode";
           }
           leaf shdsl-modem-status {
             type string;
             description "Status of the SHDSL modem";
           }
           leaf shdsl-bit-rate {
             type int32;
             description "Actual line rate";
           }
           leaf shdsl-last-fail-reason {
             type string;
             description "Reason for last line-open failure";
           }
           leaf shdsl-last-fail-code {
             type int32;
             description "Last line-open failure code";
           }
           leaf shdsl-framer-mode {
             type string;
             description "Framer mode used";
           }
           leaf shdsl-dying-gasp {
             type string;
             description "Dying gasp is enabled or disabled";
           }
           leaf shdsl-framer-sync-status {
             type string;
             description "Framer synchronization status";
           }
           leaf shdsl-chipset-version {
             type int32;
             description "Version number for the DSP/framer chip";
           }
           leaf shdsl-firmware-version {
             type string;
             description "Transreceiver firmware release number";
           }
           container shdsl-statistics {
             leaf shdsl-loop-attenuation {
               type int32;
               description "An estimate of the loop attenuation";
             }
             leaf shdsl-transmit-power {
               type int32;
               description "Nominal transmit power";
             }
             leaf shdsl-receiver-gain {
               type int32;
               description "Total receiver gain";
             }
             leaf shdsl-snr-sampling {
               type int32;
               description "Received signal to noise ratio";
             }
             leaf shdsl-rx-cells {
               type int32;
               description "Total ATM cells received";
             }
             leaf shdsl-tx-cells {
               type int32;
               description "Total ATM cells transmitted";
             }
             leaf shdsl-crc {
               type int32;
               description "Number of CRC errors";
             }
             leaf shdsl-sega {
               type int32;
               description "Number of SEGA errors";
             }
             leaf shdsl-losw {
               type int32;
               description "Number of LOSW  errors";
             }
             leaf shdsl-hec {
               type int32;
               description "Header error check errors";
             }
             leaf shdsl-cell-drop {
               type int32;
               description "Cells dropped because of errors";
             }
           }
         }
         container efm-information {
           container efm-group-statistics {
             leaf efm-type {
               type string;
               description "EFM type Single pair or EFM bond";
             }
             leaf efm-active-pairs {
               type int32;
               description "Number of EFM Active Pairs";
             }
             leaf efm-group-bit-rate {
               type int32;
               description "Bit rate (in Kbps) for EFM Group";
             }
           }
           container efm-line-statistics {
             leaf line-pair {
               type int32;
               description "Line Pair Number";
             }
             leaf line-status {
               type string;
             }
             container active-alarms-efm {
               leaf type-efm {
                 type string;
                 description "Media type for associated interface alarms";
               }
               container interface-alarms {
                 leaf alarm-not-present {
                   type empty;
                   description "No alarm indicated";
                 }
                 leaf sonet-alarm-lol {
                   type empty;
                   description "Loss of light alarm";
                 }
                 leaf sonet-alarm-pll {
                   type empty;
                   description "PLL lock alarm";
                 }
                 leaf sonet-alarm-lof {
                   type empty;
                   description "Loss of frame alarm";
                 }
                 leaf sonet-alarm-los {
                   type empty;
                   description "Loss of signal alarm";
                 }
                 leaf sonet-alarm-sef {
                   type empty;
                   description "Severely errored frame alarm";
                 }
                 leaf sonet-alarm-lais {
                   type empty;
                   description "Line AIS alarm";
                 }
                 leaf sonet-alarm-pais {
                   type empty;
                   description "Path AIS alarm";
                 }
                 leaf sonet-alarm-lop {
                   type empty;
                   description "Loss of pointer alarm";
                 }
                 leaf sonet-alarm-berr-sd {
                   type empty;
                   description "Bit error rate alarm, defect";
                 }
                 leaf sonet-alarm-berr-sf {
                   type empty;
                   description "Bit error rate alarm, fault";
                 }
                 leaf sonet-alarm-lrdi {
                   type empty;
                   description "Line remote defect indicator alarm";
                 }
                 leaf sonet-alarm-prdi {
                   type empty;
                   description "Path remote defect indicator alarm";
                 }
                 leaf sonet-alarm-rei {
                   type empty;
                   description "Path remote error indicator alarm";
                 }
                 leaf sonet-alarm-uneq {
                   type empty;
                   description "Unequipped alarm";
                 }
                 leaf sonet-alarm-pmis {
                   type empty;
                   description "Path payload level mismatch alarm";
                 }
                 leaf sonet-alarm-loc {
                   type empty;
                   description "Loss of cell delineation alarm";
                 }
                 leaf sonet-alarm-vais {
                   type empty;
                   description "VT AIS alarm";
                 }
                 leaf sonet-alarm-vlop {
                   type empty;
                   description "VT loss of pointer alarm";
                 }
                 leaf sonet-alarm-vrdi {
                   type empty;
                   description "VT remote defect indicator alarm";
                 }
                 leaf sonet-alarm-vuneq {
                   type empty;
                   description "VT unequipped alarm";
                 }
                 leaf sonet-alarm-vmis {
                   type empty;
                   description "VT label mismatch alarm";
                 }
                 leaf sonet-alarm-vloc {
                   type empty;
                   description "VT loss of cell delineation alarm";
                 }
                 leaf sdh-alarm-lol {
                   type empty;
                   description "Loss of light alarm";
                 }
                 leaf sdh-alarm-pll {
                   type empty;
                   description "PLL lock alarm";
                 }
                 leaf sdh-alarm-lof {
                   type empty;
                   description "Loss of frame alarm";
                 }
                 leaf sdh-alarm-los {
                   type empty;
                   description "Loss of signal alarm";
                 }
                 leaf sdh-alarm-oof {
                   type empty;
                   description "Out of frame alarm";
                 }
                 leaf sdh-alarm-msais {
                   type empty;
                   description "Multiplex section AIS alarm";
                 }
                 leaf sdh-alarm-hpais {
                   type empty;
                   description "High order path AIS alarm";
                 }
                 leaf sdh-alarm-lop {
                   type empty;
                   description "Loss of pointer alarm";
                 }
                 leaf sdh-alarm-berr-sd {
                   type empty;
                   description "Bit error rate alarm, defect";
                 }
                 leaf sdh-alarm-berr-sf {
                   type empty;
                   description "Bit error rate alarm, fault";
                 }
                 leaf sdh-alarm-msferf {
                   type empty;
                   description "Multiplex section far-end remote failure alarm";
                 }
                 leaf sdh-alarm-hpferf {
                   type empty;
                   description "High order path far-end remote failure alarm";
                 }
                 leaf sdh-alarm-hpfebe {
                   type empty;
                   description "High order path far-end block error alarm";
                 }
                 leaf sdh-alarm-hpuneq {
                   type empty;
                   description "High order path unequipped alarm";
                 }
                 leaf sdh-alarm-hpplm {
                   type empty;
                   description "High order path payload level mismatch alarm";
                 }
                 leaf sdh-alarm-loc {
                   type empty;
                   description "Loss of cell delineation alarm";
                 }
                 leaf sdh-alarm-tuais {
                   type empty;
                   description "TU AIS alarm";
                 }
                 leaf sdh-alarm-tulop {
                   type empty;
                   description "TU loss of pointer alarm";
                 }
                 leaf sdh-alarm-turdi {
                   type empty;
                   description "TU remote defect indicator alarm";
                 }
                 leaf sdh-alarm-tuuneq {
                   type empty;
                   description "TU unequipped alarm";
                 }
                 leaf sdh-alarm-tumis {
                   type empty;
                   description "TU label mismatch error";
                 }
                 leaf sdh-alarm-tuloc {
                   type empty;
                   description "TU loss of cell delineation alarm";
                 }
                 leaf ds3-alarm-pll {
                   type empty;
                   description "PLL lock alarm";
                 }
                 leaf ds3-alarm-ais {
                   type empty;
                   description "AIS alarm";
                 }
                 leaf ds3-alarm-lof {
                   type empty;
                   description "Loss of frame alarm";
                 }
                 leaf ds3-alarm-los {
                   type empty;
                   description "Loss of signal alarm";
                 }
                 leaf ds3-alarm-lcv {
                   type empty;
                   description "Line code violation alarm";
                 }
                 leaf ds3-alarm-exz {
                   type empty;
                   description "Excessive zeros alarm";
                 }
                 leaf ds3-alarm-ferf {
                   type empty;
                   description "Far-end receive failure alarm";
                 }
                 leaf ds3-alarm-ylw {
                   type empty;
                   description "Yellow alarm";
                 }
                 leaf ds3-alarm-idle {
                   type empty;
                   description "Idle alarm";
                 }
                 leaf ds1-alarm-ais {
                   type empty;
                   description "AIS alarm";
                 }
                 leaf ds1-alarm-lof {
                   type empty;
                   description "Loss of frame alarm";
                 }
                 leaf ds1-alarm-los {
                   type empty;
                   description "Loss of signal alarm";
                 }
                 leaf ds1-alarm-ylw {
                   type empty;
                   description "Yellow alarm";
                 }
                 leaf ds1-alarm-crc-major {
                   type empty;
                   description "CRC errors crossed major threshold";
                 }
                 leaf ds1-alarm-crc-minor {
                   type empty;
                   description "CRC errors crossed minor threshold";
                 }
                 leaf dsl-alarm-lof {
                   type empty;
                   description "Loss of frame alarm";
                 }
                 leaf dsl-alarm-los {
                   type empty;
                   description "Loss of signal alarm";
                 }
                 leaf dsl-alarm-lom {
                   type empty;
                   description "Loss of multiframe alarm";
                 }
                 leaf dsl-alarm-locdi {
                   type empty;
                   description "Loss of cell delineation alarm for interleaved channel";
                 }
                 leaf dsl-alarm-locdni {
                   type empty;
                   description "Loss of cell delineation alarm for non-interleaved channel";
                 }
                 leaf dsl-alarm-lop {
                   type empty;
                   description "Loss of power alarm";
                 }
                 leaf dsl-alarm-far-lof {
                   type empty;
                   description "Far-end loss-of-frame alarm";
                 }
                 leaf dsl-alarm-far-los {
                   type empty;
                   description "Far-end loss-of-signal alarm";
                 }
                 leaf dsl-alarm-far-locdi {
                   type empty;
                   description "Far-end loss-of-cell-delineation alarm for interleaved channel";
                 }
                 leaf dsl-alarm-far-locdni {
                   type empty;
                   description "Far-end loss-of-cell-delineation alarm for non-interleaved channel";
                 }
                 leaf fibrechannel-alarm-link-down {
                   type empty;
                   description "Link alive failure";
                 }
                 leaf ethernet-alarm-link-down {
                   type empty;
                   description "Link alive failure";
                 }
                 leaf ethernet-alarm-link-local-fault {
                   type empty;
                   description "Link local fault";
                 }
                 leaf ethernet-alarm-link-remote-fault {
                   type empty;
                   description "Link remote fault";
                 }
                 leaf ethernet-alarm-lcdp {
                   type empty;
                   description "Loss of code-group delineation";
                 }
                 leaf isdn-alarm-los {
                   type empty;
                   description "Loss of signal alarm";
                 }
                 leaf isdn-alarm-lof {
                   type empty;
                   description "Loss of frame alarm";
                 }
                 leaf shdsl-alarm-losd {
                   type empty;
                   description "Loss of signal alarm";
                 }
                 leaf shdsl-alarm-losw {
                   type empty;
                   description "Loss of sync word alarm";
                 }
                 leaf shdsl-alarm-line1-losd {
                   type empty;
                   description "Loss of signal (line 1) alarm";
                 }
                 leaf shdsl-alarm-line1-losw {
                   type empty;
                   description "Loss of sync word (line 1) alarm";
                 }
                 leaf shdsl-alarm-line2-losd {
                   type empty;
                   description "Loss of signal (line 2) alarm";
                 }
                 leaf shdsl-alarm-line2-losw {
                   type empty;
                   description "Loss of sync word (line 2) alarm";
                 }
                 leaf shdsl-efm-alarm-losd {
                   type empty;
                   description "Loss of signal alarm";
                 }
                 leaf shdsl-efm-alarm-losw {
                   type empty;
                   description "Loss of sync word alarm";
                 }
                 leaf otn-alarm-los {
                   type empty;
                   description "Loss of signal alarm";
                 }
                 leaf otn-alarm-lof {
                   type empty;
                   description "Loss of frame alarm";
                 }
                 leaf otn-alarm-lom {
                   type empty;
                   description "Loss of multiframe alarm";
                 }
                 leaf otn-alarm-wavelength-lock {
                   type empty;
                   description "Loss of Wavelength Lock alarm";
                 }
                 leaf otn-alarm-otu-ais {
                   type empty;
                   description "OTU Alarm Indication Signal alarm";
                 }
                 leaf otn-alarm-otu-bdi {
                   type empty;
                   description "OTU Background Block Error alarm";
                 }
                 leaf otn-alarm-otu-ttim {
                   type empty;
                   description "OTU Trail Trace Identifier Mismatch alarm";
                 }
                 leaf otn-alarm-otu-iae {
                   type empty;
                   description "OTU Incoming Alignment alarm";
                 }
                 leaf otn-alarm-otu-sd {
                   type empty;
                   description "OTU Signal Degrade alarm";
                 }
                 leaf otn-alarm-otu-sf {
                   type empty;
                   description "OTU Signal Fail alarm";
                 }
                 leaf otn-alarm-otu-biae {
                   type empty;
                   description "OTU Backward Incoming Alignment alarm";
                 }
                 leaf otn-alarm-otu-tsf {
                   type empty;
                   description "OTU Trail Signal Fail alarm";
                 }
                 leaf otn-alarm-otu-ssf {
                   type empty;
                   description "OTU Server Signal Fail alarm";
                 }
                 leaf otn-alarm-otu-fec-excessive {
                   type empty;
                   description "OTU FEC Excessive alarm";
                 }
                 leaf otn-alarm-otu-fec-degraded {
                   type empty;
                   description "OTU FEC Degraded alarm";
                 }
                 leaf otn-alarm-otu-fe-fec-degraded {
                   type empty;
                   description "OTU FE FEC Degraded/Excessive alarm";
                 }
                 leaf otn-alarm-otu-threshold-bbe {
                   type empty;
                   description "OTU Background Block Error threshold alarm";
                 }
                 leaf otn-alarm-otu-threshold-es {
                   type empty;
                   description "OTU Errored Seconds threshold alarm";
                 }
                 leaf otn-alarm-otu-threshold-ses {
                   type empty;
                   description "OTU Severely Errored Seconds threshold alarm";
                 }
                 leaf otn-alarm-otu-threshold-uas {
                   type empty;
                   description "OTU Unavailable Seconds threshold alarm";
                 }
                 leaf otn-alarm-odu-ais {
                   type empty;
                   description "ODU  Alarm Indiaction Signal alarm";
                 }
                 leaf otn-alarm-odu-oci {
                   type empty;
                   description "ODU Open Connection Indication alarm";
                 }
                 leaf otn-alarm-odu-lck {
                   type empty;
                   description "ODU Locked alarm";
                 }
                 leaf otn-alarm-odu-bdi {
                   type empty;
                   description "ODU Backward Defect Indication alarm";
                 }
                 leaf otn-alarm-odu-ttim {
                   type empty;
                   description "ODU Trail Trace Identifier Mismatch alarm";
                 }
                 leaf otn-alarm-odu-sd {
                   type empty;
                   description "ODU Signal Degrade alarm";
                 }
                 leaf otn-alarm-odu-sf {
                   type empty;
                   description "ODU Signal Fail alarm";
                 }
                 leaf otn-alarm-odu-iae {
                   type empty;
                   description "ODU Incoming Alignment alarm";
                 }
                 leaf otn-alarm-odu-ltc {
                   type empty;
                   description "ODU Loss of Tandem Connection alarm";
                 }
                 leaf otn-alarm-odu-csf {
                   type empty;
                   description "ODU Client Signal Fail alarm";
                 }
                 leaf otn-alarm-odu-tsf {
                   type empty;
                   description "ODU Trail Signal Fail alarm";
                 }
                 leaf otn-alarm-odu-ssf {
                   type empty;
                   description "ODU Server Signal Fail alarm";
                 }
                 leaf otn-alarm-odu-rx-aps-change {
                   type empty;
                   description "ODU Rx Aps Change alarm";
                 }
                 leaf otn-alarm-odu-threshold-bbe {
                   type empty;
                   description "ODU Background Block Error threshold alarm";
                 }
                 leaf otn-alarm-odu-threshold-es {
                   type empty;
                   description "ODU Errored Seconds threshold alarm";
                 }
                 leaf otn-alarm-odu-threshold-ses {
                   type empty;
                   description "ODU Severely Errored Seconds threshold alarm";
                 }
                 leaf otn-alarm-odu-threshold-uas {
                   type empty;
                   description "ODU Unavailable Seconds threshold alarm";
                 }
                 leaf otn-alarm-opu-pmi {
                   type empty;
                   description "OPU Payload Mismatch alarm";
                 }
                 leaf otn-alarm-pre-fec-sd {
                   type empty;
                   description "Pre-FEC SD alarm";
                 }
                 leaf otn-alarm-fe-pre-fec-sd {
                   type empty;
                   description "Far end pre-FEC SD alarm";
                 }
                 leaf optics-alarms-mod-fault {
                   type empty;
                   description "Module Fault alarm";
                 }
                 leaf optics-alarms-lol {
                   type empty;
                   description "Loss of Lock alarm";
                 }
                 leaf optics-alarms-los {
                   type empty;
                   description "Loss of Signal alarms";
                 }
                 leaf optics-alarms-lof {
                   type empty;
                   description "Loss of frame alarm";
                 }
                 leaf optics-alarms-lom {
                   type empty;
                   description "Loss of multi-frame alarm";
                 }
                 leaf optics-alarms-otu-bdi {
                   type empty;
                   description "Backward defect indiacation alarm";
                 }
                 leaf optics-alarms-rmsf {
                   type empty;
                   description "Rx Modem sysnc fault alarm";
                 }
                 leaf optics-alarms-rmlol {
                   type empty;
                   description "Rx Modem loss of lock alarm";
                 }
                 leaf optics-alarms-rloa {
                   type empty;
                   description "Rx loss of alignment alarm";
                 }
                 leaf optics-alarms-mbclf {
                   type empty;
                   description "Modulator Bias control loop fail alarm";
                 }
                 leaf optics-alarms-itlaf {
                   type empty;
                   description "ITLA Fault alarm";
                 }
                 leaf optics-alarms-daccf {
                   type empty;
                   description "DAC Calibration Fault alarm";
                 }
                 leaf optics-alarms-adccf {
                   type empty;
                   description "ADC Calibration Fault alarm";
                 }
                 leaf optics-alarms-fec-degrade {
                   type empty;
                   description "FEC Degrade alarm";
                 }
                 leaf optics-alarms-fec-excessive {
                   type empty;
                   description "FEC Excessive alarm";
                 }
                 leaf optics-alarms-fe-fec-degrade {
                   type empty;
                   description "Far-end FEC Degrade alarm";
                 }
                 leaf optics-alarms-fe-fec-excessive {
                   type empty;
                   description "Far-end FEC Excessive alarm";
                 }
                 leaf ima-alarm-startup-fe {
                   type empty;
                   description "IMA group startup far-end alarm";
                 }
                 leaf ima-alarm-config-abort {
                   type empty;
                   description "IMA group config abort alarm";
                 }
                 leaf ima-alarm-config-abort-fe {
                   type empty;
                   description "IMA group config abort far-end alarm";
                 }
                 leaf ima-alarm-insufficient-links {
                   type empty;
                   description "IMA group insufficient links alarm";
                 }
                 leaf ima-alarm-insufficient-links-fe {
                   type empty;
                   description "IMA group insufficient links far-end alarm";
                 }
                 leaf ima-alarm-blocked {
                   type empty;
                   description "IMA group blocked alarm";
                 }
                 leaf ima-alarm-blocked-fe {
                   type empty;
                   description "IMA group blocked far-end alarm";
                 }
                 leaf ima-alarm-timing-mismatch {
                   type empty;
                   description "IMA group timing mismatch alarm";
                 }
                 leaf ima-alarm-version-mismatch {
                   type empty;
                   description "IMA group version mismatch alarm";
                 }
                 leaf ima-alarm-lif {
                   type empty;
                   description "IMA link loss of IMA frame alarm";
                 }
                 leaf ima-alarm-lods {
                   type empty;
                   description "IMA link out of delay synchronization alarm";
                 }
                 leaf ima-alarm-rdi {
                   type empty;
                   description "IMA link remote defect indicator alarm";
                 }
                 leaf ima-alarm-tx-misconnected {
                   type empty;
                   description "IMA link tx misconnected alarm";
                 }
                 leaf ima-alarm-rx-misconnected {
                   type empty;
                   description "IMA link rx misconnected alarm";
                 }
                 leaf ima-alarm-fault {
                   type empty;
                   description "IMA link fault alarm";
                 }
                 leaf ima-alarm-tx-unusable-fe {
                   type empty;
                   description "IMA link Tx unusable far-end alarm";
                 }
                 leaf ima-alarm-rx-unusable-fe {
                   type empty;
                   description "IMA link Tx unusable far-end alarm";
                 }
                 leaf generic-value {
                   type int32;
                   description "Hexadecimal value of unknown flag bits";
                 }
               }
             }
             container active-defects-efm {
               leaf type-efm {
                 type string;
                 description "Media type for associated interface alarms";
               }
               container interface-alarms {
                 leaf alarm-not-present {
                   type empty;
                   description "No alarm indicated";
                 }
                 leaf sonet-alarm-lol {
                   type empty;
                   description "Loss of light alarm";
                 }
                 leaf sonet-alarm-pll {
                   type empty;
                   description "PLL lock alarm";
                 }
                 leaf sonet-alarm-lof {
                   type empty;
                   description "Loss of frame alarm";
                 }
                 leaf sonet-alarm-los {
                   type empty;
                   description "Loss of signal alarm";
                 }
                 leaf sonet-alarm-sef {
                   type empty;
                   description "Severely errored frame alarm";
                 }
                 leaf sonet-alarm-lais {
                   type empty;
                   description "Line AIS alarm";
                 }
                 leaf sonet-alarm-pais {
                   type empty;
                   description "Path AIS alarm";
                 }
                 leaf sonet-alarm-lop {
                   type empty;
                   description "Loss of pointer alarm";
                 }
                 leaf sonet-alarm-berr-sd {
                   type empty;
                   description "Bit error rate alarm, defect";
                 }
                 leaf sonet-alarm-berr-sf {
                   type empty;
                   description "Bit error rate alarm, fault";
                 }
                 leaf sonet-alarm-lrdi {
                   type empty;
                   description "Line remote defect indicator alarm";
                 }
                 leaf sonet-alarm-prdi {
                   type empty;
                   description "Path remote defect indicator alarm";
                 }
                 leaf sonet-alarm-rei {
                   type empty;
                   description "Path remote error indicator alarm";
                 }
                 leaf sonet-alarm-uneq {
                   type empty;
                   description "Unequipped alarm";
                 }
                 leaf sonet-alarm-pmis {
                   type empty;
                   description "Path payload level mismatch alarm";
                 }
                 leaf sonet-alarm-loc {
                   type empty;
                   description "Loss of cell delineation alarm";
                 }
                 leaf sonet-alarm-vais {
                   type empty;
                   description "VT AIS alarm";
                 }
                 leaf sonet-alarm-vlop {
                   type empty;
                   description "VT loss of pointer alarm";
                 }
                 leaf sonet-alarm-vrdi {
                   type empty;
                   description "VT remote defect indicator alarm";
                 }
                 leaf sonet-alarm-vuneq {
                   type empty;
                   description "VT unequipped alarm";
                 }
                 leaf sonet-alarm-vmis {
                   type empty;
                   description "VT label mismatch alarm";
                 }
                 leaf sonet-alarm-vloc {
                   type empty;
                   description "VT loss of cell delineation alarm";
                 }
                 leaf sdh-alarm-lol {
                   type empty;
                   description "Loss of light alarm";
                 }
                 leaf sdh-alarm-pll {
                   type empty;
                   description "PLL lock alarm";
                 }
                 leaf sdh-alarm-lof {
                   type empty;
                   description "Loss of frame alarm";
                 }
                 leaf sdh-alarm-los {
                   type empty;
                   description "Loss of signal alarm";
                 }
                 leaf sdh-alarm-oof {
                   type empty;
                   description "Out of frame alarm";
                 }
                 leaf sdh-alarm-msais {
                   type empty;
                   description "Multiplex section AIS alarm";
                 }
                 leaf sdh-alarm-hpais {
                   type empty;
                   description "High order path AIS alarm";
                 }
                 leaf sdh-alarm-lop {
                   type empty;
                   description "Loss of pointer alarm";
                 }
                 leaf sdh-alarm-berr-sd {
                   type empty;
                   description "Bit error rate alarm, defect";
                 }
                 leaf sdh-alarm-berr-sf {
                   type empty;
                   description "Bit error rate alarm, fault";
                 }
                 leaf sdh-alarm-msferf {
                   type empty;
                   description "Multiplex section far-end remote failure alarm";
                 }
                 leaf sdh-alarm-hpferf {
                   type empty;
                   description "High order path far-end remote failure alarm";
                 }
                 leaf sdh-alarm-hpfebe {
                   type empty;
                   description "High order path far-end block error alarm";
                 }
                 leaf sdh-alarm-hpuneq {
                   type empty;
                   description "High order path unequipped alarm";
                 }
                 leaf sdh-alarm-hpplm {
                   type empty;
                   description "High order path payload level mismatch alarm";
                 }
                 leaf sdh-alarm-loc {
                   type empty;
                   description "Loss of cell delineation alarm";
                 }
                 leaf sdh-alarm-tuais {
                   type empty;
                   description "TU AIS alarm";
                 }
                 leaf sdh-alarm-tulop {
                   type empty;
                   description "TU loss of pointer alarm";
                 }
                 leaf sdh-alarm-turdi {
                   type empty;
                   description "TU remote defect indicator alarm";
                 }
                 leaf sdh-alarm-tuuneq {
                   type empty;
                   description "TU unequipped alarm";
                 }
                 leaf sdh-alarm-tumis {
                   type empty;
                   description "TU label mismatch error";
                 }
                 leaf sdh-alarm-tuloc {
                   type empty;
                   description "TU loss of cell delineation alarm";
                 }
                 leaf ds3-alarm-pll {
                   type empty;
                   description "PLL lock alarm";
                 }
                 leaf ds3-alarm-ais {
                   type empty;
                   description "AIS alarm";
                 }
                 leaf ds3-alarm-lof {
                   type empty;
                   description "Loss of frame alarm";
                 }
                 leaf ds3-alarm-los {
                   type empty;
                   description "Loss of signal alarm";
                 }
                 leaf ds3-alarm-lcv {
                   type empty;
                   description "Line code violation alarm";
                 }
                 leaf ds3-alarm-exz {
                   type empty;
                   description "Excessive zeros alarm";
                 }
                 leaf ds3-alarm-ferf {
                   type empty;
                   description "Far-end receive failure alarm";
                 }
                 leaf ds3-alarm-ylw {
                   type empty;
                   description "Yellow alarm";
                 }
                 leaf ds3-alarm-idle {
                   type empty;
                   description "Idle alarm";
                 }
                 leaf ds1-alarm-ais {
                   type empty;
                   description "AIS alarm";
                 }
                 leaf ds1-alarm-lof {
                   type empty;
                   description "Loss of frame alarm";
                 }
                 leaf ds1-alarm-los {
                   type empty;
                   description "Loss of signal alarm";
                 }
                 leaf ds1-alarm-ylw {
                   type empty;
                   description "Yellow alarm";
                 }
                 leaf ds1-alarm-crc-major {
                   type empty;
                   description "CRC errors crossed major threshold";
                 }
                 leaf ds1-alarm-crc-minor {
                   type empty;
                   description "CRC errors crossed minor threshold";
                 }
                 leaf dsl-alarm-lof {
                   type empty;
                   description "Loss of frame alarm";
                 }
                 leaf dsl-alarm-los {
                   type empty;
                   description "Loss of signal alarm";
                 }
                 leaf dsl-alarm-lom {
                   type empty;
                   description "Loss of multiframe alarm";
                 }
                 leaf dsl-alarm-locdi {
                   type empty;
                   description "Loss of cell delineation alarm for interleaved channel";
                 }
                 leaf dsl-alarm-locdni {
                   type empty;
                   description "Loss of cell delineation alarm for non-interleaved channel";
                 }
                 leaf dsl-alarm-lop {
                   type empty;
                   description "Loss of power alarm";
                 }
                 leaf dsl-alarm-far-lof {
                   type empty;
                   description "Far-end loss-of-frame alarm";
                 }
                 leaf dsl-alarm-far-los {
                   type empty;
                   description "Far-end loss-of-signal alarm";
                 }
                 leaf dsl-alarm-far-locdi {
                   type empty;
                   description "Far-end loss-of-cell-delineation alarm for interleaved channel";
                 }
                 leaf dsl-alarm-far-locdni {
                   type empty;
                   description "Far-end loss-of-cell-delineation alarm for non-interleaved channel";
                 }
                 leaf fibrechannel-alarm-link-down {
                   type empty;
                   description "Link alive failure";
                 }
                 leaf ethernet-alarm-link-down {
                   type empty;
                   description "Link alive failure";
                 }
                 leaf ethernet-alarm-link-local-fault {
                   type empty;
                   description "Link local fault";
                 }
                 leaf ethernet-alarm-link-remote-fault {
                   type empty;
                   description "Link remote fault";
                 }
                 leaf ethernet-alarm-lcdp {
                   type empty;
                   description "Loss of code-group delineation";
                 }
                 leaf isdn-alarm-los {
                   type empty;
                   description "Loss of signal alarm";
                 }
                 leaf isdn-alarm-lof {
                   type empty;
                   description "Loss of frame alarm";
                 }
                 leaf shdsl-alarm-losd {
                   type empty;
                   description "Loss of signal alarm";
                 }
                 leaf shdsl-alarm-losw {
                   type empty;
                   description "Loss of sync word alarm";
                 }
                 leaf shdsl-alarm-line1-losd {
                   type empty;
                   description "Loss of signal (line 1) alarm";
                 }
                 leaf shdsl-alarm-line1-losw {
                   type empty;
                   description "Loss of sync word (line 1) alarm";
                 }
                 leaf shdsl-alarm-line2-losd {
                   type empty;
                   description "Loss of signal (line 2) alarm";
                 }
                 leaf shdsl-alarm-line2-losw {
                   type empty;
                   description "Loss of sync word (line 2) alarm";
                 }
                 leaf shdsl-efm-alarm-losd {
                   type empty;
                   description "Loss of signal alarm";
                 }
                 leaf shdsl-efm-alarm-losw {
                   type empty;
                   description "Loss of sync word alarm";
                 }
                 leaf otn-alarm-los {
                   type empty;
                   description "Loss of signal alarm";
                 }
                 leaf otn-alarm-lof {
                   type empty;
                   description "Loss of frame alarm";
                 }
                 leaf otn-alarm-lom {
                   type empty;
                   description "Loss of multiframe alarm";
                 }
                 leaf otn-alarm-wavelength-lock {
                   type empty;
                   description "Loss of Wavelength Lock alarm";
                 }
                 leaf otn-alarm-otu-ais {
                   type empty;
                   description "OTU Alarm Indication Signal alarm";
                 }
                 leaf otn-alarm-otu-bdi {
                   type empty;
                   description "OTU Background Block Error alarm";
                 }
                 leaf otn-alarm-otu-ttim {
                   type empty;
                   description "OTU Trail Trace Identifier Mismatch alarm";
                 }
                 leaf otn-alarm-otu-iae {
                   type empty;
                   description "OTU Incoming Alignment alarm";
                 }
                 leaf otn-alarm-otu-sd {
                   type empty;
                   description "OTU Signal Degrade alarm";
                 }
                 leaf otn-alarm-otu-sf {
                   type empty;
                   description "OTU Signal Fail alarm";
                 }
                 leaf otn-alarm-otu-biae {
                   type empty;
                   description "OTU Backward Incoming Alignment alarm";
                 }
                 leaf otn-alarm-otu-tsf {
                   type empty;
                   description "OTU Trail Signal Fail alarm";
                 }
                 leaf otn-alarm-otu-ssf {
                   type empty;
                   description "OTU Server Signal Fail alarm";
                 }
                 leaf otn-alarm-otu-fec-excessive {
                   type empty;
                   description "OTU FEC Excessive alarm";
                 }
                 leaf otn-alarm-otu-fec-degraded {
                   type empty;
                   description "OTU FEC Degraded alarm";
                 }
                 leaf otn-alarm-otu-fe-fec-degraded {
                   type empty;
                   description "OTU FE FEC Degraded/Excessive alarm";
                 }
                 leaf otn-alarm-otu-threshold-bbe {
                   type empty;
                   description "OTU Background Block Error threshold alarm";
                 }
                 leaf otn-alarm-otu-threshold-es {
                   type empty;
                   description "OTU Errored Seconds threshold alarm";
                 }
                 leaf otn-alarm-otu-threshold-ses {
                   type empty;
                   description "OTU Severely Errored Seconds threshold alarm";
                 }
                 leaf otn-alarm-otu-threshold-uas {
                   type empty;
                   description "OTU Unavailable Seconds threshold alarm";
                 }
                 leaf otn-alarm-odu-ais {
                   type empty;
                   description "ODU  Alarm Indiaction Signal alarm";
                 }
                 leaf otn-alarm-odu-oci {
                   type empty;
                   description "ODU Open Connection Indication alarm";
                 }
                 leaf otn-alarm-odu-lck {
                   type empty;
                   description "ODU Locked alarm";
                 }
                 leaf otn-alarm-odu-bdi {
                   type empty;
                   description "ODU Backward Defect Indication alarm";
                 }
                 leaf otn-alarm-odu-ttim {
                   type empty;
                   description "ODU Trail Trace Identifier Mismatch alarm";
                 }
                 leaf otn-alarm-odu-sd {
                   type empty;
                   description "ODU Signal Degrade alarm";
                 }
                 leaf otn-alarm-odu-sf {
                   type empty;
                   description "ODU Signal Fail alarm";
                 }
                 leaf otn-alarm-odu-iae {
                   type empty;
                   description "ODU Incoming Alignment alarm";
                 }
                 leaf otn-alarm-odu-ltc {
                   type empty;
                   description "ODU Loss of Tandem Connection alarm";
                 }
                 leaf otn-alarm-odu-csf {
                   type empty;
                   description "ODU Client Signal Fail alarm";
                 }
                 leaf otn-alarm-odu-tsf {
                   type empty;
                   description "ODU Trail Signal Fail alarm";
                 }
                 leaf otn-alarm-odu-ssf {
                   type empty;
                   description "ODU Server Signal Fail alarm";
                 }
                 leaf otn-alarm-odu-rx-aps-change {
                   type empty;
                   description "ODU Rx Aps Change alarm";
                 }
                 leaf otn-alarm-odu-threshold-bbe {
                   type empty;
                   description "ODU Background Block Error threshold alarm";
                 }
                 leaf otn-alarm-odu-threshold-es {
                   type empty;
                   description "ODU Errored Seconds threshold alarm";
                 }
                 leaf otn-alarm-odu-threshold-ses {
                   type empty;
                   description "ODU Severely Errored Seconds threshold alarm";
                 }
                 leaf otn-alarm-odu-threshold-uas {
                   type empty;
                   description "ODU Unavailable Seconds threshold alarm";
                 }
                 leaf otn-alarm-opu-pmi {
                   type empty;
                   description "OPU Payload Mismatch alarm";
                 }
                 leaf otn-alarm-pre-fec-sd {
                   type empty;
                   description "Pre-FEC SD alarm";
                 }
                 leaf otn-alarm-fe-pre-fec-sd {
                   type empty;
                   description "Far end pre-FEC SD alarm";
                 }
                 leaf optics-alarms-mod-fault {
                   type empty;
                   description "Module Fault alarm";
                 }
                 leaf optics-alarms-lol {
                   type empty;
                   description "Loss of Lock alarm";
                 }
                 leaf optics-alarms-los {
                   type empty;
                   description "Loss of Signal alarms";
                 }
                 leaf optics-alarms-lof {
                   type empty;
                   description "Loss of frame alarm";
                 }
                 leaf optics-alarms-lom {
                   type empty;
                   description "Loss of multi-frame alarm";
                 }
                 leaf optics-alarms-otu-bdi {
                   type empty;
                   description "Backward defect indiacation alarm";
                 }
                 leaf optics-alarms-rmsf {
                   type empty;
                   description "Rx Modem sysnc fault alarm";
                 }
                 leaf optics-alarms-rmlol {
                   type empty;
                   description "Rx Modem loss of lock alarm";
                 }
                 leaf optics-alarms-rloa {
                   type empty;
                   description "Rx loss of alignment alarm";
                 }
                 leaf optics-alarms-mbclf {
                   type empty;
                   description "Modulator Bias control loop fail alarm";
                 }
                 leaf optics-alarms-itlaf {
                   type empty;
                   description "ITLA Fault alarm";
                 }
                 leaf optics-alarms-daccf {
                   type empty;
                   description "DAC Calibration Fault alarm";
                 }
                 leaf optics-alarms-adccf {
                   type empty;
                   description "ADC Calibration Fault alarm";
                 }
                 leaf optics-alarms-fec-degrade {
                   type empty;
                   description "FEC Degrade alarm";
                 }
                 leaf optics-alarms-fec-excessive {
                   type empty;
                   description "FEC Excessive alarm";
                 }
                 leaf optics-alarms-fe-fec-degrade {
                   type empty;
                   description "Far-end FEC Degrade alarm";
                 }
                 leaf optics-alarms-fe-fec-excessive {
                   type empty;
                   description "Far-end FEC Excessive alarm";
                 }
                 leaf ima-alarm-startup-fe {
                   type empty;
                   description "IMA group startup far-end alarm";
                 }
                 leaf ima-alarm-config-abort {
                   type empty;
                   description "IMA group config abort alarm";
                 }
                 leaf ima-alarm-config-abort-fe {
                   type empty;
                   description "IMA group config abort far-end alarm";
                 }
                 leaf ima-alarm-insufficient-links {
                   type empty;
                   description "IMA group insufficient links alarm";
                 }
                 leaf ima-alarm-insufficient-links-fe {
                   type empty;
                   description "IMA group insufficient links far-end alarm";
                 }
                 leaf ima-alarm-blocked {
                   type empty;
                   description "IMA group blocked alarm";
                 }
                 leaf ima-alarm-blocked-fe {
                   type empty;
                   description "IMA group blocked far-end alarm";
                 }
                 leaf ima-alarm-timing-mismatch {
                   type empty;
                   description "IMA group timing mismatch alarm";
                 }
                 leaf ima-alarm-version-mismatch {
                   type empty;
                   description "IMA group version mismatch alarm";
                 }
                 leaf ima-alarm-lif {
                   type empty;
                   description "IMA link loss of IMA frame alarm";
                 }
                 leaf ima-alarm-lods {
                   type empty;
                   description "IMA link out of delay synchronization alarm";
                 }
                 leaf ima-alarm-rdi {
                   type empty;
                   description "IMA link remote defect indicator alarm";
                 }
                 leaf ima-alarm-tx-misconnected {
                   type empty;
                   description "IMA link tx misconnected alarm";
                 }
                 leaf ima-alarm-rx-misconnected {
                   type empty;
                   description "IMA link rx misconnected alarm";
                 }
                 leaf ima-alarm-fault {
                   type empty;
                   description "IMA link fault alarm";
                 }
                 leaf ima-alarm-tx-unusable-fe {
                   type empty;
                   description "IMA link Tx unusable far-end alarm";
                 }
                 leaf ima-alarm-rx-unusable-fe {
                   type empty;
                   description "IMA link Tx unusable far-end alarm";
                 }
                 leaf generic-value {
                   type int32;
                   description "Hexadecimal value of unknown flag bits";
                 }
               }
             }
             container media-information {
               leaf media-type {
                 type string;
                 description "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description "Circuit Emulation counter information";
                 }
                 leaf ce-counter-packets {
                   type int32;
                   description "Circuit Emulation number of packets";
                 }
                 leaf ce-counter-bytes {
                   type int32;
                   description "Circuit Emulation number of bytes";
                 }
                 leaf ce-counter-count {
                   type int32;
                   description "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description "Number of feet";
               }
             }
             container shdsl-information {
               leaf shdsl-line-termination {
                 type string;
                 description "Line termination remote or central";
               }
               leaf shdsl-annex {
                 type string;
                 description "Type of SHDSL annex";
               }
               leaf shdsl-line-mode {
                 type string;
                 description "Two or four wire mode";
               }
               leaf shdsl-modem-status {
                 type string;
                 description "Status of the SHDSL modem";
               }
               leaf shdsl-bit-rate {
                 type int32;
                 description "Actual line rate";
               }
               leaf shdsl-last-fail-reason {
                 type string;
                 description "Reason for last line-open failure";
               }
               leaf shdsl-last-fail-code {
                 type int32;
                 description "Last line-open failure code";
               }
               leaf shdsl-framer-mode {
                 type string;
                 description "Framer mode used";
               }
               leaf shdsl-paf-status {
                 type string;
                 description "EFM PAF Status";
               }
               leaf shdsl-dying-gasp {
                 type string;
                 description "Dying gasp is enabled or disabled";
               }
               leaf shdsl-framer-sync-status {
                 type string;
                 description "Framer synchronization status";
               }
               leaf shdsl-chipset-version {
                 type int32;
                 description "Version number for the DSP/framer chip";
               }
               leaf shdsl-firmware-version {
                 type string;
                 description "Transreceiver firmware release number";
               }
               container shdsl-statistics {
                 leaf shdsl-loop-attenuation {
                   type int32;
                   description "An estimate of the loop attenuation";
                 }
                 leaf shdsl-transmit-power {
                   type int32;
                   description "Nominal transmit power";
                 }
                 leaf shdsl-receiver-gain {
                   type int32;
                   description "Total receiver gain";
                 }
                 leaf shdsl-snr-sampling {
                   type int32;
                   description "Received signal to noise ratio";
                 }
                 leaf shdsl-rx-cells {
                   type int32;
                   description "Total ATM cells received";
                 }
                 leaf shdsl-tx-cells {
                   type int32;
                   description "Total ATM cells transmitted";
                 }
                 leaf shdsl-crc {
                   type int32;
                   description "Number of CRC errors";
                 }
                 leaf shdsl-sega {
                   type int32;
                   description "Number of SEGA errors";
                 }
                 leaf shdsl-losw {
                   type int32;
                   description "Number of LOSW  errors";
                 }
                 leaf shdsl-hec {
                   type int32;
                   description "Header error check errors";
                 }
                 leaf shdsl-cell-drop {
                   type int32;
                   description "Cells dropped because of errors";
                 }
               }
             }
           }
         }
         container atm-information {
           leaf atm-hcs-state {
             type string;
           }
           leaf atm-loss-of-cell {
             type string;
           }
           container plcp-defects {
             list media-alarm {
               leaf media-alarm-name {
                 type string;
               }
               leaf media-alarm-seconds {
                 type int32;
               }
               leaf media-alarm-count {
                 type int32;
               }
               leaf media-alarm-state {
                 type string;
               }
             }
           }
           container atm-defects {
             list media-alarm {
               leaf media-alarm-name {
                 type string;
               }
               leaf media-alarm-seconds {
                 type int32;
               }
               leaf media-alarm-count {
                 type int32;
               }
               leaf media-alarm-state {
                 type string;
               }
             }
           }
           container plcp-statistics {
             leaf ferr-count {
               type int32;
             }
             leaf ferr-seconds {
               type int32;
             }
             leaf bipe-count {
               type int32;
             }
             leaf bipe-seconds {
               type int32;
             }
             leaf febe-count {
               type int32;
             }
             leaf febe-seconds {
               type int32;
             }
           }
           container atm-statistics {
             leaf uncorrectable-hcs-errors {
               type int32;
             }
             leaf correctable-hcs-errors {
               type int32;
             }
             leaf tx-cell-fifo-overruns {
               type int32;
             }
             leaf rx-cell-fifo-overruns {
               type int32;
             }
             leaf rx-cell-fifo-underruns {
               type int32;
             }
             leaf rx-cell-count {
               type int32;
             }
             leaf tx-cell-count {
               type int32;
             }
             leaf tx-idle-cell-count {
               type int32;
             }
             leaf vc-queue-drops {
               type int32;
             }
             leaf no-buffers {
               type int32;
             }
             leaf length-errors {
               type int32;
             }
             leaf timeouts {
               type int32;
             }
             leaf bundle-timeouts {
               type int32;
             }
             leaf rx-invalid-vcs {
               type int32;
             }
             leaf bad-crcs {
               type int32;
             }
             leaf oam-cell-no-buffers {
               type int32;
             }
           }
         }
         container modem-information {
           leaf modem-type {
             type string;
             description "Modem type information";
           }
           leaf init-command-str {
             type string;
             description "Modem initialization command string";
           }
           leaf init-status {
             type string;
             description "Modem initialization status";
           }
           leaf call-status {
             type string;
             description "Current status of call";
           }
           leaf call-duration {
             type int32;
             description "Duration for which call has been on";
           }
           leaf call-direction {
             type string;
             description "Direction of call (incoming or outgoing)";
           }
           leaf baud-rate {
             type int32;
             description "Modem baud rate";
           }
           leaf error-code {
             type string;
             description "Error string as returned by modem";
           }
         }
         container serial-information {
           leaf dce-loopback-override {
             type string;
           }
           container line-protocol {
             leaf line-protocol-mode {
               type string;
             }
           }
           container resync-history {
             leaf resync-counter {
               type int32;
             }
             leaf resync-timestamp {
               type string;
             }
           }
           container clocking-mode {
             leaf clock-mode {
               type string;
             }
           }
           container clocking-rate {
             leaf clock-rate {
               type string;
               description "Interface clock rate";
             }
           }
           container serial-encoding {
             leaf serial-encoding-conf {
               type string;
             }
           }
           container dtr-circuit {
             leaf dtr-circuit-mode {
               type string;
             }
           }
           container eia530-signal-polarity {
             leaf dtr-polarity {
               type string;
             }
             leaf rts-polarity {
               type string;
             }
             leaf dcd-polarity {
               type string;
             }
             leaf dsr-polarity {
               type string;
             }
             leaf cts-polarity {
               type string;
             }
             leaf tm-polarity {
               type string;
             }
           }
           container x21-signal-polarity {
             leaf rts-polarity {
               type string;
             }
             leaf cts-polarity {
               type string;
             }
           }
           container serial-loopback {
             leaf serial-loopback-mode {
               type string;
             }
           }
           container tx-clock {
             leaf tx-clock-mode {
               type string;
             }
           }
           container data-signal {
             leaf rx-clock {
               type string;
             }
           }
           container eia530-control-signal {
             leaf eia530-mode {
               type string;
             }
             container to-dce {
               leaf dtr {
                 type string;
               }
               leaf rts {
                 type string;
               }
               leaf cts {
                 type string;
               }
               leaf dcd {
                 type string;
               }
               leaf dsr {
                 type string;
               }
             }
             container from-dce {
               leaf dtr {
                 type string;
               }
               leaf rts {
                 type string;
               }
               leaf cts {
                 type string;
               }
               leaf dcd {
                 type string;
               }
               leaf dsr {
                 type string;
               }
               leaf tm {
                 type string;
               }
             }
             container to-dte {
               leaf dtr {
                 type string;
               }
               leaf rts {
                 type string;
               }
               leaf cts {
                 type string;
               }
               leaf dcd {
                 type string;
               }
               leaf dsr {
                 type string;
               }
             }
             container from-dte {
               leaf dtr {
                 type string;
               }
               leaf rts {
                 type string;
               }
               leaf cts {
                 type string;
               }
               leaf dcd {
                 type string;
               }
               leaf dsr {
                 type string;
               }
               leaf tm {
                 type string;
               }
             }
           }
           container x21-control-signal {
             leaf rts {
               type string;
             }
             leaf cts {
               type string;
             }
           }
         }
         container virtual-path-information {
           leaf vpi {
             type int32;
             description "Virtual path identifier";
           }
           leaf atm-tm-cbr {
             type empty;
             description "Constant bit rate";
           }
           leaf atm-tm-vbr {
             type empty;
             description "Variable bit rate";
           }
           leaf atm-tm-rtvbr {
             type empty;
             description "Real-time variable bit rate";
           }
           leaf peak {
             type int32;
           }
           leaf sustained {
             type int32;
           }
           leaf burst {
             type int32;
           }
           leaf queue-limit {
             type int32;
           }
           leaf down-time {
             type int32;
             description "Total down time for this circuit";
           }
           leaf last-down-time {
             type int32;
             description "Time elapsed since circuit last went down";
           }
           leaf cdvt {
             type int32;
           }
           container ifvp-flags {
             leaf ifvp-down {
               type empty;
             }
             leaf ifvp-none {
               type empty;
             }
             leaf ifvp-active {
               type empty;
             }
             leaf ifvp-closed {
               type empty;
             }
             leaf ifvp-oam {
               type empty;
             }
             leaf ifvp-shaping {
               type empty;
             }
             leaf ifvp-passiveoam {
               type empty;
             }
             leaf ifvp-tunnel {
               type empty;
             }
             leaf generic-value {
               type int32;
               description "Hexadecimal value of unknown flag bits";
             }
           }
           container oam-parameters {
             leaf period {
               type int32;
             }
             leaf up-count {
               type int32;
             }
             leaf down-count {
               type int32;
             }
           }
           container oam-statistics {
             leaf oam-total-received-count {
               type int32;
             }
             leaf oam-total-transmitted-count {
               type int32;
             }
             leaf oam-loopback-received-count {
               type int32;
             }
             leaf oam-loopback-transmitted-count {
               type int32;
             }
             leaf oam-loopback-received-last {
               type string;
             }
             leaf oam-loopback-transmitted-last {
               type string;
             }
             leaf oam-rdi-received-count {
               type int32;
             }
             leaf oam-rdi-transmitted-count {
               type int32;
             }
             leaf oam-rdi-received-last {
               type string;
             }
             leaf oam-rdi-transmitted-last {
               type string;
             }
             leaf oam-ais-received-count {
               type int32;
             }
             leaf oam-ais-transmitted-count {
               type int32;
             }
             leaf oam-ais-received-last {
               type string;
             }
             leaf oam-ais-transmitted-last {
               type string;
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             leaf name {
               type string;
               description "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container cds1-information {
           list interface-tx-queue {
             leaf name {
               type string;
               description "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container nxds0-information {
           list interface-tx-queue {
             leaf name {
               type string;
               description "Name of this item";
             }
             leaf bandwidth {
               type string;
             }
             leaf wrr {
               type string;
             }
             leaf output-packets {
               type int32;
             }
             leaf output-bytes {
               type int32;
             }
             leaf output-drops {
               type int32;
             }
             leaf output-errors {
               type int32;
             }
             leaf output-drops-bytes {
               type int32;
             }
           }
         }
         container dsu-information {
           leaf dsu-compatibility-mode {
             type string;
           }
           leaf dsu-scrambler {
             type string;
           }
           leaf dsu-subrate {
             type string;
           }
           leaf feac-loopback {
             type string;
           }
           leaf feac-response {
             type string;
           }
           leaf feac-count {
             type int32;
           }
         }
         container ds3-bert-information {
           leaf ds3-bert-period {
             type int32;
           }
           leaf ds3-bert-elapsed {
             type int32;
           }
           leaf ds3-bert-status {
             type string;
           }
           leaf ds3-bert-algorithm {
             type string;
           }
           leaf ds3-bert-induced-error-rate {
             type int32;
           }
           leaf ds3-bert-bit-count {
             type int32;
           }
           leaf ds3-bert-bit-count-overflow {
             type int32;
           }
           leaf ds3-bert-error-bit-count {
             type int32;
           }
           leaf ds3-bert-error-bit-count-overflow {
             type int32;
           }
           leaf ds3-bert-error-rate {
             type string;
           }
           leaf ds3-bert-los-status {
             type string;
           }
           leaf ds3-bert-los-count {
             type int32;
           }
           leaf ds3-bert-los-seconds {
             type int32;
           }
         }
         container e3-bert-information {
           leaf e3-bert-period {
             type int32;
           }
           leaf e3-bert-elapsed {
             type int32;
           }
           leaf e3-bert-status {
             type string;
           }
           leaf e3-bert-algorithm {
             type string;
           }
           leaf e3-bert-induced-error-rate {
             type int32;
           }
           leaf e3-bert-bit-count {
             type int32;
           }
           leaf e3-bert-bit-count-overflow {
             type int32;
           }
           leaf e3-bert-error-bit-count {
             type int32;
           }
           leaf e3-bert-error-bit-count-overflow {
             type int32;
           }
           leaf e3-bert-error-rate {
             type string;
           }
           leaf e3-bert-los-status {
             type string;
           }
           leaf e3-bert-los-count {
             type string;
           }
           leaf e3-bert-los-seconds {
             type string;
           }
         }
         container ds1-bert-information {
           leaf ds1-bert-period {
             type int32;
           }
           leaf ds1-bert-elapsed {
             type int32;
           }
           leaf ds1-bert-status {
             type string;
           }
           leaf ds1-bert-induced-error-rate {
             type int32;
           }
           leaf ds1-bert-algorithm {
             type string;
           }
           leaf ds1-bert-bit-count {
             type int32;
           }
           leaf ds1-bert-error-bit-count {
             type int32;
           }
           leaf ds1-bert-error-rate {
             type string;
           }
           leaf ds1-bert-los-status {
             type string;
           }
           leaf ds1-bert-los-count {
             type int32;
           }
           leaf ds1-bert-los-seconds {
             type int32;
           }
         }
         container ds0-bert-information {
           leaf ds0-bert-period {
             type int32;
           }
           leaf ds0-bert-elapsed {
             type int32;
           }
           leaf ds0-bert-status {
             type string;
           }
           leaf ds0-bert-induced-error-rate {
             type int32;
           }
           leaf ds0-bert-algorithm {
             type string;
           }
           leaf ds0-bert-bit-count {
             type int32;
           }
           leaf ds0-bert-error-bit-count {
             type int32;
           }
           leaf ds0-bert-error-rate {
             type string;
           }
           leaf ds0-bert-los-status {
             type string;
           }
           leaf ds0-bert-los-count {
             type int32;
           }
           leaf ds0-bert-los-seconds {
             type int32;
           }
         }
         container hdlc-information {
           leaf hdlc-rx-bucket-state {
             type string;
           }
           leaf hdlc-rx-bit-rate {
             type int32;
           }
           leaf hdlc-rx-threshold {
             type int32;
           }
           leaf hdlc-tx-bucket-state {
             type string;
           }
           leaf hdlc-tx-bit-rate {
             type int32;
           }
           leaf hdlc-tx-threshold {
             type int32;
           }
           leaf hdlc-giant-threshold {
             type int32;
           }
           leaf hdlc-runt-threshold {
             type int32;
           }
         }
         container pfe-information {
           leaf destination-slot {
             type int32;
           }
           leaf destination-mask {
             type int32;
           }
           leaf stream-number {
             type int32;
           }
           leaf stream-mask {
             type int32;
           }
           leaf plp-byte-count {
             type int32;
           }
           leaf plp-byte {
             type string;
           }
           leaf pop-all-label {
             type string;
           }
         }
         list logical-interface {
           leaf lcp-state {
             type string;
             description "State of the Line Control Protocol";
           }
           leaf chap-state {
             type string;
             description "State of the Challenge Handshake Authentication Protocol";
           }
           leaf pap-state {
             type string;
             description "State of the Password Authentication Protocol";
           }
           leaf name {
             type string;
             description "Name of this item";
           }
           leaf local-index {
             type int32;
             description "Local kernel index for this interface";
           }
           leaf snmp-index {
             type int32;
             description "SNMP ifIndex for this interface";
           }
           leaf hardware-token {
             type int32;
             description "Hardware token for layer 3 ifl";
           }
           leaf generation {
             type int32;
             description "Generation number used to distinguish between successive instances of this interface";
           }
           leaf description {
             type string;
             description "Description of this interface";
           }
           leaf multilink-flapped {
             type string;
             description "Time when the interface last flapped";
           }
           leaf logical-interface-bandwidth {
             type string;
             description "Bandwidth of this logical interface";
           }
           leaf link-address {
             type string;
             description "Link address on this logical interface";
           }
           leaf encapsulation {
             type string;
             description "Encapsulation on the logical interface";
           }
           leaf esi-value {
             type string;
             description "Ethernet segment identifier for this interface";
           }
           leaf esi-mode {
             type string;
             description "Ethernet segment mode for this interface";
           }
           leaf evpn-multihomed-status {
             type string;
           }
           leaf virtual-gateway-esi-value {
             type string;
             description "Ethernet segment identifier for this interface";
           }
           leaf virtual-gateway-esi-mode {
             type string;
             description "Ethernet segment mode for this interface";
           }
           leaf interface-set-name {
             type string;
             description "Class-of-service interface-set name";
           }
           leaf tenant-name {
             type string;
             description "Tenant name assigned to logical interface";
           }
           leaf demux-table-type {
             type string;
             description "Demux table enabled on the logical interface";
           }
           leaf gre-keepalive-configured {
             type string;
             description "Gre Keepalives enabled on the logical interface";
           }
           leaf gre-keepalive-adj-state {
             type string;
             description "Gre Keepalives enabled on the logical interface";
           }
           leaf copy-tos-to-outer-ip-header {
             type string;
             description "Flag that enables copying of the value in the ToS field of the IP packet's payload header to the delivery header in the generic routingencapsulation packet";
           }
           leaf copy-tos-to-outer-ip-header-transit {
             type string;
             description "Flag that enables copying of the value in the ToS field of the IP packet's payload header to the delivery header in the generic routing encapsulation transit packet";
           }
           leaf redundant-logical-interface-name {
             type string;
             description "Name of the redundant logical interface";
           }
           leaf logical-interface-mac {
             type string;
             description "MAC on the logical interface";
           }
           leaf logical-interface-vgw-v4-mac {
             type string;
             description "MAC on the logical interface";
           }
           leaf logical-interface-vgw-v6-mac {
             type string;
             description "MAC on the logical interface";
           }
           leaf vrfname {
             type string;
             description "Routing instance name";
           }
           leaf zonename {
             type string;
             description "Zone name";
           }
           leaf subunit {
             type int32;
             description "Subunit for this interface";
           }
           leaf dialer-time-to-disconnect {
             type string;
             description "Time for dialer to disconnect due to idle timeout";
           }
           container if-config-flags {
             leaf iff-none {
               type empty;
             }
             leaf iff-hardware-down {
               type empty;
             }
             leaf iff-down {
               type empty;
             }
             leaf iff-up {
               type empty;
             }
             leaf iff-admin-down {
               type empty;
             }
             leaf iff-admin-up {
               type empty;
             }
             leaf iff-link-down {
               type empty;
             }
             leaf iff-device-down {
               type empty;
             }
             leaf iff-point-to-point {
               type empty;
             }
             leaf iff-point-to-multipoint {
               type empty;
             }
             leaf plp-to-clp {
               type empty;
             }
             leaf iff-multiaccess {
               type empty;
             }
             leaf iff-change {
               type empty;
             }
             leaf iff-inverse-arp {
               type empty;
             }
             leaf iff-no-multicast {
               type empty;
             }
             leaf iff-multicast {
               type empty;
             }
             leaf iff-promiscuous {
               type empty;
             }
             leaf iff-all-multicast {
               type empty;
             }
             leaf iff-snmp-traps {
               type empty;
             }
             leaf iff-rx-passive {
               type empty;
             }
             leaf iff-tx-passive {
               type empty;
             }
             leaf iff-ccc-down {
               type empty;
             }
             leaf iff-clear-df {
               type empty;
             }
             leaf iff-tunnel-reassembly {
               type empty;
             }
             leaf iff-acfc {
               type empty;
             }
             leaf iff-pfc {
               type empty;
             }
             leaf iff-rdd {
               type empty;
             }
             leaf iff-looped {
               type empty;
             }
             leaf iff-framing-conflict {
               type empty;
             }
             leaf internal-flags {
               type int32;
               description "Hexadecimal value of internal flag bits";
             }
           }
           container layer2-input-policer-information {
             leaf layer2-input-policer {
               type string;
               description "Name of the Layer 2 input policer";
             }
           }
           container layer2-output-policer-information {
             leaf layer2-output-policer {
               type string;
               description "Name of the Layer 2 output policer";
             }
           }
           container atm-input-policer-information {
             leaf atm-input-policer {
               type string;
               description "Name of the atm input policer";
             }
           }
           container pppoe-information {
             list pppoe-interface {
               leaf state {
                 type string;
                 description "State";
               }
               leaf session-id {
                 type string;
                 description "Session ID";
               }
               leaf ac-name-session {
                 type string;
                 description "Session AC name";
               }
               leaf remote-mac {
                 type string;
                 description "Remote MAC address";
               }
               leaf ac-name-config {
                 type string;
                 description "Configured AC name";
               }
               leaf service-name {
                 type string;
                 description "Service name";
               }
               leaf auto-reconnect {
                 type string;
                 description "Autoreconnect timeout";
               }
               leaf idle-timeout {
                 type string;
                 description "Idle timeout";
               }
               leaf underlying-interface-name {
                 type string;
                 description "Underlying interface name";
               }
               leaf underlying-interface-index {
                 type string;
                 description "Underlying interface index";
               }
               leaf padg-credits {
                 type int32;
                 description "PADG transmit credits";
               }
               leaf pppoe-credit-scale-factor {
                 type string;
                 description "Scaling factor";
               }
               leaf ignore-eol-tag {
                 type string;
                 description "Ignore End-of-List TAG";
               }
               leaf ppp-max-payload-tag {
                 type int32;
                 description "PPP-Max-Payload TAG";
               }
               leaf interface-name {
                 type string;
                 description "Class-of-service interface name";
               }
               leaf interface-index {
                 type uint32;
                 description "Class-of-service interface index";
               }
               leaf aci-iflset-name {
                 type string;
                 description "ACI Interface Set name";
               }
               leaf aci-iflset-index {
                 type string;
                 description "ACI Interface Set index";
               }
               leaf ifl-type {
                 type string;
                 description "Type";
               }
               leaf session-uptime {
                 type string;
                 description "Duration for which the session has been up";
               }
               leaf dynamic-profile {
                 type string;
                 description "Dynamic Profile name";
               }
               leaf pppoe-credits {
                 type string;
                 description "Forwarding credit balances";
               }
               leaf dynamic-interface-bandwidth {
                 type string;
                 description "Dynamic interface bandwidth";
               }
               leaf agent-circuit-id {
                 type string;
                 description "Agent Circuit ID";
               }
               leaf agent-remote-id {
                 type string;
                 description "Agent Remote ID";
               }
               leaf padm-motm {
                 type string;
                 description "PADM Message of the Moment tag";
               }
               leaf padm-hurl {
                 type string;
                 description "PADM HTTP URL tag";
               }
             }
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           container aci-vlan-information {
             leaf dynamic-profile {
               type string;
               description "Dynamic Profile name";
             }
           }
           container line-identity-information {
             leaf dynamic-profile {
               type string;
               description "Dynamic Profile name";
             }
             leaf circuit-id {
               type string;
               description "Aci vlan attribute";
             }
             leaf remote-id {
               type string;
               description "Aci vlan attribute";
             }
             leaf accept-no-ids {
               type string;
               description "Aci vlan attribute";
             }
           }
           container demux-information {
             container demux-interface {
               leaf demux-underlying-interface-name {
                 type string;
                 description "Underlying interface name";
               }
               leaf demux-underlying-interface-index {
                 type string;
                 description "Underlying interface index";
               }
               leaf demux-inet-prefix-type {
                 type string;
                 description "Prefix type";
               }
               leaf demux-inet-prefix-count {
                 type string;
                 description "IPv4 Prefix count";
               }
               leaf demux-inet-prefix {
                 type string;
                 description "IPv4 Prefix";
               }
               leaf demux-inet6-prefix-type {
                 type string;
                 description "Prefix type";
               }
               leaf demux-inet6-prefix-count {
                 type string;
                 description "IPv6 Prefix count";
               }
               leaf demux-inet6-prefix {
                 type string;
                 description "IPv6 Prefix";
               }
             }
           }
           container dual-ad-icl-color-information {
             container dual-ad-icl-color-info {
               leaf dual-ad-icl-color-type {
                 type uint32;
                 description "Dual-AD ICL Color Type";
               }
               leaf dual-ad-icl-color {
                 type uint32;
                 description "Dual-AD ICL Color";
               }
             }
           }
           container dialer-information {
             leaf dialer-time-to-disconnect {
               type string;
               description "Time for dialer to disconnect due to idle timeout";
             }
             container dialer-interface {
               leaf dialer-interface-name {
                 type string;
                 description "Interface name";
               }
               leaf dialer-interface-state {
                 type string;
                 description "Dialer interface state";
               }
               leaf pool-id {
                 type string;
                 description "Pool identifier";
               }
               leaf primary-interface {
                 type string;
                 description "Primary interface";
               }
               leaf activation-delay {
                 type string;
                 description "Activation delay";
               }
               leaf deactivation-delay {
                 type string;
                 description "Deactivation delay";
               }
               leaf activation-delay-elapsed {
                 type string;
                 description "Activation delay elapsed";
               }
               leaf deactivation-delay-elapsed {
                 type string;
                 description "Deactivation delay elapsed";
               }
               leaf call-idle-timeout {
                 type string;
                 description "Call idle timeout";
               }
               leaf initial-route-check {
                 type string;
                 description "Initial route check delay";
               }
               leaf redial-delay {
                 type string;
                 description "Delay before dialer dials out again (seconds)";
               }
               leaf callback-wait-period {
                 type string;
                 description "Delay before dialer attempts callback (seconds)";
               }
               leaf callback-wait-period-elapsed {
                 type string;
                 description "Number of seconds in callback wait period that have elapsed";
               }
               leaf load-threshold {
                 type string;
                 description "Load threshold that determines when interfaces are added to bundle";
               }
               leaf load-interval {
                 type string;
                 description "Interval over which average load is calculated";
               }
               container dialer-interface-flags {
                 leaf backup {
                   type empty;
                   description "Dialer backup";
                 }
                 leaf multilink {
                   type empty;
                   description "Dialer multilink";
                 }
                 leaf watchlist {
                   type empty;
                   description "Dialer watchlist";
                 }
                 leaf interesting-detected {
                   type empty;
                   description "Interesting packet detected";
                 }
               }
             }
           }
           container shared-interface-information {
             container shared-interface-logical-interface {
               leaf peer-interface-name {
                 type string;
                 description "Peer interface name";
               }
               leaf interface-shared-with {
                 type string;
                 description "Logical interface owner";
               }
               leaf rx-fe {
                 type string;
                 description "Rx tunnel token forwarding element";
               }
               leaf rx-nhid {
                 type string;
                 description "Rx tunnel token next hop index";
               }
               leaf tx-fe {
                 type string;
                 description "Tx tunnel token forwarding element";
               }
               leaf tx-nhid {
                 type string;
                 description "Tx tunnel token next hop index";
               }
             }
           }
           container mac-database {
             leaf number-of-mac-record {
               type int32;
             }
             list mac-record {
               leaf mac-address {
                 type jt:mac-addr;
               }
               leaf receive-frames {
                 type int32;
               }
               leaf receive-bytes {
                 type int32;
               }
               leaf transmit-frames {
                 type int32;
               }
               leaf transmit-bytes {
                 type int32;
               }
             }
           }
           container policer-overhead {
             leaf ingress-policer-overhead {
               type int32;
               description "Ingress policer overhead information";
             }
             leaf egress-policer-overhead {
               type int32;
               description "Egress policer overhead information";
             }
           }
           container queue-counters {
             leaf queue-counters-error-message {
               type string;
               description "Queue statistics not available for this interface";
             }
             list queue {
               leaf queue-number {
                 type int32;
                 description "Queue number";
               }
               leaf queue-counters-queued-packets {
                 type uint64;
                 description "Queued packet count";
               }
               leaf queue-counters-trans-packets {
                 type uint64;
                 description "Total number of transmitted packets";
               }
               leaf queue-counters-total-drop-packets {
                 type uint64;
                 description "Number of total packets dropped at the queue";
               }
               leaf forwarding-class-name {
                 type string;
                 description "Forwarding class name associated with queue";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
           }
           container ingress-queue-counters {
             list queue {
               leaf queue-number {
                 type int32;
                 description "Queue number";
               }
               leaf forwarding-class-name {
                 type string;
                 description "Forwarding class name associated with queue";
               }
               leaf queue-counters-queued-packets {
                 type uint64;
                 description "Queued packet count";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets {
                 type uint64;
                 description "Total number of transmitted packets";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets {
                 type uint64;
                 description "Number of total packets dropped at the queue";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container queue-num-forwarding-class-name-map {
               leaf queue-number {
                 type int32;
                 description "Queue number";
               }
               leaf forwarding-class-name {
                 type string;
                 description "Forwarding class name associated with queue";
               }
             }
           }
           container forwarding-class-counters {
             leaf forwarding-class-counters-error-message {
               type string;
               description "Forwarding-class statistics not available for this interface";
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
             container ipv4-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
           }
           container multilink-bundle-link-information {
             leaf multilink-active-bundle-links {
               type int32;
               description "Number of active bundle links in this multilink bundle instance";
             }
             leaf multilink-removed-bundle-links {
               type int32;
               description "Number of bundle links that are removed from service in this multilink bundle instance";
             }
             leaf multilink-disabled-bundle-links {
               type int32;
               description "Number of bundle links that are not allowed to transmit in this multilink bundle instance";
             }
           }
           container multilink-bundle-options {
             leaf mrru {
               type int32;
             }
             leaf remote-mrru {
               type int32;
               description "Remote max received reconstructed unit";
             }
             leaf drop-timeout {
               type int32;
             }
             leaf mlppp-inner-ppp-pfc {
               type string;
               description "MLPPP inner PPP protocol field compression";
             }
             leaf sequence-number-format {
               type string;
             }
             leaf ml-fragment-threshold {
               type int32;
             }
             leaf minimum-links {
               type int32;
             }
             leaf interleave-fragments {
               type string;
             }
             leaf multilink-classes {
               type int32;
               description "Number of multilink classes";
             }
             leaf link-layer-overhead {
               type string;
               description "Link layer overhead";
             }
             leaf filler-packet-interval {
               type int32;
             }
           }
           container multilink-bundle-errors {
             leaf packet-drops {
               type int32;
               description "Number of packets dropped";
             }
             leaf packet-drop-bytes {
               type int32;
               description "Number of bytes in dropped packets";
             }
             leaf fragment-drops {
               type int32;
               description "Number of fragments dropped";
             }
             leaf fragment-drop-bytes {
               type int32;
               description "Number of bytes in dropped fragments";
             }
             leaf mrru-exceeded {
               type int32;
               description "Number of assembled packets that exceeded MRRU";
             }
             leaf processing-errors {
               type int32;
               description "Number of errors encountered in assembling packets";
             }
           }
           container multilink-traffic-statistics {
             container bundle {
               container multilink-frames {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-frames {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-v6-frames {
                 leaf inputv6-packets {
                   type int32;
                 }
                 leaf inputv6-bytes {
                   type int32;
                 }
                 leaf outputv6-packets {
                   type int32;
                 }
                 leaf outputv6-bytes {
                   type int32;
                 }
               }
             }
             container class {
               container class-info {
                 leaf multilink-class-id {
                   type int32;
                   description "Multilink class ID";
                 }
               }
               container multilink-frames {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container network-frames {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
             list link {
               leaf name {
                 type string;
                 description "Name of this item";
               }
               leaf down {
                 type empty;
                 description "Link is down";
               }
               leaf link-uptime {
                 type string;
                 description "Total uptime for the member link";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container multilink-detail-statistics {
               container bundle-detail {
                 container fragments {
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container non-fragments {
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container lfi {
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
               }
               container class-detail {
                 container class-info {
                   leaf multilink-class-id {
                     type int32;
                     description "Multilink class ID";
                   }
                 }
                 container fragments {
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
                 container non-fragments {
                   leaf input-frames {
                     type int32;
                   }
                   leaf input-fps {
                     type int32;
                   }
                   leaf input-bytes {
                     type int32;
                   }
                   leaf input-bps {
                     type int32;
                   }
                   leaf output-frames {
                     type int32;
                   }
                   leaf output-fps {
                     type int32;
                   }
                   leaf output-bytes {
                     type int32;
                   }
                   leaf output-bps {
                     type int32;
                   }
                 }
               }
             }
             container crtp {
               container crtp-sessions {
                 leaf input-frames {
                   type int32;
                 }
                 leaf output-frames {
                   type int32;
                 }
               }
               list crtp-statistics {
                 leaf name {
                   type string;
                   description "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container statistics-account-overhead {
             leaf ingress-account-overhead {
               type int32;
               description "Ingress Statistics account overhead information";
             }
             leaf egress-account-overhead {
               type int32;
               description "Egress Statistics account overhead information";
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             leaf multicast-statistics-header {
               type empty;
             }
             container ipv4-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             leaf input-bps {
               type int32;
             }
             leaf input-pps {
               type int32;
             }
             leaf input-drop-bps {
               type int32;
               description "Drop rate at ingress in bits per second ";
             }
             leaf input-drop-pps {
               type int32;
               description "Drop rate at ingress in packets per second ";
             }
             leaf input-bytes {
               type int32;
             }
             leaf input-packets {
               type int32;
             }
             leaf input-drop-bytes {
               type int32;
               description "Drop statistics at ingress in bytes";
             }
             leaf input-drop-packets {
               type int32;
               description "Drop statistics at ingress in packets";
             }
           }
           container local-traffic-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container transit-traffic-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
             container ipv6-transit-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-total-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container keepalive-config {
             leaf keepalive-interval {
               type int32;
             }
             leaf keepalive-up-count {
               type int32;
             }
             leaf keepalive-down-count {
               type int32;
             }
           }
           container keepalive-statistics {
             leaf keepalive-lmi-descriptor {
               type string;
             }
             leaf keepalive-input-count {
               type int32;
             }
             leaf keepalive-input-time {
               type string;
             }
             leaf keepalive-output-count {
               type int32;
             }
             leaf keepalive-output-time {
               type string;
             }
           }
           container ppp-flags {
             leaf iff-ppp-flags-acfc {
               type empty;
             }
             leaf iff-ppp-flags-pfc {
               type empty;
             }
           }
           list ncp-information {
             leaf ncp-protocol {
               type string;
               description "Network protocol for this NCP instance";
             }
             leaf ncp-state {
               type string;
               description "State of this NCP instance";
             }
           }
           container virtual-circuit-information {
             leaf vpi {
               type int32;
               description "Virtual path identifier";
             }
             leaf vci {
               type int32;
               description "Virtual circuit identifier";
             }
             leaf psn-tag {
               type string;
               description "VPI/VCI swapping configuration";
             }
             leaf psn-vpi {
               type int32;
               description "PSN virtual path identifier";
             }
             leaf psn-vci {
               type int32;
               description "PSN virtual circuit identifier";
             }
             leaf trunk {
               type int32;
               description "ATM trunk identifier";
             }
             leaf dlci {
               type int32;
             }
             leaf swapping {
               type string;
               description "VPI/VCI swapping configuration";
             }
             leaf trunk-bandwidth {
               type int32;
               description "ATM trunk bandwidth";
             }
             leaf atm-tm-cbr {
               type empty;
               description "Constant bit rate";
             }
             leaf atm-tm-vbr {
               type empty;
               description "Variable bit rate";
             }
             leaf atm-tm-rtvbr {
               type empty;
               description "Real-time variable bit rate";
             }
             leaf peak {
               type int32;
             }
             leaf sustained {
               type int32;
             }
             leaf burst {
               type int32;
             }
             leaf cdvt {
               type int32;
             }
             leaf queue-limit {
               type int32;
             }
             leaf down-time {
               type int32;
               description "Total down time for this circuit";
             }
             leaf last-down-time {
               type int32;
               description "Time elapsed since circuit last went down";
             }
             leaf ifvc-epd {
               type int32;
               description "Early packet discard threshold";
             }
             leaf ifvc-weight {
               type int32;
               description "Transmit weight";
             }
             leaf ifvc-epd-plp0 {
               type int32;
               description "Early packet discard threshold for PLP 0";
             }
             leaf ifvc-epd-plp1 {
               type int32;
               description "Early packet discard threshold for PLP 1";
             }
             container dlci-statistics {
               leaf dlci-active {
                 type int32;
                 description "Number of DLCIs in active state";
               }
               leaf dlci-inactive {
                 type int32;
                 description "Number of DLCIs in inactive state";
               }
             }
             container vci-range {
               leaf vpi {
                 type int32;
                 description "Virtual path identifier";
               }
               leaf start-vci {
                 type int32;
                 description "ATM VCI range's start value";
               }
               leaf end-vci {
                 type int32;
                 description "ATM VCI range's end value";
               }
             }
             container ifvc-flags {
               leaf ifvc-down {
                 type empty;
               }
               leaf ifvc-none {
                 type empty;
               }
               leaf ifvc-active {
                 type empty;
               }
               leaf ifvc-closed {
                 type empty;
               }
               leaf ifvc-inverse-arp {
                 type empty;
               }
               leaf ifvc-ilmi {
                 type empty;
               }
               leaf ifvc-oam {
                 type empty;
               }
               leaf ifvc-shaping {
                 type empty;
               }
               leaf ifvc-passiveoam {
                 type empty;
               }
               leaf ifvc-multicast {
                 type empty;
               }
               leaf ifvc-ccc-down {
                 type empty;
               }
               leaf ifvc-configured {
                 type empty;
                 description "DCE-end is configured";
               }
               leaf ifvc-unconfigured {
                 type empty;
                 description "DCE-end is unconfigured";
               }
               leaf generic-value {
                 type int32;
                 description "Hexadecimal value of unknown flag bits";
               }
             }
             container ifvc-multipoint-destination {
               leaf multipoint-address {
                 type string;
                 description "Protocol address of the remote side of this connection";
               }
             }
             container oam-parameters {
               leaf period {
                 type int32;
               }
               leaf up-count {
                 type int32;
               }
               leaf down-count {
                 type int32;
               }
             }
             container oam-statistics {
               leaf oam-total-received-count {
                 type int32;
               }
               leaf oam-total-transmitted-count {
                 type int32;
               }
               leaf oam-total-received-count-4 {
                 type int32;
               }
               leaf oam-total-transmitted-count-4 {
                 type int32;
               }
               leaf oam-loopback-received-count {
                 type int32;
               }
               leaf oam-loopback-transmitted-count {
                 type int32;
               }
               leaf oam-loopback-received-last {
                 type string;
               }
               leaf oam-loopback-transmitted-last {
                 type string;
               }
               leaf oam-rdi-received-count {
                 type int32;
               }
               leaf oam-rdi-transmitted-count {
                 type int32;
               }
               leaf oam-rdi-received-last {
                 type string;
               }
               leaf oam-rdi-transmitted-last {
                 type string;
               }
               leaf oam-ais-received-count {
                 type int32;
               }
               leaf oam-ais-transmitted-count {
                 type int32;
               }
               leaf oam-ais-received-last {
                 type string;
               }
               leaf oam-ais-transmitted-last {
                 type string;
               }
             }
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-policer-statistics {
               leaf non-conform-clp0-cells {
                 type int32;
                 description "UPC non-conforming ATM CLP0 cell";
               }
               leaf non-conform-clp1-cells {
                 type int32;
                 description "UPC non-conforming ATM CLP1 cell";
               }
               leaf tagged-cells {
                 type int32;
                 description "UPC tagged cell";
               }
             }
             container atm-statistics {
               leaf vc-queue-drops {
                 type int32;
               }
             }
             container atm-cos-information {
               leaf vc-cos-mode {
                 type string;
                 description "Virtual circuit CoS scheduling mode";
               }
               list atm-cos-queue {
                 container atm-cos-queue-parameters {
                   leaf cos-forwarding-class-name {
                     type string;
                     description "Forwarding class name associated with queue";
                   }
                   leaf cos-queue-number {
                     type int32;
                     description "Queue number";
                   }
                   leaf scheduling-priority {
                     type string;
                     description "Scheduling priority";
                   }
                   leaf transmit-weight-cells {
                     type int32;
                     description "Weight to apply to scheduling as number of cells";
                   }
                   leaf transmit-weight-percent {
                     type int32;
                     description "Weight to apply to scheduling as fill percentage";
                   }
                   leaf epd-threshold {
                     type int32;
                     description "Early packet drop threshold";
                   }
                   leaf epd-threshold-plp0 {
                     type int32;
                     description "Early packet drop threshold for PLP 0";
                   }
                   leaf epd-threshold-plp1 {
                     type int32;
                     description "Early packet drop threshold for PLP 1";
                   }
                   container linear-red-drop-profile {
                     leaf queue-depth {
                       type uint32;
                       description "Instantaneous queue depth";
                     }
                     leaf low-red {
                       type int32;
                       description "Fill level percentage when linear RED is applied for low PLP";
                     }
                     leaf high-red {
                       type int32;
                       description "Fill level percentage when linear RED is applied for high PLP";
                     }
                     leaf max-low-red {
                       type int32;
                       description "Fill level percentage with 100% packet drop for low PLP";
                     }
                     leaf max-high-red {
                       type int32;
                       description "Fill level percentage with 100% packet drop for high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
             container in-arp-statistics {
               leaf received-count {
                 type int32;
                 description "Number of ARPs received";
               }
               leaf transmitted-count {
                 type int32;
                 description "Number of ARPs sent";
               }
               leaf denied-count {
                 type int32;
                 description "Number of ARPs denied";
               }
               leaf operation-not-supported-count {
                 type int32;
                 description "Number of ARPs with operation not supported";
               }
               leaf bad-packet-length-count {
                 type int32;
                 description "Number of ARPs with bad packet length";
               }
               leaf bad-protocol-count {
                 type int32;
                 description "Number of ARPs with bad protocol";
               }
               leaf bad-protocol-length-count {
                 type int32;
                 description "Number of ARPs with bad protocol length";
               }
               leaf bad-hardware-length-count {
                 type int32;
                 description "Number of ARPs with bad hardware length";
               }
               leaf dropped-count {
                 type int32;
                 description "Number of ARPs dropped";
               }
               leaf last-received {
                 type string;
                 description "Time an ARP was last received";
               }
               leaf last-transmitted {
                 type string;
                 description "Time an ARP was last sent";
               }
             }
           }
           list filter-information {
             leaf-list filter-input {
               type string;
               description "Name of the input filter";
             }
             leaf-list filter-input-precedence {
               type uint32;
               description "Precedence of the input filter";
             }
             leaf-list filter-output {
               type string;
               description "Name of the output filter";
             }
             leaf-list filter-output-precedence {
               type uint32;
               description "Precedence of the output filter";
             }
           }
           list address-family {
             leaf compression-device-name {
               type string;
               description "Name of the link service device";
             }
             leaf address-family-name {
               type string;
             }
             leaf multilink-bundle-name {
               type string;
               description "Name of the multilink bundle for this address family";
             }
             leaf as-bundle-name {
               type string;
               description "Name of the aggregated SONET bundle for this address family";
             }
             leaf ae-bundle-name {
               type string;
               description "Name of the aggregated Ethernet bundle";
             }
             leaf es-sa-name {
               type string;
               description "Name of the IPSec security association for this address family";
             }
             leaf mtu {
               type string;
               description "MTU size on this interface";
             }
             leaf maximum-labels {
               type uint32;
               description "Maximum labels on MPLS iffamily";
             }
             leaf generation {
               type int32;
               description "Generation number used to distinguish between successive instances of this interface";
             }
             leaf route-table {
               type int32;
             }
             leaf vpls-mesh-group {
               type string;
             }
             leaf es-sa-fail-count {
               type int32;
               description "Number of failures for IPSec security association for this family";
             }
             leaf es-sa-xmt-seq-num {
               type int32;
               description "Transmit sequence number of IPSec security association family";
             }
             leaf es-sa-recv-seq-num {
               type int32;
               description "Receive sequence number of IPSec security association family";
             }
             leaf evpn-multihomed-status {
               type string;
             }
             leaf evpn-mh-esi-sh-label {
               type string;
             }
             leaf iff-next-hop {
               type int32;
               description "Interface family next-hop";
             }
             leaf iff-vpls-status {
               type string;
               description "Interface family vpls status";
             }
             leaf max-local-cache {
               type uint32;
               description "Max local nh cache size";
             }
             leaf new-hold-limit {
               type uint32;
               description "Max limit on new unresolved nh";
             }
             leaf intf-curr-cnt {
               type uint32;
               description "Current nh total cache size on this interface";
             }
             leaf intf-unresolved-cnt {
               type uint32;
               description "Current new unresolved nh cache size on this interface";
             }
             leaf intf-dropcnt {
               type uint32;
               description "Current interface nh drop count";
             }
             leaf mlppp-service-interface {
               type string;
               description "Name of the multilink service interface for this address family";
             }
             leaf mlppp-service-dev-pool {
               type string;
               description "Name of the multilink service device pool for this address family";
             }
             leaf mlppp-dynamic-profile {
               type string;
               description "Name of the multilink dynamic profile for this address family";
             }
             leaf arp-respond-any-local-address {
               type string;
               description "Respond to ARP requests for any local address";
             }
             leaf local-bias-information {
               type string;
             }
             leaf ft-iff-dest-port {
               type uint32;
               description "Destination UDP port to be used for this family";
             }
             container address-family-flags {
               leaf ifff-none {
                 type empty;
               }
               leaf ifff-primary {
                 type empty;
               }
               leaf ifff-redirects {
                 type empty;
               }
               leaf ifff-no-redirects {
                 type empty;
               }
               leaf ifff-no-neighbor-learn {
                 type empty;
               }
               leaf ifff-targeted-broadcast {
                 type empty;
               }
               leaf ifff-sendbcast-pkt-to-re {
                 type empty;
               }
               leaf ifff-hard-down {
                 type empty;
               }
               leaf ifff-down {
                 type empty;
               }
               leaf ifff-up {
                 type empty;
               }
               leaf ifff-func1 {
                 type empty;
               }
               leaf ifff-func2 {
                 type empty;
               }
               leaf ifff-is-primary {
                 type empty;
               }
               leaf ifff-recv-options {
                 type empty;
               }
               leaf ifff-recv-ttl-exceeded {
                 type empty;
               }
               leaf ifff-dst-class-usage {
                 type empty;
               }
               leaf ifff-src-class-input {
                 type empty;
               }
               leaf ifff-src-class-output {
                 type empty;
               }
               leaf ifff-mtu-user-conf {
                 type empty;
               }
               leaf ifff-mac-validate-strict {
                 type empty;
               }
               leaf ifff-mac-validate-loose {
                 type empty;
               }
               leaf ifff-rpf-check {
                 type empty;
               }
               leaf ifff-rpf-loose-mode {
                 type empty;
               }
               leaf ifff-sample-input {
                 type empty;
               }
               leaf ifff-sample-output {
                 type empty;
               }
               leaf ifff-no-asynch-notification {
                 type empty;
               }
               leaf ifff-negotiate-address {
                 type empty;
               }
               leaf ifff-port-mode-trunk {
                 type empty;
               }
               leaf ifff-inter-switch-link {
                 type empty;
               }
               leaf ifff-mtu-protocol-adj {
                 type empty;
               }
               leaf ifff-unnumbered {
                 type empty;
               }
               leaf ifff-tcc-mpls {
                 type empty;
               }
               leaf ifff-tcc-inet {
                 type empty;
               }
               leaf ifff-tcc-inet6 {
                 type empty;
               }
               leaf ifff-tcc-iso {
                 type empty;
               }
               leaf ifff-port-mode-isid-trunk {
                 type empty;
               }
               leaf generic-value {
                 type int32;
                 description "Hexadecimal value of unknown flag bits";
               }
             }
             list address-family-unnumbered {
               leaf unnumbered-family-donor-interface-name {
                 type string;
                 description "Donor interface name";
               }
               leaf unnumbered-family-donor-interface-index {
                 type string;
                 description "Donor interface index";
               }
               leaf unnumbered-family-preferred-source-address {
                 type string;
                 description "Unnumbered interface preferred source address";
               }
             }
             container pppoe-underlying-information {
               list pppoe-underlying-interface {
                 leaf dynamic-profile {
                   type string;
                   description "Dynamic Profile name";
                 }
                 leaf service-name-table {
                   type string;
                   description "Name of Service Name Table";
                 }
                 leaf max-sessions {
                   type int32;
                   description "Maximum number of PPPoE sessions";
                 }
                 leaf max-sessions-vsa-ignore {
                   type string;
                   description "Ignore max-sessions VSA";
                 }
                 leaf duplicate-protection {
                   type string;
                   description "Duplicate protection mode";
                 }
                 leaf short-cycle-protection {
                   type string;
                   description "Short cycle protection mode";
                 }
                 leaf direct-connect {
                   type string;
                   description "Direct connect mode";
                 }
                 leaf ac-name {
                   type string;
                   description "Access Concentrator name";
                 }
                 leaf underlying-interface-name {
                   type string;
                   description "Underlying interface name";
                 }
                 leaf underlying-interface-index {
                   type string;
                   description "Underlying interface index";
                 }
                 leaf encapsulation-type-identifier {
                   type string;
                   description "Encapsulation type identifier";
                 }
                 leaf state {
                   type string;
                   description "State";
                 }
                 leaf active-sessions {
                   type int32;
                   description "Number of active PPPoE sessions";
                 }
                 leaf aci-autosensing {
                   type string;
                   description "ACI VLAN Autosensing mode";
                 }
                 leaf line-identity-autosensing {
                   type string;
                   description "Line Identity Autosensing mode";
                 }
               }
             }
             list filter-information {
               leaf-list filter-input {
                 type string;
                 description "Name of the input filter";
               }
               leaf-list filter-input-precedence {
                 type uint32;
                 description "Precedence of the input filter";
               }
               leaf-list filter-output {
                 type string;
                 description "Name of the output filter";
               }
               leaf-list filter-output-precedence {
                 type uint32;
                 description "Precedence of the output filter";
               }
             }
             list policer-information {
               leaf policer-input {
                 type string;
                 description "Name of the input policer";
               }
               leaf policer-output {
                 type string;
                 description "Name of the output policer";
               }
             }
             list interface-address {
               leaf ifa-destination {
                 type string;
                 description "Protocol address of the remote side of this connection";
               }
               leaf ifa-local {
                 type string;
                 description "Protocol address on this interface";
               }
               leaf ifa-broadcast {
                 type string;
                 description "Network broadcast address";
               }
               leaf ifa-primary-dns {
                 type string;
                 description "Primary DNS server address";
               }
               leaf ifa-primary-nbns {
                 type string;
                 description "Primary Netbios Name server address";
               }
               leaf ifa-secondary-dns {
                 type string;
                 description "Secondary DNS server address";
               }
               leaf ifa-secondary-nbns {
                 type string;
                 description "Secondary Netbios Name server address";
               }
               leaf ifa-address-pool {
                 type string;
                 description "Address pool name";
               }
               leaf generation {
                 type int32;
                 description "Generation number used to distinguish between successive instances of this interface";
               }
               container ifa-flags {
                 leaf ifaf-none {
                   type empty;
                 }
                 leaf ifaf-primary {
                   type empty;
                 }
                 leaf ifaf-preferred {
                   type empty;
                 }
                 leaf ifaf-master-only {
                   type empty;
                 }
                 leaf ifaf-down {
                   type empty;
                 }
                 leaf ifaf-kernel {
                   type empty;
                 }
                 leaf ifaf-current-default {
                   type empty;
                 }
                 leaf ifaf-current-preferred {
                   type empty;
                 }
                 leaf ifaf-current-primary {
                   type empty;
                 }
                 leaf ifaf-duplicate {
                   type empty;
                 }
                 leaf ifaf-webauth-http {
                   type empty;
                 }
                 leaf generic-value {
                   type int32;
                   description "Hexadecimal value of unknown flag bits";
                 }
               }
               container in6-addr-flags {
                 leaf in6-anycast {
                   type empty;
                 }
                 leaf in6-tentative {
                   type empty;
                 }
                 leaf in6-duplicate {
                   type empty;
                 }
                 leaf in6-detached {
                   type empty;
                 }
                 leaf in6-deprecated {
                   type empty;
                 }
                 leaf in6-nodad {
                   type empty;
                 }
                 leaf in6-temporary {
                   type empty;
                 }
                 leaf in6-autoconf {
                   type empty;
                 }
                 leaf in6-nopfxmgmt {
                   type empty;
                 }
               }
             }
             container mac-validate-statistics {
               leaf mac-validate-packets {
                 type int32;
                 description "Number of packets that have failed the mac-validate check";
               }
               leaf mac-validate-bytes {
                 type int32;
                 description "Number of bytes that have failed the mac-validate check";
               }
             }
             container route-rpf-statistics {
               leaf route-rpf-packets {
                 type int32;
                 description "Number of packets that have failed the RPF check";
               }
               leaf route-rpf-bytes {
                 type int32;
                 description "Number of bytes that have failed the RPF check";
               }
             }
             container destination-class-statistics {
               list destination-class {
                 leaf dcu-class-name {
                   type string;
                   description "Name of DCU class";
                 }
                 leaf dcu-class-packets {
                   type int32;
                   description "Number of packets counted by DCU for this class";
                 }
                 leaf dcu-class-bytes {
                   type int32;
                   description "Number of bytes counted by DCU for this class";
                 }
                 leaf dcu-class-pps {
                   type int32;
                   description "Packet-per-seconds counted by DCU for this class";
                 }
                 leaf dcu-class-bps {
                   type int32;
                   description "Bit-per-seconds counted by DCU for this class";
                 }
               }
             }
             container source-class-statistics {
               list source-class {
                 leaf scu-class-name {
                   type string;
                   description "Name of SCU class";
                 }
                 leaf scu-class-packets {
                   type int32;
                   description "Number of packets counted by SCU for this class";
                 }
                 leaf scu-class-bytes {
                   type int32;
                   description "Number of bytes counted by SCU for this class";
                 }
                 leaf scu-class-pps {
                   type int32;
                   description "Packet-per-seconds counted by SCU for this class";
                 }
                 leaf scu-class-bps {
                   type int32;
                   description "Bit-per-seconds counted by SCU for this class";
                 }
               }
             }
           }
           list bridge-iff-properties {
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container irb-domain {
             leaf irb-routing-instance {
               type string;
               description "Name of the Routing Instance";
             }
             leaf irb-bridge {
               type string;
               description "Name of the Bridging Domain";
             }
           }
           container media-information {
             leaf media-type {
               type string;
               description "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description "Circuit Emulation counter information";
               }
               leaf ce-counter-packets {
                 type int32;
                 description "Circuit Emulation number of packets";
               }
               leaf ce-counter-bytes {
                 type int32;
                 description "Circuit Emulation number of bytes";
               }
               leaf ce-counter-count {
                 type int32;
                 description "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description "Number of feet";
             }
           }
           container vtep-info {
             leaf vtep-type {
               type string;
               description "Type of VXLAN endpoint";
             }
             leaf vtep-address {
               type string;
               description "Protocol address of the connection";
             }
             leaf vtep-l2-routing-instance {
               type string;
               description "Name of the layer-2 routing instance";
             }
             leaf vtep-l3-routing-instance {
               type string;
               description "Name of the layer-3 routing instance";
             }
           }
           container ft-info {
             leaf ft-encap {
               type string;
               description "Type of encap used for FTI";
             }
             leaf ft-dest-port {
               type int32;
               description "Destnation UDP port used in encap";
             }
             leaf ft-vnid {
               type int32;
               description "VNI value used in encap";
             }
             leaf ft-src-addr {
               type string;
               description "Source address used for encap";
             }
             leaf ft-dst-addr {
               type string;
               description "Destination address used for encap";
             }
           }
           container rbeb-info {
             leaf rbeb-address {
               type string;
               description "Protocol address of the connection";
             }
             leaf rbeb-l2-routing-instance {
               type string;
               description "Name of the layer-2 routing instance";
             }
           }
           list macsec-statistics {
             leaf interface-name {
               type string;
               description "Class-of-service interface name";
             }
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
             leaf ok-packets {
               type uint64;
               description "Macsec packets accepted";
             }
             leaf decrypted-bytes {
               type uint64;
               description "Macsec received bytes decrypted";
             }
             leaf decrypted-packets {
               type uint64;
               description "Macsec received packets decrypted";
             }
             leaf validated-packets {
               type uint64;
               description "Macsec received packets validated";
             }
             leaf validated-bytes {
               type uint64;
               description "Macsec received bytes validated";
             }
             leaf untagged-packets {
               type uint64;
               description "Macsec untagged packets";
             }
             leaf toolong-packets {
               type uint64;
               description "Macsec too long packets transmitted on a secure channel";
             }
             leaf control-packets {
               type uint64;
               description "Macsec control packets received on a secure channel";
             }
             leaf tagged-miss-packets {
               type uint64;
               description "Macsec tagged miss packets received on a secure channel";
             }
             leaf untagged-hit-packets {
               type uint64;
               description "Macsec untagged hit packets received on a secure channel";
             }
             leaf notag-packets {
               type uint64;
               description "Macsec no tag packets received on a secure channel";
             }
             leaf badtag-packets {
               type uint64;
               description "Macsec bad tag packets received on a secure channel";
             }
             leaf unknown-sci-packets {
               type uint64;
               description "Macsec unknown sci packets received on a secure channel";
             }
             leaf no-sci-packets {
               type uint64;
               description "Macsec no sci packets received on a secure channel";
             }
             leaf control-pass-packets {
               type uint64;
               description "Macsec allowed control packets received on a secure channel";
             }
             leaf uncontrol-pass-packets {
               type uint64;
               description "Macsec allowed uncontrol packets received on a secure channel";
             }
             leaf control-fail-packets {
               type uint64;
               description "Macsec dropped control packets received on a secure channel";
             }
             leaf uncontrol-fail-packets {
               type uint64;
               description "Macsec dropped uncontrol packets received on a secure channel";
             }
             leaf hit-dropped-packets {
               type uint64;
               description "Macsec hit dropped packets received on a security channel";
             }
             leaf notusing-sa-packets {
               type uint64;
               description "Macsec not using sa packets received on a security channel";
             }
             leaf unused-sa-packets {
               type uint64;
               description "Macsec unused sa packets received on a security channel";
             }
             leaf late-packets {
               type uint64;
               description "Macsec late packets dropped on a security channel";
             }
             leaf delayed-packets {
               type uint64;
               description "Macsec delayed packets accepted on a security channel";
             }
             leaf unchecked-packets {
               type uint64;
               description "Macsec unchecked packets accepted on a security channel";
             }
             leaf notvalid-packets {
               type uint64;
               description "Macsec not valid packets dropped on a security channel";
             }
             leaf invalid-packets {
               type uint64;
               description "Macsec invalid packets accepted on a security channel";
             }
             list secure-channel-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-association-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-channel-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list secure-association-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list macsec-error-information {
               list secure-channel-sent-errors {
                 leaf untagged-packets {
                   type uint64;
                   description "Macsec untagged packets";
                 }
                 leaf toolong-packets {
                   type uint64;
                   description "Macsec too long packets transmitted on a secure channel";
                 }
               }
               list secure-channel-received-errors {
                 leaf control-packets {
                   type uint64;
                   description "Macsec control packets received on a secure channel";
                 }
                 leaf tagged-miss-packets {
                   type uint64;
                   description "Macsec tagged miss packets received on a secure channel";
                 }
                 leaf untagged-hit-packets {
                   type uint64;
                   description "Macsec untagged hit packets received on a secure channel";
                 }
                 leaf untagged-packets {
                   type uint64;
                   description "Macsec untagged packets";
                 }
                 leaf notag-packets {
                   type uint64;
                   description "Macsec no tag packets received on a secure channel";
                 }
                 leaf badtag-packets {
                   type uint64;
                   description "Macsec bad tag packets received on a secure channel";
                 }
                 leaf unknown-sci-packets {
                   type uint64;
                   description "Macsec unknown sci packets received on a secure channel";
                 }
                 leaf no-sci-packets {
                   type uint64;
                   description "Macsec no sci packets received on a secure channel";
                 }
                 leaf control-pass-packets {
                   type uint64;
                   description "Macsec allowed control packets received on a secure channel";
                 }
                 leaf control-fail-packets {
                   type uint64;
                   description "Macsec dropped control packets received on a secure channel";
                 }
                 leaf uncontrol-pass-packets {
                   type uint64;
                   description "Macsec allowed uncontrol packets received on a secure channel";
                 }
                 leaf uncontrol-fail-packets {
                   type uint64;
                   description "Macsec dropped uncontrol packets received on a secure channel";
                 }
               }
               list secure-channel-received-extended {
                 leaf hit-dropped-packets {
                   type uint64;
                   description "Macsec hit dropped packets received on a security channel";
                 }
                 leaf invalid-packets {
                   type uint64;
                   description "Macsec invalid packets accepted on a security channel";
                 }
                 leaf late-packets {
                   type uint64;
                   description "Macsec late packets dropped on a security channel";
                 }
                 leaf delayed-packets {
                   type uint64;
                   description "Macsec delayed packets accepted on a security channel";
                 }
                 leaf unchecked-packets {
                   type uint64;
                   description "Macsec unchecked packets accepted on a security channel";
                 }
                 leaf notvalid-packets {
                   type uint64;
                   description "Macsec not valid packets dropped on a security channel";
                 }
                 leaf notusing-sa-packets {
                   type uint64;
                   description "Macsec not using sa packets received on a security channel";
                 }
                 leaf unused-sa-packets {
                   type uint64;
                   description "Macsec unused sa packets received on a security channel";
                 }
                 leaf untagged-hit-packets {
                   type uint64;
                   description "Macsec untagged hit packets received on a secure channel";
                 }
               }
             }
           }
           container multilink-bundle-status {
             leaf rx-sequence-number {
               type string;
               description "Received sequence number";
             }
             leaf tx-sequence-number {
               type string;
               description "Transmitted sequence number";
             }
             leaf packet-drops {
               type int32;
               description "Number of packets dropped";
             }
             leaf packet-drop-bytes {
               type int32;
               description "Number of bytes in dropped packets";
             }
             leaf fragment-drops {
               type int32;
               description "Number of fragments dropped";
             }
             leaf fragment-drop-bytes {
               type int32;
               description "Number of bytes in dropped fragments";
             }
             leaf mrru-exceeded {
               type int32;
               description "Number of assembled packets that exceeded MRRU";
             }
             leaf processing-errors {
               type int32;
               description "Number of errors encountered in assembling packets";
             }
             leaf fragment-timeout {
               type int32;
               description "Fragments timed out during assembly";
             }
             leaf sequence-number-missing {
               type int32;
               description "Gap detected in sequence numbers";
             }
             leaf out-of-order-sequence-number {
               type int32;
               description "Fragments with an out-of-order sequence number";
             }
             leaf out-of-range-sequence-number {
               type int32;
               description "Fragments with an out-of-range sequence number";
             }
             leaf packet-buffer-overflow {
               type int32;
               description "Number of times the packet data buffer overflowed";
             }
             leaf fragment-buffer-overflow {
               type int32;
               description "Number of times the fragment data buffer overflowed";
             }
           }
           container multilink-bundle-class {
             leaf multilink-class-id {
               type int32;
               description "Multilink class ID";
             }
             leaf rx-sequence-number {
               type string;
               description "Received sequence number";
             }
             leaf tx-sequence-number {
               type string;
               description "Transmitted sequence number";
             }
             leaf packet-drops {
               type int32;
               description "Number of packets dropped";
             }
             leaf packet-drop-bytes {
               type int32;
               description "Number of bytes in dropped packets";
             }
             leaf fragment-drops {
               type int32;
               description "Number of fragments dropped";
             }
             leaf fragment-drop-bytes {
               type int32;
               description "Number of bytes in dropped fragments";
             }
             leaf mrru-exceeded {
               type int32;
               description "Number of assembled packets that exceeded MRRU";
             }
             leaf processing-errors {
               type int32;
               description "Number of errors encountered in assembling packets";
             }
             leaf fragment-timeout {
               type int32;
               description "Fragments timed out during assembly";
             }
             leaf sequence-number-missing {
               type int32;
               description "Gap detected in sequence numbers";
             }
             leaf out-of-order-sequence-number {
               type int32;
               description "Fragments with an out-of-order sequence number";
             }
             leaf out-of-range-sequence-number {
               type int32;
               description "Fragments with an out-of-range sequence number";
             }
             leaf packet-buffer-overflow {
               type int32;
               description "Number of times the packet data buffer overflowed";
             }
             leaf fragment-buffer-overflow {
               type int32;
               description "Number of times the fragment data buffer overflowed";
             }
             leaf multilink-class-drop-timeout {
               type int32;
               description "Drop timeout for multilink class (milliseconds)";
             }
           }
           container lag-traffic-statistics {
             container lag-bundle {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-adaptive-statistics {
               leaf adaptive-adjusts {
                 type int32;
               }
               leaf adaptive-scans {
                 type int32;
               }
               leaf adaptive-updates {
                 type int32;
               }
             }
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             container aggregate-member-info {
               leaf aggregate-member-count {
                 type uint32;
               }
             }
             list lag-link {
               leaf name {
                 type string;
                 description "Name of this item";
               }
               leaf down {
                 type empty;
                 description "Link is down";
               }
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             list lag-bfd-view {
               leaf name {
                 type string;
                 description "Name of this item";
               }
               leaf link-usability {
                 type string;
               }
             }
             list lag-targeting-summary {
               leaf targeting-intf-name {
                 type string;
               }
               leaf targeting-intf-type {
                 type string;
               }
               leaf targeting-intf-link-state {
                 type string;
               }
             }
             list lag-marker {
               leaf name {
                 type string;
                 description "Name of this item";
               }
               leaf marker-rx-packets {
                 type string;
               }
               leaf marker-response-tx-packets {
                 type string;
               }
               leaf unknown-rx-packets {
                 type string;
                 description "Number of unknown type packets received";
               }
               leaf illegal-rx-packets {
                 type string;
                 description "Number of ill formed packets received";
               }
             }
             list lag-lacp-statistics {
               leaf name {
                 type string;
                 description "Name of this item";
               }
               leaf lacp-rx-packets {
                 type string;
                 description "Number of LACP packets received";
               }
               leaf lacp-tx-packets {
                 type string;
                 description "Number of LACP packets transmitted";
               }
               leaf unknown-rx-packets {
                 type string;
                 description "Number of unknown type packets received";
               }
               leaf illegal-rx-packets {
                 type string;
                 description "Number of ill formed packets received";
               }
             }
             list if-distribution-list-information {
               leaf list-type {
                 type string;
               }
               leaf list-status {
                 type string;
               }
               list if-list {
                 leaf if-child-name {
                   type string;
                 }
                 leaf if-status {
                   type string;
                 }
               }
             }
             list lag-link-protection-subgrp {
               leaf name {
                 type string;
                 description "Name of this item";
               }
               leaf lag-link-protection-subgrp-name {
                 type string;
               }
               leaf lag-link-protection-subgrp-state {
                 type string;
               }
             }
             list lag-lacp-info {
               leaf name {
                 type string;
                 description "Name of this item";
               }
               leaf lacp-role {
                 type string;
                 description "Whether it is an actor or partner";
               }
               leaf lacp-sys-priority {
                 type string;
                 description "System priority";
               }
               leaf lacp-system-id {
                 type string;
                 description "LACP system identifier";
               }
               leaf lacp-port-priority {
                 type string;
                 description "Priority of the port";
               }
               leaf lacp-port-number {
                 type string;
                 description "Port number";
               }
               leaf lacp-port-key {
                 type string;
                 description "Operational key of the port";
               }
             }
             list lag-lacp-state {
               leaf name {
                 type string;
                 description "Name of this item";
               }
               leaf lacp-role {
                 type string;
                 description "Whether it is an actor or partner";
               }
               leaf lacp-expired {
                 type string;
                 description "State of the receive lacp machine is EXPIRED?";
               }
               leaf lacp-defaulted {
                 type string;
                 description "State of the receive lacp machine is DEFAULTED?";
               }
               leaf lacp-distributing {
                 type string;
                 description "State of the mux lacp machine is DISTRIBUTING?";
               }
               leaf lacp-collecting {
                 type string;
                 description "State of the mux lacp machine is COLLECTING?";
               }
               leaf lacp-synchronization {
                 type string;
                 description "Actor view of partner information is in sync";
               }
               leaf lacp-aggregation {
                 type string;
                 description "Actor view of partner information is in sync";
               }
               leaf lacp-timeout {
                 type string;
                 description "Configured as either fast or slow periodic";
               }
               leaf lacp-activity {
                 type string;
                 description "Configured as either active or passive";
               }
             }
             list lag-lacp-protocol {
               leaf name {
                 type string;
                 description "Name of this item";
               }
               leaf lacp-receive-state {
                 type string;
                 description "State of the receive lacp machine";
               }
               leaf lacp-transmit-state {
                 type string;
                 description "State of the transmit lacp machine";
               }
               leaf lacp-mux-state {
                 type string;
                 description "State of the mux lacp machine";
               }
             }
             list lag-lacp-bfd {
               leaf name {
                 type string;
                 description "Name of this item";
               }
               leaf lacp-bfd-state {
                 type string;
                 description "State of the BFD session";
               }
             }
             list lacp-hold-up-information {
               leaf name {
                 type string;
                 description "Name of this item";
               }
               leaf status {
                 type string;
               }
               leaf restart-count {
                 type int32;
               }
               leaf time-to-expire {
                 type int32;
               }
               leaf start-time {
                 type string;
               }
             }
           }
           container layer2-input-policer-statistics {
             leaf policer-low-iq2-frames {
               type int32;
               description "Number of loss priority low frames";
             }
             leaf policer-medium-low-iq2-frames {
               type int32;
               description "Number of loss priority medium low frames";
             }
             leaf policer-medium-high-iq2-frames {
               type int32;
               description "Number of loss priority medium high frames";
             }
             leaf policer-high-iq2-frames {
               type int32;
               description "Number of loss priority high frames";
             }
             leaf policer-dropped-iq2-frames {
               type int32;
               description "Number of dropped frames";
             }
             leaf policer-low-bytes {
               type int32;
               description "Number of loss priority low bytes";
             }
             leaf policer-low-frames {
               type int32;
               description "Number of loss priority low frames";
             }
             leaf policer-low-rate {
               type int32;
               description "Rate of loss priority low pkts";
             }
             leaf policer-medium-high-bytes {
               type int32;
               description "Number of loss priority medium high bytes";
             }
             leaf policer-medium-high-frames {
               type int32;
               description "Number of loss priority medium high frames";
             }
             leaf policer-medium-high-rate {
               type int32;
               description "Rate of loss priority medium high rate";
             }
             leaf policer-high-bytes {
               type int32;
               description "Number of loss priority high bytes";
             }
             leaf policer-high-frames {
               type int32;
               description "Number of loss priority high frames";
             }
             leaf policer-high-rate {
               type int32;
               description "Rate of loss priority high rate";
             }
             leaf policer-dropped-bytes {
               type int32;
               description "Number of dropped bytes";
             }
             leaf policer-dropped-frames {
               type int32;
               description "Number of dropped frames";
             }
             leaf policer-dropped-rate {
               type int32;
               description "Number of dropped rate";
             }
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container layer2-output-policer-statistics {
             leaf policer-low-iq2-frames {
               type int32;
               description "Number of loss priority low frames";
             }
             leaf policer-medium-low-iq2-frames {
               type int32;
               description "Number of loss priority medium low frames";
             }
             leaf policer-medium-high-iq2-frames {
               type int32;
               description "Number of loss priority medium high frames";
             }
             leaf policer-high-iq2-frames {
               type int32;
               description "Number of loss priority high frames";
             }
             leaf policer-dropped-iq2-frames {
               type int32;
               description "Number of dropped frames";
             }
             leaf policer-low-bytes {
               type int32;
               description "Number of loss priority low bytes";
             }
             leaf policer-low-frames {
               type int32;
               description "Number of loss priority low frames";
             }
             leaf policer-low-rate {
               type int32;
               description "Rate of loss priority low pkts";
             }
             leaf policer-medium-high-bytes {
               type int32;
               description "Number of loss priority medium high bytes";
             }
             leaf policer-medium-high-frames {
               type int32;
               description "Number of loss priority medium high frames";
             }
             leaf policer-medium-high-rate {
               type int32;
               description "Rate of loss priority medium high rate";
             }
             leaf policer-high-bytes {
               type int32;
               description "Number of loss priority high bytes";
             }
             leaf policer-high-frames {
               type int32;
               description "Number of loss priority high frames";
             }
             leaf policer-high-rate {
               type int32;
               description "Rate of loss priority high rate";
             }
             leaf policer-dropped-bytes {
               type int32;
               description "Number of dropped bytes";
             }
             leaf policer-dropped-frames {
               type int32;
               description "Number of dropped frames";
             }
             leaf policer-dropped-rate {
               type int32;
               description "Number of dropped rate";
             }
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container atm-input-policer-statistics {
             leaf atm-policer-traffic-count-cells {
               type int32;
               description "Stats for counted ATM Cells";
             }
             leaf atm-policer-traffic-discard-cells {
               type int32;
               description "Stats for discarded ATM Cells";
             }
             leaf atm-policer-traffic-discard-tag-cells {
               type int32;
               description "Stats for discard-tag ATM Cells";
             }
           }
           container mac-policer-information {
             leaf mac-address {
               type jt:mac-addr;
             }
             leaf mac-entry-type {
               type string;
             }
             leaf receive-bytes {
               type int32;
             }
             leaf transmit-bytes {
               type int32;
             }
             leaf receive-frames {
               type int32;
             }
             leaf transmit-frames {
               type int32;
             }
             container ether-policer-list {
               list ether-policer-record {
                 leaf policer-type {
                   type string;
                 }
                 leaf out-of-spec-frames {
                   type int32;
                 }
                 leaf out-of-spec-bytes {
                   type int32;
                 }
               }
             }
           }
         }
         container active-alarms-otn {
           leaf type-otn {
             type string;
             description "OTN type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container active-defects-otn {
           leaf type-otn {
             type string;
             description "OTN type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container active-alarms-optics {
           leaf type-optics {
             type string;
             description "Optics type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container active-defects-optics {
           leaf type-optics {
             type string;
             description "Optics type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
           leaf type-otn {
             type string;
             description "OTN type for associated interface alarms";
           }
           container interface-alarms {
             leaf alarm-not-present {
               type empty;
               description "No alarm indicated";
             }
             leaf sonet-alarm-lol {
               type empty;
               description "Loss of light alarm";
             }
             leaf sonet-alarm-pll {
               type empty;
               description "PLL lock alarm";
             }
             leaf sonet-alarm-lof {
               type empty;
               description "Loss of frame alarm";
             }
             leaf sonet-alarm-los {
               type empty;
               description "Loss of signal alarm";
             }
             leaf sonet-alarm-sef {
               type empty;
               description "Severely errored frame alarm";
             }
             leaf sonet-alarm-lais {
               type empty;
               description "Line AIS alarm";
             }
             leaf sonet-alarm-pais {
               type empty;
               description "Path AIS alarm";
             }
             leaf sonet-alarm-lop {
               type empty;
               description "Loss of pointer alarm";
             }
             leaf sonet-alarm-berr-sd {
               type empty;
               description "Bit error rate alarm, defect";
             }
             leaf sonet-alarm-berr-sf {
               type empty;
               description "Bit error rate alarm, fault";
             }
             leaf sonet-alarm-lrdi {
               type empty;
               description "Line remote defect indicator alarm";
             }
             leaf sonet-alarm-prdi {
               type empty;
               description "Path remote defect indicator alarm";
             }
             leaf sonet-alarm-rei {
               type empty;
               description "Path remote error indicator alarm";
             }
             leaf sonet-alarm-uneq {
               type empty;
               description "Unequipped alarm";
             }
             leaf sonet-alarm-pmis {
               type empty;
               description "Path payload level mismatch alarm";
             }
             leaf sonet-alarm-loc {
               type empty;
               description "Loss of cell delineation alarm";
             }
             leaf sonet-alarm-vais {
               type empty;
               description "VT AIS alarm";
             }
             leaf sonet-alarm-vlop {
               type empty;
               description "VT loss of pointer alarm";
             }
             leaf sonet-alarm-vrdi {
               type empty;
               description "VT remote defect indicator alarm";
             }
             leaf sonet-alarm-vuneq {
               type empty;
               description "VT unequipped alarm";
             }
             leaf sonet-alarm-vmis {
               type empty;
               description "VT label mismatch alarm";
             }
             leaf sonet-alarm-vloc {
               type empty;
               description "VT loss of cell delineation alarm";
             }
             leaf sdh-alarm-lol {
               type empty;
               description "Loss of light alarm";
             }
             leaf sdh-alarm-pll {
               type empty;
               description "PLL lock alarm";
             }
             leaf sdh-alarm-lof {
               type empty;
               description "Loss of frame alarm";
             }
             leaf sdh-alarm-los {
               type empty;
               description "Loss of signal alarm";
             }
             leaf sdh-alarm-oof {
               type empty;
               description "Out of frame alarm";
             }
             leaf sdh-alarm-msais {
               type empty;
               description "Multiplex section AIS alarm";
             }
             leaf sdh-alarm-hpais {
               type empty;
               description "High order path AIS alarm";
             }
             leaf sdh-alarm-lop {
               type empty;
               description "Loss of pointer alarm";
             }
             leaf sdh-alarm-berr-sd {
               type empty;
               description "Bit error rate alarm, defect";
             }
             leaf sdh-alarm-berr-sf {
               type empty;
               description "Bit error rate alarm, fault";
             }
             leaf sdh-alarm-msferf {
               type empty;
               description "Multiplex section far-end remote failure alarm";
             }
             leaf sdh-alarm-hpferf {
               type empty;
               description "High order path far-end remote failure alarm";
             }
             leaf sdh-alarm-hpfebe {
               type empty;
               description "High order path far-end block error alarm";
             }
             leaf sdh-alarm-hpuneq {
               type empty;
               description "High order path unequipped alarm";
             }
             leaf sdh-alarm-hpplm {
               type empty;
               description "High order path payload level mismatch alarm";
             }
             leaf sdh-alarm-loc {
               type empty;
               description "Loss of cell delineation alarm";
             }
             leaf sdh-alarm-tuais {
               type empty;
               description "TU AIS alarm";
             }
             leaf sdh-alarm-tulop {
               type empty;
               description "TU loss of pointer alarm";
             }
             leaf sdh-alarm-turdi {
               type empty;
               description "TU remote defect indicator alarm";
             }
             leaf sdh-alarm-tuuneq {
               type empty;
               description "TU unequipped alarm";
             }
             leaf sdh-alarm-tumis {
               type empty;
               description "TU label mismatch error";
             }
             leaf sdh-alarm-tuloc {
               type empty;
               description "TU loss of cell delineation alarm";
             }
             leaf ds3-alarm-pll {
               type empty;
               description "PLL lock alarm";
             }
             leaf ds3-alarm-ais {
               type empty;
               description "AIS alarm";
             }
             leaf ds3-alarm-lof {
               type empty;
               description "Loss of frame alarm";
             }
             leaf ds3-alarm-los {
               type empty;
               description "Loss of signal alarm";
             }
             leaf ds3-alarm-lcv {
               type empty;
               description "Line code violation alarm";
             }
             leaf ds3-alarm-exz {
               type empty;
               description "Excessive zeros alarm";
             }
             leaf ds3-alarm-ferf {
               type empty;
               description "Far-end receive failure alarm";
             }
             leaf ds3-alarm-ylw {
               type empty;
               description "Yellow alarm";
             }
             leaf ds3-alarm-idle {
               type empty;
               description "Idle alarm";
             }
             leaf ds1-alarm-ais {
               type empty;
               description "AIS alarm";
             }
             leaf ds1-alarm-lof {
               type empty;
               description "Loss of frame alarm";
             }
             leaf ds1-alarm-los {
               type empty;
               description "Loss of signal alarm";
             }
             leaf ds1-alarm-ylw {
               type empty;
               description "Yellow alarm";
             }
             leaf ds1-alarm-crc-major {
               type empty;
               description "CRC errors crossed major threshold";
             }
             leaf ds1-alarm-crc-minor {
               type empty;
               description "CRC errors crossed minor threshold";
             }
             leaf dsl-alarm-lof {
               type empty;
               description "Loss of frame alarm";
             }
             leaf dsl-alarm-los {
               type empty;
               description "Loss of signal alarm";
             }
             leaf dsl-alarm-lom {
               type empty;
               description "Loss of multiframe alarm";
             }
             leaf dsl-alarm-locdi {
               type empty;
               description "Loss of cell delineation alarm for interleaved channel";
             }
             leaf dsl-alarm-locdni {
               type empty;
               description "Loss of cell delineation alarm for non-interleaved channel";
             }
             leaf dsl-alarm-lop {
               type empty;
               description "Loss of power alarm";
             }
             leaf dsl-alarm-far-lof {
               type empty;
               description "Far-end loss-of-frame alarm";
             }
             leaf dsl-alarm-far-los {
               type empty;
               description "Far-end loss-of-signal alarm";
             }
             leaf dsl-alarm-far-locdi {
               type empty;
               description "Far-end loss-of-cell-delineation alarm for interleaved channel";
             }
             leaf dsl-alarm-far-locdni {
               type empty;
               description "Far-end loss-of-cell-delineation alarm for non-interleaved channel";
             }
             leaf fibrechannel-alarm-link-down {
               type empty;
               description "Link alive failure";
             }
             leaf ethernet-alarm-link-down {
               type empty;
               description "Link alive failure";
             }
             leaf ethernet-alarm-link-local-fault {
               type empty;
               description "Link local fault";
             }
             leaf ethernet-alarm-link-remote-fault {
               type empty;
               description "Link remote fault";
             }
             leaf ethernet-alarm-lcdp {
               type empty;
               description "Loss of code-group delineation";
             }
             leaf isdn-alarm-los {
               type empty;
               description "Loss of signal alarm";
             }
             leaf isdn-alarm-lof {
               type empty;
               description "Loss of frame alarm";
             }
             leaf shdsl-alarm-losd {
               type empty;
               description "Loss of signal alarm";
             }
             leaf shdsl-alarm-losw {
               type empty;
               description "Loss of sync word alarm";
             }
             leaf shdsl-alarm-line1-losd {
               type empty;
               description "Loss of signal (line 1) alarm";
             }
             leaf shdsl-alarm-line1-losw {
               type empty;
               description "Loss of sync word (line 1) alarm";
             }
             leaf shdsl-alarm-line2-losd {
               type empty;
               description "Loss of signal (line 2) alarm";
             }
             leaf shdsl-alarm-line2-losw {
               type empty;
               description "Loss of sync word (line 2) alarm";
             }
             leaf shdsl-efm-alarm-losd {
               type empty;
               description "Loss of signal alarm";
             }
             leaf shdsl-efm-alarm-losw {
               type empty;
               description "Loss of sync word alarm";
             }
             leaf otn-alarm-los {
               type empty;
               description "Loss of signal alarm";
             }
             leaf otn-alarm-lof {
               type empty;
               description "Loss of frame alarm";
             }
             leaf otn-alarm-lom {
               type empty;
               description "Loss of multiframe alarm";
             }
             leaf otn-alarm-wavelength-lock {
               type empty;
               description "Loss of Wavelength Lock alarm";
             }
             leaf otn-alarm-otu-ais {
               type empty;
               description "OTU Alarm Indication Signal alarm";
             }
             leaf otn-alarm-otu-bdi {
               type empty;
               description "OTU Background Block Error alarm";
             }
             leaf otn-alarm-otu-ttim {
               type empty;
               description "OTU Trail Trace Identifier Mismatch alarm";
             }
             leaf otn-alarm-otu-iae {
               type empty;
               description "OTU Incoming Alignment alarm";
             }
             leaf otn-alarm-otu-sd {
               type empty;
               description "OTU Signal Degrade alarm";
             }
             leaf otn-alarm-otu-sf {
               type empty;
               description "OTU Signal Fail alarm";
             }
             leaf otn-alarm-otu-biae {
               type empty;
               description "OTU Backward Incoming Alignment alarm";
             }
             leaf otn-alarm-otu-tsf {
               type empty;
               description "OTU Trail Signal Fail alarm";
             }
             leaf otn-alarm-otu-ssf {
               type empty;
               description "OTU Server Signal Fail alarm";
             }
             leaf otn-alarm-otu-fec-excessive {
               type empty;
               description "OTU FEC Excessive alarm";
             }
             leaf otn-alarm-otu-fec-degraded {
               type empty;
               description "OTU FEC Degraded alarm";
             }
             leaf otn-alarm-otu-fe-fec-degraded {
               type empty;
               description "OTU FE FEC Degraded/Excessive alarm";
             }
             leaf otn-alarm-otu-threshold-bbe {
               type empty;
               description "OTU Background Block Error threshold alarm";
             }
             leaf otn-alarm-otu-threshold-es {
               type empty;
               description "OTU Errored Seconds threshold alarm";
             }
             leaf otn-alarm-otu-threshold-ses {
               type empty;
               description "OTU Severely Errored Seconds threshold alarm";
             }
             leaf otn-alarm-otu-threshold-uas {
               type empty;
               description "OTU Unavailable Seconds threshold alarm";
             }
             leaf otn-alarm-odu-ais {
               type empty;
               description "ODU  Alarm Indiaction Signal alarm";
             }
             leaf otn-alarm-odu-oci {
               type empty;
               description "ODU Open Connection Indication alarm";
             }
             leaf otn-alarm-odu-lck {
               type empty;
               description "ODU Locked alarm";
             }
             leaf otn-alarm-odu-bdi {
               type empty;
               description "ODU Backward Defect Indication alarm";
             }
             leaf otn-alarm-odu-ttim {
               type empty;
               description "ODU Trail Trace Identifier Mismatch alarm";
             }
             leaf otn-alarm-odu-sd {
               type empty;
               description "ODU Signal Degrade alarm";
             }
             leaf otn-alarm-odu-sf {
               type empty;
               description "ODU Signal Fail alarm";
             }
             leaf otn-alarm-odu-iae {
               type empty;
               description "ODU Incoming Alignment alarm";
             }
             leaf otn-alarm-odu-ltc {
               type empty;
               description "ODU Loss of Tandem Connection alarm";
             }
             leaf otn-alarm-odu-csf {
               type empty;
               description "ODU Client Signal Fail alarm";
             }
             leaf otn-alarm-odu-tsf {
               type empty;
               description "ODU Trail Signal Fail alarm";
             }
             leaf otn-alarm-odu-ssf {
               type empty;
               description "ODU Server Signal Fail alarm";
             }
             leaf otn-alarm-odu-rx-aps-change {
               type empty;
               description "ODU Rx Aps Change alarm";
             }
             leaf otn-alarm-odu-threshold-bbe {
               type empty;
               description "ODU Background Block Error threshold alarm";
             }
             leaf otn-alarm-odu-threshold-es {
               type empty;
               description "ODU Errored Seconds threshold alarm";
             }
             leaf otn-alarm-odu-threshold-ses {
               type empty;
               description "ODU Severely Errored Seconds threshold alarm";
             }
             leaf otn-alarm-odu-threshold-uas {
               type empty;
               description "ODU Unavailable Seconds threshold alarm";
             }
             leaf otn-alarm-opu-pmi {
               type empty;
               description "OPU Payload Mismatch alarm";
             }
             leaf otn-alarm-pre-fec-sd {
               type empty;
               description "Pre-FEC SD alarm";
             }
             leaf otn-alarm-fe-pre-fec-sd {
               type empty;
               description "Far end pre-FEC SD alarm";
             }
             leaf optics-alarms-mod-fault {
               type empty;
               description "Module Fault alarm";
             }
             leaf optics-alarms-lol {
               type empty;
               description "Loss of Lock alarm";
             }
             leaf optics-alarms-los {
               type empty;
               description "Loss of Signal alarms";
             }
             leaf optics-alarms-lof {
               type empty;
               description "Loss of frame alarm";
             }
             leaf optics-alarms-lom {
               type empty;
               description "Loss of multi-frame alarm";
             }
             leaf optics-alarms-otu-bdi {
               type empty;
               description "Backward defect indiacation alarm";
             }
             leaf optics-alarms-rmsf {
               type empty;
               description "Rx Modem sysnc fault alarm";
             }
             leaf optics-alarms-rmlol {
               type empty;
               description "Rx Modem loss of lock alarm";
             }
             leaf optics-alarms-rloa {
               type empty;
               description "Rx loss of alignment alarm";
             }
             leaf optics-alarms-mbclf {
               type empty;
               description "Modulator Bias control loop fail alarm";
             }
             leaf optics-alarms-itlaf {
               type empty;
               description "ITLA Fault alarm";
             }
             leaf optics-alarms-daccf {
               type empty;
               description "DAC Calibration Fault alarm";
             }
             leaf optics-alarms-adccf {
               type empty;
               description "ADC Calibration Fault alarm";
             }
             leaf optics-alarms-fec-degrade {
               type empty;
               description "FEC Degrade alarm";
             }
             leaf optics-alarms-fec-excessive {
               type empty;
               description "FEC Excessive alarm";
             }
             leaf optics-alarms-fe-fec-degrade {
               type empty;
               description "Far-end FEC Degrade alarm";
             }
             leaf optics-alarms-fe-fec-excessive {
               type empty;
               description "Far-end FEC Excessive alarm";
             }
             leaf ima-alarm-startup-fe {
               type empty;
               description "IMA group startup far-end alarm";
             }
             leaf ima-alarm-config-abort {
               type empty;
               description "IMA group config abort alarm";
             }
             leaf ima-alarm-config-abort-fe {
               type empty;
               description "IMA group config abort far-end alarm";
             }
             leaf ima-alarm-insufficient-links {
               type empty;
               description "IMA group insufficient links alarm";
             }
             leaf ima-alarm-insufficient-links-fe {
               type empty;
               description "IMA group insufficient links far-end alarm";
             }
             leaf ima-alarm-blocked {
               type empty;
               description "IMA group blocked alarm";
             }
             leaf ima-alarm-blocked-fe {
               type empty;
               description "IMA group blocked far-end alarm";
             }
             leaf ima-alarm-timing-mismatch {
               type empty;
               description "IMA group timing mismatch alarm";
             }
             leaf ima-alarm-version-mismatch {
               type empty;
               description "IMA group version mismatch alarm";
             }
             leaf ima-alarm-lif {
               type empty;
               description "IMA link loss of IMA frame alarm";
             }
             leaf ima-alarm-lods {
               type empty;
               description "IMA link out of delay synchronization alarm";
             }
             leaf ima-alarm-rdi {
               type empty;
               description "IMA link remote defect indicator alarm";
             }
             leaf ima-alarm-tx-misconnected {
               type empty;
               description "IMA link tx misconnected alarm";
             }
             leaf ima-alarm-rx-misconnected {
               type empty;
               description "IMA link rx misconnected alarm";
             }
             leaf ima-alarm-fault {
               type empty;
               description "IMA link fault alarm";
             }
             leaf ima-alarm-tx-unusable-fe {
               type empty;
               description "IMA link Tx unusable far-end alarm";
             }
             leaf ima-alarm-rx-unusable-fe {
               type empty;
               description "IMA link Tx unusable far-end alarm";
             }
             leaf generic-value {
               type int32;
               description "Hexadecimal value of unknown flag bits";
             }
           }
         }
         container links {
           list link-entry {
             leaf link-id {
               type int32;
               description "Link id for aggregated SONET/SDH interface";
             }
             leaf sonet-rx-overhead {
               type string;
             }
             leaf sonet-tx-overhead {
               type string;
             }
             leaf sonet-rx-path-trace {
               type string;
               description "Received SONET path trace";
             }
             leaf sonet-tx-path-trace {
               type string;
               description "Transmitted SONET path trace";
             }
             leaf sonet-payload-pointer-curptr {
               type string;
               description "Value of the SONET/SDH payload pointer, derived from the H1 and H2 overhead bytes";
             }
             leaf sonet-payload-pointer-ptrinc-count {
               type string;
               description "Number of times the value of the SONET/SDH payload pointer had positive justification";
             }
             leaf sonet-payload-pointer-ptrdec-count {
               type string;
               description "Number of times the value of the SONET/SDH payload pointer had negative justification";
             }
             leaf sonet-payload-pointer-newptr-ndf-count {
               type string;
               description "Number of times a new payload pointer was created with the New Data Found flag set";
             }
             container active-alarms {
               leaf type {
                 type string;
                 description "Media type for associated interface alarms";
               }
               container interface-alarms {
                 leaf alarm-not-present {
                   type empty;
                   description "No alarm indicated";
                 }
                 leaf sonet-alarm-lol {
                   type empty;
                   description "Loss of light alarm";
                 }
                 leaf sonet-alarm-pll {
                   type empty;
                   description "PLL lock alarm";
                 }
                 leaf sonet-alarm-lof {
                   type empty;
                   description "Loss of frame alarm";
                 }
                 leaf sonet-alarm-los {
                   type empty;
                   description "Loss of signal alarm";
                 }
                 leaf sonet-alarm-sef {
                   type empty;
                   description "Severely errored frame alarm";
                 }
                 leaf sonet-alarm-lais {
                   type empty;
                   description "Line AIS alarm";
                 }
                 leaf sonet-alarm-pais {
                   type empty;
                   description "Path AIS alarm";
                 }
                 leaf sonet-alarm-lop {
                   type empty;
                   description "Loss of pointer alarm";
                 }
                 leaf sonet-alarm-berr-sd {
                   type empty;
                   description "Bit error rate alarm, defect";
                 }
                 leaf sonet-alarm-berr-sf {
                   type empty;
                   description "Bit error rate alarm, fault";
                 }
                 leaf sonet-alarm-lrdi {
                   type empty;
                   description "Line remote defect indicator alarm";
                 }
                 leaf sonet-alarm-prdi {
                   type empty;
                   description "Path remote defect indicator alarm";
                 }
                 leaf sonet-alarm-rei {
                   type empty;
                   description "Path remote error indicator alarm";
                 }
                 leaf sonet-alarm-uneq {
                   type empty;
                   description "Unequipped alarm";
                 }
                 leaf sonet-alarm-pmis {
                   type empty;
                   description "Path payload level mismatch alarm";
                 }
                 leaf sonet-alarm-loc {
                   type empty;
                   description "Loss of cell delineation alarm";
                 }
                 leaf sonet-alarm-vais {
                   type empty;
                   description "VT AIS alarm";
                 }
                 leaf sonet-alarm-vlop {
                   type empty;
                   description "VT loss of pointer alarm";
                 }
                 leaf sonet-alarm-vrdi {
                   type empty;
                   description "VT remote defect indicator alarm";
                 }
                 leaf sonet-alarm-vuneq {
                   type empty;
                   description "VT unequipped alarm";
                 }
                 leaf sonet-alarm-vmis {
                   type empty;
                   description "VT label mismatch alarm";
                 }
                 leaf sonet-alarm-vloc {
                   type empty;
                   description "VT loss of cell delineation alarm";
                 }
                 leaf sdh-alarm-lol {
                   type empty;
                   description "Loss of light alarm";
                 }
                 leaf sdh-alarm-pll {
                   type empty;
                   description "PLL lock alarm";
                 }
                 leaf sdh-alarm-lof {
                   type empty;
                   description "Loss of frame alarm";
                 }
                 leaf sdh-alarm-los {
                   type empty;
                   description "Loss of signal alarm";
                 }
                 leaf sdh-alarm-oof {
                   type empty;
                   description "Out of frame alarm";
                 }
                 leaf sdh-alarm-msais {
                   type empty;
                   description "Multiplex section AIS alarm";
                 }
                 leaf sdh-alarm-hpais {
                   type empty;
                   description "High order path AIS alarm";
                 }
                 leaf sdh-alarm-lop {
                   type empty;
                   description "Loss of pointer alarm";
                 }
                 leaf sdh-alarm-berr-sd {
                   type empty;
                   description "Bit error rate alarm, defect";
                 }
                 leaf sdh-alarm-berr-sf {
                   type empty;
                   description "Bit error rate alarm, fault";
                 }
                 leaf sdh-alarm-msferf {
                   type empty;
                   description "Multiplex section far-end remote failure alarm";
                 }
                 leaf sdh-alarm-hpferf {
                   type empty;
                   description "High order path far-end remote failure alarm";
                 }
                 leaf sdh-alarm-hpfebe {
                   type empty;
                   description "High order path far-end block error alarm";
                 }
                 leaf sdh-alarm-hpuneq {
                   type empty;
                   description "High order path unequipped alarm";
                 }
                 leaf sdh-alarm-hpplm {
                   type empty;
                   description "High order path payload level mismatch alarm";
                 }
                 leaf sdh-alarm-loc {
                   type empty;
                   description "Loss of cell delineation alarm";
                 }
                 leaf sdh-alarm-tuais {
                   type empty;
                   description "TU AIS alarm";
                 }
                 leaf sdh-alarm-tulop {
                   type empty;
                   description "TU loss of pointer alarm";
                 }
                 leaf sdh-alarm-turdi {
                   type empty;
                   description "TU remote defect indicator alarm";
                 }
                 leaf sdh-alarm-tuuneq {
                   type empty;
                   description "TU unequipped alarm";
                 }
                 leaf sdh-alarm-tumis {
                   type empty;
                   description "TU label mismatch error";
                 }
                 leaf sdh-alarm-tuloc {
                   type empty;
                   description "TU loss of cell delineation alarm";
                 }
                 leaf ds3-alarm-pll {
                   type empty;
                   description "PLL lock alarm";
                 }
                 leaf ds3-alarm-ais {
                   type empty;
                   description "AIS alarm";
                 }
                 leaf ds3-alarm-lof {
                   type empty;
                   description "Loss of frame alarm";
                 }
                 leaf ds3-alarm-los {
                   type empty;
                   description "Loss of signal alarm";
                 }
                 leaf ds3-alarm-lcv {
                   type empty;
                   description "Line code violation alarm";
                 }
                 leaf ds3-alarm-exz {
                   type empty;
                   description "Excessive zeros alarm";
                 }
                 leaf ds3-alarm-ferf {
                   type empty;
                   description "Far-end receive failure alarm";
                 }
                 leaf ds3-alarm-ylw {
                   type empty;
                   description "Yellow alarm";
                 }
                 leaf ds3-alarm-idle {
                   type empty;
                   description "Idle alarm";
                 }
                 leaf ds1-alarm-ais {
                   type empty;
                   description "AIS alarm";
                 }
                 leaf ds1-alarm-lof {
                   type empty;
                   description "Loss of frame alarm";
                 }
                 leaf ds1-alarm-los {
                   type empty;
                   description "Loss of signal alarm";
                 }
                 leaf ds1-alarm-ylw {
                   type empty;
                   description "Yellow alarm";
                 }
                 leaf ds1-alarm-crc-major {
                   type empty;
                   description "CRC errors crossed major threshold";
                 }
                 leaf ds1-alarm-crc-minor {
                   type empty;
                   description "CRC errors crossed minor threshold";
                 }
                 leaf dsl-alarm-lof {
                   type empty;
                   description "Loss of frame alarm";
                 }
                 leaf dsl-alarm-los {
                   type empty;
                   description "Loss of signal alarm";
                 }
                 leaf dsl-alarm-lom {
                   type empty;
                   description "Loss of multiframe alarm";
                 }
                 leaf dsl-alarm-locdi {
                   type empty;
                   description "Loss of cell delineation alarm for interleaved channel";
                 }
                 leaf dsl-alarm-locdni {
                   type empty;
                   description "Loss of cell delineation alarm for non-interleaved channel";
                 }
                 leaf dsl-alarm-lop {
                   type empty;
                   description "Loss of power alarm";
                 }
                 leaf dsl-alarm-far-lof {
                   type empty;
                   description "Far-end loss-of-frame alarm";
                 }
                 leaf dsl-alarm-far-los {
                   type empty;
                   description "Far-end loss-of-signal alarm";
                 }
                 leaf dsl-alarm-far-locdi {
                   type empty;
                   description "Far-end loss-of-cell-delineation alarm for interleaved channel";
                 }
                 leaf dsl-alarm-far-locdni {
                   type empty;
                   description "Far-end loss-of-cell-delineation alarm for non-interleaved channel";
                 }
                 leaf fibrechannel-alarm-link-down {
                   type empty;
                   description "Link alive failure";
                 }
                 leaf ethernet-alarm-link-down {
                   type empty;
                   description "Link alive failure";
                 }
                 leaf ethernet-alarm-link-local-fault {
                   type empty;
                   description "Link local fault";
                 }
                 leaf ethernet-alarm-link-remote-fault {
                   type empty;
                   description "Link remote fault";
                 }
                 leaf ethernet-alarm-lcdp {
                   type empty;
                   description "Loss of code-group delineation";
                 }
                 leaf isdn-alarm-los {
                   type empty;
                   description "Loss of signal alarm";
                 }
                 leaf isdn-alarm-lof {
                   type empty;
                   description "Loss of frame alarm";
                 }
                 leaf shdsl-alarm-losd {
                   type empty;
                   description "Loss of signal alarm";
                 }
                 leaf shdsl-alarm-losw {
                   type empty;
                   description "Loss of sync word alarm";
                 }
                 leaf shdsl-alarm-line1-losd {
                   type empty;
                   description "Loss of signal (line 1) alarm";
                 }
                 leaf shdsl-alarm-line1-losw {
                   type empty;
                   description "Loss of sync word (line 1) alarm";
                 }
                 leaf shdsl-alarm-line2-losd {
                   type empty;
                   description "Loss of signal (line 2) alarm";
                 }
                 leaf shdsl-alarm-line2-losw {
                   type empty;
                   description "Loss of sync word (line 2) alarm";
                 }
                 leaf shdsl-efm-alarm-losd {
                   type empty;
                   description "Loss of signal alarm";
                 }
                 leaf shdsl-efm-alarm-losw {
                   type empty;
                   description "Loss of sync word alarm";
                 }
                 leaf otn-alarm-los {
                   type empty;
                   description "Loss of signal alarm";
                 }
                 leaf otn-alarm-lof {
                   type empty;
                   description "Loss of frame alarm";
                 }
                 leaf otn-alarm-lom {
                   type empty;
                   description "Loss of multiframe alarm";
                 }
                 leaf otn-alarm-wavelength-lock {
                   type empty;
                   description "Loss of Wavelength Lock alarm";
                 }
                 leaf otn-alarm-otu-ais {
                   type empty;
                   description "OTU Alarm Indication Signal alarm";
                 }
                 leaf otn-alarm-otu-bdi {
                   type empty;
                   description "OTU Background Block Error alarm";
                 }
                 leaf otn-alarm-otu-ttim {
                   type empty;
                   description "OTU Trail Trace Identifier Mismatch alarm";
                 }
                 leaf otn-alarm-otu-iae {
                   type empty;
                   description "OTU Incoming Alignment alarm";
                 }
                 leaf otn-alarm-otu-sd {
                   type empty;
                   description "OTU Signal Degrade alarm";
                 }
                 leaf otn-alarm-otu-sf {
                   type empty;
                   description "OTU Signal Fail alarm";
                 }
                 leaf otn-alarm-otu-biae {
                   type empty;
                   description "OTU Backward Incoming Alignment alarm";
                 }
                 leaf otn-alarm-otu-tsf {
                   type empty;
                   description "OTU Trail Signal Fail alarm";
                 }
                 leaf otn-alarm-otu-ssf {
                   type empty;
                   description "OTU Server Signal Fail alarm";
                 }
                 leaf otn-alarm-otu-fec-excessive {
                   type empty;
                   description "OTU FEC Excessive alarm";
                 }
                 leaf otn-alarm-otu-fec-degraded {
                   type empty;
                   description "OTU FEC Degraded alarm";
                 }
                 leaf otn-alarm-otu-fe-fec-degraded {
                   type empty;
                   description "OTU FE FEC Degraded/Excessive alarm";
                 }
                 leaf otn-alarm-otu-threshold-bbe {
                   type empty;
                   description "OTU Background Block Error threshold alarm";
                 }
                 leaf otn-alarm-otu-threshold-es {
                   type empty;
                   description "OTU Errored Seconds threshold alarm";
                 }
                 leaf otn-alarm-otu-threshold-ses {
                   type empty;
                   description "OTU Severely Errored Seconds threshold alarm";
                 }
                 leaf otn-alarm-otu-threshold-uas {
                   type empty;
                   description "OTU Unavailable Seconds threshold alarm";
                 }
                 leaf otn-alarm-odu-ais {
                   type empty;
                   description "ODU  Alarm Indiaction Signal alarm";
                 }
                 leaf otn-alarm-odu-oci {
                   type empty;
                   description "ODU Open Connection Indication alarm";
                 }
                 leaf otn-alarm-odu-lck {
                   type empty;
                   description "ODU Locked alarm";
                 }
                 leaf otn-alarm-odu-bdi {
                   type empty;
                   description "ODU Backward Defect Indication alarm";
                 }
                 leaf otn-alarm-odu-ttim {
                   type empty;
                   description "ODU Trail Trace Identifier Mismatch alarm";
                 }
                 leaf otn-alarm-odu-sd {
                   type empty;
                   description "ODU Signal Degrade alarm";
                 }
                 leaf otn-alarm-odu-sf {
                   type empty;
                   description "ODU Signal Fail alarm";
                 }
                 leaf otn-alarm-odu-iae {
                   type empty;
                   description "ODU Incoming Alignment alarm";
                 }
                 leaf otn-alarm-odu-ltc {
                   type empty;
                   description "ODU Loss of Tandem Connection alarm";
                 }
                 leaf otn-alarm-odu-csf {
                   type empty;
                   description "ODU Client Signal Fail alarm";
                 }
                 leaf otn-alarm-odu-tsf {
                   type empty;
                   description "ODU Trail Signal Fail alarm";
                 }
                 leaf otn-alarm-odu-ssf {
                   type empty;
                   description "ODU Server Signal Fail alarm";
                 }
                 leaf otn-alarm-odu-rx-aps-change {
                   type empty;
                   description "ODU Rx Aps Change alarm";
                 }
                 leaf otn-alarm-odu-threshold-bbe {
                   type empty;
                   description "ODU Background Block Error threshold alarm";
                 }
                 leaf otn-alarm-odu-threshold-es {
                   type empty;
                   description "ODU Errored Seconds threshold alarm";
                 }
                 leaf otn-alarm-odu-threshold-ses {
                   type empty;
                   description "ODU Severely Errored Seconds threshold alarm";
                 }
                 leaf otn-alarm-odu-threshold-uas {
                   type empty;
                   description "ODU Unavailable Seconds threshold alarm";
                 }
                 leaf otn-alarm-opu-pmi {
                   type empty;
                   description "OPU Payload Mismatch alarm";
                 }
                 leaf otn-alarm-pre-fec-sd {
                   type empty;
                   description "Pre-FEC SD alarm";
                 }
                 leaf otn-alarm-fe-pre-fec-sd {
                   type empty;
                   description "Far end pre-FEC SD alarm";
                 }
                 leaf optics-alarms-mod-fault {
                   type empty;
                   description "Module Fault alarm";
                 }
                 leaf optics-alarms-lol {
                   type empty;
                   description "Loss of Lock alarm";
                 }
                 leaf optics-alarms-los {
                   type empty;
                   description "Loss of Signal alarms";
                 }
                 leaf optics-alarms-lof {
                   type empty;
                   description "Loss of frame alarm";
                 }
                 leaf optics-alarms-lom {
                   type empty;
                   description "Loss of multi-frame alarm";
                 }
                 leaf optics-alarms-otu-bdi {
                   type empty;
                   description "Backward defect indiacation alarm";
                 }
                 leaf optics-alarms-rmsf {
                   type empty;
                   description "Rx Modem sysnc fault alarm";
                 }
                 leaf optics-alarms-rmlol {
                   type empty;
                   description "Rx Modem loss of lock alarm";
                 }
                 leaf optics-alarms-rloa {
                   type empty;
                   description "Rx loss of alignment alarm";
                 }
                 leaf optics-alarms-mbclf {
                   type empty;
                   description "Modulator Bias control loop fail alarm";
                 }
                 leaf optics-alarms-itlaf {
                   type empty;
                   description "ITLA Fault alarm";
                 }
                 leaf optics-alarms-daccf {
                   type empty;
                   description "DAC Calibration Fault alarm";
                 }
                 leaf optics-alarms-adccf {
                   type empty;
                   description "ADC Calibration Fault alarm";
                 }
                 leaf optics-alarms-fec-degrade {
                   type empty;
                   description "FEC Degrade alarm";
                 }
                 leaf optics-alarms-fec-excessive {
                   type empty;
                   description "FEC Excessive alarm";
                 }
                 leaf optics-alarms-fe-fec-degrade {
                   type empty;
                   description "Far-end FEC Degrade alarm";
                 }
                 leaf optics-alarms-fe-fec-excessive {
                   type empty;
                   description "Far-end FEC Excessive alarm";
                 }
                 leaf ima-alarm-startup-fe {
                   type empty;
                   description "IMA group startup far-end alarm";
                 }
                 leaf ima-alarm-config-abort {
                   type empty;
                   description "IMA group config abort alarm";
                 }
                 leaf ima-alarm-config-abort-fe {
                   type empty;
                   description "IMA group config abort far-end alarm";
                 }
                 leaf ima-alarm-insufficient-links {
                   type empty;
                   description "IMA group insufficient links alarm";
                 }
                 leaf ima-alarm-insufficient-links-fe {
                   type empty;
                   description "IMA group insufficient links far-end alarm";
                 }
                 leaf ima-alarm-blocked {
                   type empty;
                   description "IMA group blocked alarm";
                 }
                 leaf ima-alarm-blocked-fe {
                   type empty;
                   description "IMA group blocked far-end alarm";
                 }
                 leaf ima-alarm-timing-mismatch {
                   type empty;
                   description "IMA group timing mismatch alarm";
                 }
                 leaf ima-alarm-version-mismatch {
                   type empty;
                   description "IMA group version mismatch alarm";
                 }
                 leaf ima-alarm-lif {
                   type empty;
                   description "IMA link loss of IMA frame alarm";
                 }
                 leaf ima-alarm-lods {
                   type empty;
                   description "IMA link out of delay synchronization alarm";
                 }
                 leaf ima-alarm-rdi {
                   type empty;
                   description "IMA link remote defect indicator alarm";
                 }
                 leaf ima-alarm-tx-misconnected {
                   type empty;
                   description "IMA link tx misconnected alarm";
                 }
                 leaf ima-alarm-rx-misconnected {
                   type empty;
                   description "IMA link rx misconnected alarm";
                 }
                 leaf ima-alarm-fault {
                   type empty;
                   description "IMA link fault alarm";
                 }
                 leaf ima-alarm-tx-unusable-fe {
                   type empty;
                   description "IMA link Tx unusable far-end alarm";
                 }
                 leaf ima-alarm-rx-unusable-fe {
                   type empty;
                   description "IMA link Tx unusable far-end alarm";
                 }
                 leaf generic-value {
                   type int32;
                   description "Hexadecimal value of unknown flag bits";
                 }
               }
             }
             container active-defects {
               leaf type {
                 type string;
                 description "Media type for associated interface alarms";
               }
               container interface-alarms {
                 leaf alarm-not-present {
                   type empty;
                   description "No alarm indicated";
                 }
                 leaf sonet-alarm-lol {
                   type empty;
                   description "Loss of light alarm";
                 }
                 leaf sonet-alarm-pll {
                   type empty;
                   description "PLL lock alarm";
                 }
                 leaf sonet-alarm-lof {
                   type empty;
                   description "Loss of frame alarm";
                 }
                 leaf sonet-alarm-los {
                   type empty;
                   description "Loss of signal alarm";
                 }
                 leaf sonet-alarm-sef {
                   type empty;
                   description "Severely errored frame alarm";
                 }
                 leaf sonet-alarm-lais {
                   type empty;
                   description "Line AIS alarm";
                 }
                 leaf sonet-alarm-pais {
                   type empty;
                   description "Path AIS alarm";
                 }
                 leaf sonet-alarm-lop {
                   type empty;
                   description "Loss of pointer alarm";
                 }
                 leaf sonet-alarm-berr-sd {
                   type empty;
                   description "Bit error rate alarm, defect";
                 }
                 leaf sonet-alarm-berr-sf {
                   type empty;
                   description "Bit error rate alarm, fault";
                 }
                 leaf sonet-alarm-lrdi {
                   type empty;
                   description "Line remote defect indicator alarm";
                 }
                 leaf sonet-alarm-prdi {
                   type empty;
                   description "Path remote defect indicator alarm";
                 }
                 leaf sonet-alarm-rei {
                   type empty;
                   description "Path remote error indicator alarm";
                 }
                 leaf sonet-alarm-uneq {
                   type empty;
                   description "Unequipped alarm";
                 }
                 leaf sonet-alarm-pmis {
                   type empty;
                   description "Path payload level mismatch alarm";
                 }
                 leaf sonet-alarm-loc {
                   type empty;
                   description "Loss of cell delineation alarm";
                 }
                 leaf sonet-alarm-vais {
                   type empty;
                   description "VT AIS alarm";
                 }
                 leaf sonet-alarm-vlop {
                   type empty;
                   description "VT loss of pointer alarm";
                 }
                 leaf sonet-alarm-vrdi {
                   type empty;
                   description "VT remote defect indicator alarm";
                 }
                 leaf sonet-alarm-vuneq {
                   type empty;
                   description "VT unequipped alarm";
                 }
                 leaf sonet-alarm-vmis {
                   type empty;
                   description "VT label mismatch alarm";
                 }
                 leaf sonet-alarm-vloc {
                   type empty;
                   description "VT loss of cell delineation alarm";
                 }
                 leaf sdh-alarm-lol {
                   type empty;
                   description "Loss of light alarm";
                 }
                 leaf sdh-alarm-pll {
                   type empty;
                   description "PLL lock alarm";
                 }
                 leaf sdh-alarm-lof {
                   type empty;
                   description "Loss of frame alarm";
                 }
                 leaf sdh-alarm-los {
                   type empty;
                   description "Loss of signal alarm";
                 }
                 leaf sdh-alarm-oof {
                   type empty;
                   description "Out of frame alarm";
                 }
                 leaf sdh-alarm-msais {
                   type empty;
                   description "Multiplex section AIS alarm";
                 }
                 leaf sdh-alarm-hpais {
                   type empty;
                   description "High order path AIS alarm";
                 }
                 leaf sdh-alarm-lop {
                   type empty;
                   description "Loss of pointer alarm";
                 }
                 leaf sdh-alarm-berr-sd {
                   type empty;
                   description "Bit error rate alarm, defect";
                 }
                 leaf sdh-alarm-berr-sf {
                   type empty;
                   description "Bit error rate alarm, fault";
                 }
                 leaf sdh-alarm-msferf {
                   type empty;
                   description "Multiplex section far-end remote failure alarm";
                 }
                 leaf sdh-alarm-hpferf {
                   type empty;
                   description "High order path far-end remote failure alarm";
                 }
                 leaf sdh-alarm-hpfebe {
                   type empty;
                   description "High order path far-end block error alarm";
                 }
                 leaf sdh-alarm-hpuneq {
                   type empty;
                   description "High order path unequipped alarm";
                 }
                 leaf sdh-alarm-hpplm {
                   type empty;
                   description "High order path payload level mismatch alarm";
                 }
                 leaf sdh-alarm-loc {
                   type empty;
                   description "Loss of cell delineation alarm";
                 }
                 leaf sdh-alarm-tuais {
                   type empty;
                   description "TU AIS alarm";
                 }
                 leaf sdh-alarm-tulop {
                   type empty;
                   description "TU loss of pointer alarm";
                 }
                 leaf sdh-alarm-turdi {
                   type empty;
                   description "TU remote defect indicator alarm";
                 }
                 leaf sdh-alarm-tuuneq {
                   type empty;
                   description "TU unequipped alarm";
                 }
                 leaf sdh-alarm-tumis {
                   type empty;
                   description "TU label mismatch error";
                 }
                 leaf sdh-alarm-tuloc {
                   type empty;
                   description "TU loss of cell delineation alarm";
                 }
                 leaf ds3-alarm-pll {
                   type empty;
                   description "PLL lock alarm";
                 }
                 leaf ds3-alarm-ais {
                   type empty;
                   description "AIS alarm";
                 }
                 leaf ds3-alarm-lof {
                   type empty;
                   description "Loss of frame alarm";
                 }
                 leaf ds3-alarm-los {
                   type empty;
                   description "Loss of signal alarm";
                 }
                 leaf ds3-alarm-lcv {
                   type empty;
                   description "Line code violation alarm";
                 }
                 leaf ds3-alarm-exz {
                   type empty;
                   description "Excessive zeros alarm";
                 }
                 leaf ds3-alarm-ferf {
                   type empty;
                   description "Far-end receive failure alarm";
                 }
                 leaf ds3-alarm-ylw {
                   type empty;
                   description "Yellow alarm";
                 }
                 leaf ds3-alarm-idle {
                   type empty;
                   description "Idle alarm";
                 }
                 leaf ds1-alarm-ais {
                   type empty;
                   description "AIS alarm";
                 }
                 leaf ds1-alarm-lof {
                   type empty;
                   description "Loss of frame alarm";
                 }
                 leaf ds1-alarm-los {
                   type empty;
                   description "Loss of signal alarm";
                 }
                 leaf ds1-alarm-ylw {
                   type empty;
                   description "Yellow alarm";
                 }
                 leaf ds1-alarm-crc-major {
                   type empty;
                   description "CRC errors crossed major threshold";
                 }
                 leaf ds1-alarm-crc-minor {
                   type empty;
                   description "CRC errors crossed minor threshold";
                 }
                 leaf dsl-alarm-lof {
                   type empty;
                   description "Loss of frame alarm";
                 }
                 leaf dsl-alarm-los {
                   type empty;
                   description "Loss of signal alarm";
                 }
                 leaf dsl-alarm-lom {
                   type empty;
                   description "Loss of multiframe alarm";
                 }
                 leaf dsl-alarm-locdi {
                   type empty;
                   description "Loss of cell delineation alarm for interleaved channel";
                 }
                 leaf dsl-alarm-locdni {
                   type empty;
                   description "Loss of cell delineation alarm for non-interleaved channel";
                 }
                 leaf dsl-alarm-lop {
                   type empty;
                   description "Loss of power alarm";
                 }
                 leaf dsl-alarm-far-lof {
                   type empty;
                   description "Far-end loss-of-frame alarm";
                 }
                 leaf dsl-alarm-far-los {
                   type empty;
                   description "Far-end loss-of-signal alarm";
                 }
                 leaf dsl-alarm-far-locdi {
                   type empty;
                   description "Far-end loss-of-cell-delineation alarm for interleaved channel";
                 }
                 leaf dsl-alarm-far-locdni {
                   type empty;
                   description "Far-end loss-of-cell-delineation alarm for non-interleaved channel";
                 }
                 leaf fibrechannel-alarm-link-down {
                   type empty;
                   description "Link alive failure";
                 }
                 leaf ethernet-alarm-link-down {
                   type empty;
                   description "Link alive failure";
                 }
                 leaf ethernet-alarm-link-local-fault {
                   type empty;
                   description "Link local fault";
                 }
                 leaf ethernet-alarm-link-remote-fault {
                   type empty;
                   description "Link remote fault";
                 }
                 leaf ethernet-alarm-lcdp {
                   type empty;
                   description "Loss of code-group delineation";
                 }
                 leaf isdn-alarm-los {
                   type empty;
                   description "Loss of signal alarm";
                 }
                 leaf isdn-alarm-lof {
                   type empty;
                   description "Loss of frame alarm";
                 }
                 leaf shdsl-alarm-losd {
                   type empty;
                   description "Loss of signal alarm";
                 }
                 leaf shdsl-alarm-losw {
                   type empty;
                   description "Loss of sync word alarm";
                 }
                 leaf shdsl-alarm-line1-losd {
                   type empty;
                   description "Loss of signal (line 1) alarm";
                 }
                 leaf shdsl-alarm-line1-losw {
                   type empty;
                   description "Loss of sync word (line 1) alarm";
                 }
                 leaf shdsl-alarm-line2-losd {
                   type empty;
                   description "Loss of signal (line 2) alarm";
                 }
                 leaf shdsl-alarm-line2-losw {
                   type empty;
                   description "Loss of sync word (line 2) alarm";
                 }
                 leaf shdsl-efm-alarm-losd {
                   type empty;
                   description "Loss of signal alarm";
                 }
                 leaf shdsl-efm-alarm-losw {
                   type empty;
                   description "Loss of sync word alarm";
                 }
                 leaf otn-alarm-los {
                   type empty;
                   description "Loss of signal alarm";
                 }
                 leaf otn-alarm-lof {
                   type empty;
                   description "Loss of frame alarm";
                 }
                 leaf otn-alarm-lom {
                   type empty;
                   description "Loss of multiframe alarm";
                 }
                 leaf otn-alarm-wavelength-lock {
                   type empty;
                   description "Loss of Wavelength Lock alarm";
                 }
                 leaf otn-alarm-otu-ais {
                   type empty;
                   description "OTU Alarm Indication Signal alarm";
                 }
                 leaf otn-alarm-otu-bdi {
                   type empty;
                   description "OTU Background Block Error alarm";
                 }
                 leaf otn-alarm-otu-ttim {
                   type empty;
                   description "OTU Trail Trace Identifier Mismatch alarm";
                 }
                 leaf otn-alarm-otu-iae {
                   type empty;
                   description "OTU Incoming Alignment alarm";
                 }
                 leaf otn-alarm-otu-sd {
                   type empty;
                   description "OTU Signal Degrade alarm";
                 }
                 leaf otn-alarm-otu-sf {
                   type empty;
                   description "OTU Signal Fail alarm";
                 }
                 leaf otn-alarm-otu-biae {
                   type empty;
                   description "OTU Backward Incoming Alignment alarm";
                 }
                 leaf otn-alarm-otu-tsf {
                   type empty;
                   description "OTU Trail Signal Fail alarm";
                 }
                 leaf otn-alarm-otu-ssf {
                   type empty;
                   description "OTU Server Signal Fail alarm";
                 }
                 leaf otn-alarm-otu-fec-excessive {
                   type empty;
                   description "OTU FEC Excessive alarm";
                 }
                 leaf otn-alarm-otu-fec-degraded {
                   type empty;
                   description "OTU FEC Degraded alarm";
                 }
                 leaf otn-alarm-otu-fe-fec-degraded {
                   type empty;
                   description "OTU FE FEC Degraded/Excessive alarm";
                 }
                 leaf otn-alarm-otu-threshold-bbe {
                   type empty;
                   description "OTU Background Block Error threshold alarm";
                 }
                 leaf otn-alarm-otu-threshold-es {
                   type empty;
                   description "OTU Errored Seconds threshold alarm";
                 }
                 leaf otn-alarm-otu-threshold-ses {
                   type empty;
                   description "OTU Severely Errored Seconds threshold alarm";
                 }
                 leaf otn-alarm-otu-threshold-uas {
                   type empty;
                   description "OTU Unavailable Seconds threshold alarm";
                 }
                 leaf otn-alarm-odu-ais {
                   type empty;
                   description "ODU  Alarm Indiaction Signal alarm";
                 }
                 leaf otn-alarm-odu-oci {
                   type empty;
                   description "ODU Open Connection Indication alarm";
                 }
                 leaf otn-alarm-odu-lck {
                   type empty;
                   description "ODU Locked alarm";
                 }
                 leaf otn-alarm-odu-bdi {
                   type empty;
                   description "ODU Backward Defect Indication alarm";
                 }
                 leaf otn-alarm-odu-ttim {
                   type empty;
                   description "ODU Trail Trace Identifier Mismatch alarm";
                 }
                 leaf otn-alarm-odu-sd {
                   type empty;
                   description "ODU Signal Degrade alarm";
                 }
                 leaf otn-alarm-odu-sf {
                   type empty;
                   description "ODU Signal Fail alarm";
                 }
                 leaf otn-alarm-odu-iae {
                   type empty;
                   description "ODU Incoming Alignment alarm";
                 }
                 leaf otn-alarm-odu-ltc {
                   type empty;
                   description "ODU Loss of Tandem Connection alarm";
                 }
                 leaf otn-alarm-odu-csf {
                   type empty;
                   description "ODU Client Signal Fail alarm";
                 }
                 leaf otn-alarm-odu-tsf {
                   type empty;
                   description "ODU Trail Signal Fail alarm";
                 }
                 leaf otn-alarm-odu-ssf {
                   type empty;
                   description "ODU Server Signal Fail alarm";
                 }
                 leaf otn-alarm-odu-rx-aps-change {
                   type empty;
                   description "ODU Rx Aps Change alarm";
                 }
                 leaf otn-alarm-odu-threshold-bbe {
                   type empty;
                   description "ODU Background Block Error threshold alarm";
                 }
                 leaf otn-alarm-odu-threshold-es {
                   type empty;
                   description "ODU Errored Seconds threshold alarm";
                 }
                 leaf otn-alarm-odu-threshold-ses {
                   type empty;
                   description "ODU Severely Errored Seconds threshold alarm";
                 }
                 leaf otn-alarm-odu-threshold-uas {
                   type empty;
                   description "ODU Unavailable Seconds threshold alarm";
                 }
                 leaf otn-alarm-opu-pmi {
                   type empty;
                   description "OPU Payload Mismatch alarm";
                 }
                 leaf otn-alarm-pre-fec-sd {
                   type empty;
                   description "Pre-FEC SD alarm";
                 }
                 leaf otn-alarm-fe-pre-fec-sd {
                   type empty;
                   description "Far end pre-FEC SD alarm";
                 }
                 leaf optics-alarms-mod-fault {
                   type empty;
                   description "Module Fault alarm";
                 }
                 leaf optics-alarms-lol {
                   type empty;
                   description "Loss of Lock alarm";
                 }
                 leaf optics-alarms-los {
                   type empty;
                   description "Loss of Signal alarms";
                 }
                 leaf optics-alarms-lof {
                   type empty;
                   description "Loss of frame alarm";
                 }
                 leaf optics-alarms-lom {
                   type empty;
                   description "Loss of multi-frame alarm";
                 }
                 leaf optics-alarms-otu-bdi {
                   type empty;
                   description "Backward defect indiacation alarm";
                 }
                 leaf optics-alarms-rmsf {
                   type empty;
                   description "Rx Modem sysnc fault alarm";
                 }
                 leaf optics-alarms-rmlol {
                   type empty;
                   description "Rx Modem loss of lock alarm";
                 }
                 leaf optics-alarms-rloa {
                   type empty;
                   description "Rx loss of alignment alarm";
                 }
                 leaf optics-alarms-mbclf {
                   type empty;
                   description "Modulator Bias control loop fail alarm";
                 }
                 leaf optics-alarms-itlaf {
                   type empty;
                   description "ITLA Fault alarm";
                 }
                 leaf optics-alarms-daccf {
                   type empty;
                   description "DAC Calibration Fault alarm";
                 }
                 leaf optics-alarms-adccf {
                   type empty;
                   description "ADC Calibration Fault alarm";
                 }
                 leaf optics-alarms-fec-degrade {
                   type empty;
                   description "FEC Degrade alarm";
                 }
                 leaf optics-alarms-fec-excessive {
                   type empty;
                   description "FEC Excessive alarm";
                 }
                 leaf optics-alarms-fe-fec-degrade {
                   type empty;
                   description "Far-end FEC Degrade alarm";
                 }
                 leaf optics-alarms-fe-fec-excessive {
                   type empty;
                   description "Far-end FEC Excessive alarm";
                 }
                 leaf ima-alarm-startup-fe {
                   type empty;
                   description "IMA group startup far-end alarm";
                 }
                 leaf ima-alarm-config-abort {
                   type empty;
                   description "IMA group config abort alarm";
                 }
                 leaf ima-alarm-config-abort-fe {
                   type empty;
                   description "IMA group config abort far-end alarm";
                 }
                 leaf ima-alarm-insufficient-links {
                   type empty;
                   description "IMA group insufficient links alarm";
                 }
                 leaf ima-alarm-insufficient-links-fe {
                   type empty;
                   description "IMA group insufficient links far-end alarm";
                 }
                 leaf ima-alarm-blocked {
                   type empty;
                   description "IMA group blocked alarm";
                 }
                 leaf ima-alarm-blocked-fe {
                   type empty;
                   description "IMA group blocked far-end alarm";
                 }
                 leaf ima-alarm-timing-mismatch {
                   type empty;
                   description "IMA group timing mismatch alarm";
                 }
                 leaf ima-alarm-version-mismatch {
                   type empty;
                   description "IMA group version mismatch alarm";
                 }
                 leaf ima-alarm-lif {
                   type empty;
                   description "IMA link loss of IMA frame alarm";
                 }
                 leaf ima-alarm-lods {
                   type empty;
                   description "IMA link out of delay synchronization alarm";
                 }
                 leaf ima-alarm-rdi {
                   type empty;
                   description "IMA link remote defect indicator alarm";
                 }
                 leaf ima-alarm-tx-misconnected {
                   type empty;
                   description "IMA link tx misconnected alarm";
                 }
                 leaf ima-alarm-rx-misconnected {
                   type empty;
                   description "IMA link rx misconnected alarm";
                 }
                 leaf ima-alarm-fault {
                   type empty;
                   description "IMA link fault alarm";
                 }
                 leaf ima-alarm-tx-unusable-fe {
                   type empty;
                   description "IMA link Tx unusable far-end alarm";
                 }
                 leaf ima-alarm-rx-unusable-fe {
                   type empty;
                   description "IMA link Tx unusable far-end alarm";
                 }
                 leaf generic-value {
                   type int32;
                   description "Hexadecimal value of unknown flag bits";
                 }
               }
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-payload-pointer-information {
               leaf sonet-payload-pointer-curptr {
                 type string;
                 description "Value of the SONET/SDH payload pointer, derived from the H1 and H2 overhead bytes";
               }
               leaf sonet-payload-pointer-ptrinc-count {
                 type string;
                 description "Number of times the value of the SONET/SDH payload pointer had positive justification";
               }
               leaf sonet-payload-pointer-ptrdec-count {
                 type string;
                 description "Number of times the value of the SONET/SDH payload pointer had negative justification";
               }
               leaf sonet-payload-pointer-newptr-ndf-count {
                 type string;
                 description "Number of times a new payload pointer was created with the New Data Found flag set";
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               leaf optic-diagnostics-not-available {
                 type string;
                 description "Optical diagnostics not supported by this transceiver";
               }
               leaf laser-bias-current-not-available {
                 type string;
                 description "Laser bias current measurement not available";
               }
               leaf soa-bias-current-not-available {
                 type string;
                 description "SOA bias current measurement not available";
               }
               leaf laser-tx-power-not-available {
                 type string;
                 description "Laser output power measurement not available";
               }
               leaf module-temperature-not-available {
                 type string;
                 description "Module temperature measurement not available";
               }
               leaf tx-module-temperature-not-available {
                 type string;
                 description "Tx module temperature measurement not available";
               }
               leaf rx-module-temperature-not-available {
                 type string;
                 description "Rx module temperature measurement not available";
               }
               leaf laser-rx-power-not-available {
                 type string;
                 description "Laser receiver optical power measurement not available";
               }
               leaf laser-tx-power-high-alarm-threshold-not-available {
                 type string;
                 description "Laser output power high alarm threshold not available";
               }
               leaf laser-tx-power-low-alarm-threshold-not-available {
                 type string;
                 description "Laser output power low alarm threshold not available";
               }
               leaf laser-tx-power-high-warning-threshold-not-available {
                 type string;
                 description "Laser output power high warning threshold not available";
               }
               leaf laser-tx-power-low-warning-threshold-not-available {
                 type string;
                 description "Laser output power low warning threshold not available";
               }
               leaf laser-bias-current {
                 type string;
                 description "Laser bias current (milliamperes)";
               }
               leaf soa-bias-current {
                 type string;
                 description "SOA bias current (milliamperes)";
               }
               leaf laser-output-power {
                 type string;
                 description "Laser output power (milliwatts)";
               }
               leaf laser-output-power-dbm {
                 type string;
                 description "Laser output power (dBm)";
               }
               leaf module-temperature {
                 type string;
                 description "Module temperature";
               }
               leaf tx-module-temperature {
                 type string;
                 description "Tx module temperature";
               }
               leaf rx-module-temperature {
                 type string;
                 description "Rx module temperature";
               }
               leaf module-voltage {
                 type string;
                 description "Module voltage";
               }
               leaf corrected-error-ratio {
                 type string;
                 description "Corrected error ratio";
               }
               leaf uncorrected-words-ratio {
                 type string;
                 description "Uncorrected words ratio";
               }
               leaf tx-module-voltage {
                 type string;
                 description "Tx module voltage";
               }
               leaf rx-module-voltage {
                 type string;
                 description "Rx module voltage";
               }
               leaf rx-signal-avg-optical-power {
                 type string;
                 description "Receiver signal average power (milliwatts)";
               }
               leaf rx-signal-avg-optical-power-dbm {
                 type string;
                 description "Receiver signal average power (dBm)";
               }
               leaf laser-rx-optical-power {
                 type string;
                 description "Laser receiver optical power (milliwatts)";
               }
               leaf laser-rx-optical-power-dbm {
                 type string;
                 description "Laser receiver optical power (dBm)";
               }
               leaf wavelength-channel {
                 type string;
                 description "Wavelength channel number set";
               }
               leaf wavelength-setpoint {
                 type string;
                 description "Wavelength point set";
               }
               leaf tx-dither {
                 type string;
                 description "Tx dither status";
               }
               leaf frequency-error {
                 type string;
                 description "Frequency error value";
               }
               leaf wavelength-error {
                 type string;
                 description "Wavelength error value";
               }
               leaf laser-bias-current-high-alarm {
                 type string;
                 description "Laser bias current high alarm";
               }
               leaf laser-bias-current-low-alarm {
                 type string;
                 description "Laser bias current low alarm";
               }
               leaf laser-bias-current-high-warn {
                 type string;
                 description "Laser bias current high warning";
               }
               leaf laser-bias-current-low-warn {
                 type string;
                 description "Laser bias current low warning";
               }
               leaf soa-bias-current-high-alarm {
                 type string;
                 description "SOA bias current high alarm";
               }
               leaf soa-bias-current-low-alarm {
                 type string;
                 description "SOA bias current low alarm";
               }
               leaf soa-bias-current-high-warn {
                 type string;
                 description "SOA bias current high warning";
               }
               leaf soa-bias-current-low-warn {
                 type string;
                 description "SOA bias current low warning";
               }
               leaf laser-tx-power-high-alarm {
                 type string;
                 description "Laser output power high alarm";
               }
               leaf laser-tx-power-low-alarm {
                 type string;
                 description "Laser output power low alarm";
               }
               leaf laser-tx-power-high-warn {
                 type string;
                 description "Laser output power high warning";
               }
               leaf laser-tx-power-low-warn {
                 type string;
                 description "Laser output power low warning";
               }
               leaf tx-power-high-alarm {
                 type string;
                 description "Tx power high alarm";
               }
               leaf tx-power-low-alarm {
                 type string;
                 description "Tx power low alarm";
               }
               leaf tx-power-high-warn {
                 type string;
                 description "Tx power high warning";
               }
               leaf tx-power-low-warn {
                 type string;
                 description "Tx power low warning";
               }
               leaf module-temperature-high-alarm {
                 type string;
                 description "Module temperature high alarm";
               }
               leaf module-temperature-low-alarm {
                 type string;
                 description "Module temperature low alarm";
               }
               leaf module-temperature-high-warn {
                 type string;
                 description "Module temperature high warning";
               }
               leaf module-temperature-low-warn {
                 type string;
                 description "Module temperature low warning";
               }
               leaf tx-module-temperature-high-alarm {
                 type string;
                 description "Tx module temperature high alarm";
               }
               leaf tx-module-temperature-low-alarm {
                 type string;
                 description "Tx module temperature low alarm";
               }
               leaf rx-module-temperature-high-alarm {
                 type string;
                 description "Rx module temperature high alarm";
               }
               leaf rx-module-temperature-low-alarm {
                 type string;
                 description "Rx module temperature low alarm";
               }
               leaf module-voltage-high-alarm {
                 type string;
                 description "Module voltage high alarm";
               }
               leaf module-voltage-low-alarm {
                 type string;
                 description "Module voltage low alarm";
               }
               leaf module-voltage-high-warn {
                 type string;
                 description "Module voltage high warning";
               }
               leaf module-voltage-low-warn {
                 type string;
                 description "Module voltage low warning";
               }
               leaf tx-module-voltage-high-alarm {
                 type string;
                 description "Tx module voltage high alarm";
               }
               leaf tx-module-voltage-low-alarm {
                 type string;
                 description "Tx module voltage low alarm";
               }
               leaf rx-module-voltage-high-alarm {
                 type string;
                 description "Rx module voltage high alarm";
               }
               leaf rx-module-voltage-low-alarm {
                 type string;
                 description "Rx module voltage low alarm";
               }
               leaf laser-rx-power-high-alarm {
                 type string;
                 description "Laser receiver power high alarm";
               }
               leaf laser-rx-power-low-alarm {
                 type string;
                 description "Laser receiver power low alarm";
               }
               leaf laser-rx-power-high-warn {
                 type string;
                 description "Laser receiver power high warning";
               }
               leaf laser-rx-power-low-warn {
                 type string;
                 description "Laser receiver power low warning";
               }
               leaf rx-power-high-alarm {
                 type string;
                 description "Receiver power high alarm";
               }
               leaf rx-power-low-alarm {
                 type string;
                 description "Receiver power low alarm";
               }
               leaf rx-power-high-warn {
                 type string;
                 description "Receiver power high warning";
               }
               leaf rx-power-low-warn {
                 type string;
                 description "Receiver power low warning";
               }
               leaf laser-end-of-life-alarm {
                 type string;
                 description "Laser end-of-life alarm";
               }
               leaf laser-wavelength-alarm {
                 type string;
                 description "Laser wavelength alarm";
               }
               leaf laser-bias-current-alarm {
                 type string;
                 description "Laser bias current alarm";
               }
               leaf module-temperature-alarm {
                 type string;
                 description "Module temperature alarm";
               }
               leaf laser-power-alarm {
                 type string;
                 description "Laser power alarm";
               }
               leaf modulator-temperature-alarm {
                 type string;
                 description "Modulator temperature alarm";
               }
               leaf modulator-bias-alarm {
                 type string;
                 description "Modulator bias alarm";
               }
               leaf module-not-ready-alarm {
                 type string;
                 description "Module not ready alarm";
               }
               leaf module-power-down-alarm {
                 type string;
                 description "Module power down alarm";
               }
               leaf module-not-init-done-alarm {
                 type string;
                 description "Module initialization not done alarm";
               }
               leaf module-not-high-power-on-alarm {
                 type string;
                 description "Module not high powered on alarm";
               }
               leaf module-fault-alarm {
                 type string;
                 description "Module in fault state alarm";
               }
               leaf pld-flash-init-fault-alarm {
                 type string;
                 description "PLD or Flash initialization fault alarm";
               }
               leaf power-supply-fault-alarm {
                 type string;
                 description "Power supply fault alarm";
               }
               leaf checksum-fault-alarm {
                 type string;
                 description "Checksum fault alarm";
               }
               leaf apd-supply-fault-alarm {
                 type string;
                 description "APD supply fault alarm";
               }
               leaf tec-fault-alarm {
                 type string;
                 description "TEC fault alarm";
               }
               leaf wavelength-unlocked-alarm {
                 type string;
                 description "Wavelength unlocked alarm";
               }
               leaf tx-tune-alarm {
                 type string;
                 description "Tx tune alarm";
               }
               leaf tx-mux-fifo-error-alarm {
                 type string;
                 description "Tx multiplexer fifo error alarm";
               }
               leaf tx-loss-of-pll-alarm {
                 type string;
                 description "Tx loss of PLL alarm";
               }
               leaf tx-data-not-ready-alarm {
                 type string;
                 description "Tx data not ready alarm";
               }
               leaf tx-not-ready-alarm {
                 type string;
                 description "Tx not ready alarm";
               }
               leaf tx-laser-fault-alarm {
                 type string;
                 description "Tx laser fault alarm";
               }
               leaf tx-laser-disabled-alarm {
                 type string;
                 description "Tx laser disabled alarm";
               }
               leaf tx-loss-of-signal-functionality-alarm {
                 type string;
                 description "Tx loss of signal functionality alarm";
               }
               leaf tx-cdr-loss-of-lock-alarm {
                 type string;
                 description "Tx CDR loss of lock alarm";
               }
               leaf rx-loss-avg-opt-power-alarm {
                 type string;
                 description "Receiver loss of average optical power alarm";
               }
               leaf rx-loss-ac-power-alarm {
                 type string;
                 description "Receiver loss of AC power alarm";
               }
               leaf rx-loss-of-pll-alarm {
                 type string;
                 description "Receiver loss of PLL alarm";
               }
               leaf rx-not-ready-alarm {
                 type string;
                 description "Receiver not ready alarm";
               }
               leaf rx-loss-of-signal-alarm {
                 type string;
                 description "Receiver loss of signal alarm";
               }
               leaf rx-cdr-loss-of-lock-alarm {
                 type string;
                 description "Receiver CDR loss of lock alarm";
               }
               leaf laser-bias-current-high-alarm-threshold {
                 type string;
                 description "Laser bias current high alarm threshold (milliamperes)";
               }
               leaf laser-bias-current-low-alarm-threshold {
                 type string;
                 description "Laser bias current low alarm threshold (milliamperes)";
               }
               leaf laser-bias-current-high-warn-threshold {
                 type string;
                 description "Laser bias current high warning threshold (milliamperes)";
               }
               leaf laser-bias-current-low-warn-threshold {
                 type string;
                 description "Laser bias current low warning threshold (milliamperes)";
               }
               leaf soa-bias-current-high-alarm-threshold {
                 type string;
                 description "SOA bias current high alarm threshold (milliamperes)";
               }
               leaf soa-bias-current-low-alarm-threshold {
                 type string;
                 description "SOA bias current low alarm threshold (milliamperes)";
               }
               leaf soa-bias-current-high-warn-threshold {
                 type string;
                 description "SOA bias current high warning threshold (milliamperes)";
               }
               leaf soa-bias-current-low-warn-threshold {
                 type string;
                 description "SOA bias current low warning threshold (milliamperes)";
               }
               leaf laser-tx-power-high-alarm-threshold {
                 type string;
                 description "Laser transmitter power high alarm threshold (milliwatts)";
               }
               leaf laser-tx-power-high-alarm-threshold-dbm {
                 type string;
                 description "Laser transmitter power high alarm threshold (dBm)";
               }
               leaf laser-tx-power-low-alarm-threshold {
                 type string;
                 description "Laser transmitter power low alarm threshold (milliwatts)";
               }
               leaf laser-tx-power-low-alarm-threshold-dbm {
                 type string;
                 description "Laser transmitter power low alarm threshold (dBm)";
               }
               leaf laser-tx-power-high-warn-threshold {
                 type string;
                 description "Laser transmitter power high warning threshold (milliwatts)";
               }
               leaf laser-tx-power-high-warn-threshold-dbm {
                 type string;
                 description "Laser transmitter power high warning threshold (dBm)";
               }
               leaf laser-tx-power-low-warn-threshold {
                 type string;
                 description "Laser transmitter power low warning threshold (milliwatts)";
               }
               leaf laser-tx-power-low-warn-threshold-dbm {
                 type string;
                 description "Laser transmitter power low warning threshold (dBm)";
               }
               leaf module-temperature-high-alarm-threshold {
                 type string;
                 description "Module temperature high alarm threshold";
               }
               leaf module-temperature-low-alarm-threshold {
                 type string;
                 description "Module temperature low alarm threshold";
               }
               leaf module-temperature-high-warn-threshold {
                 type string;
                 description "Module temperature high warning threshold";
               }
               leaf module-temperature-low-warn-threshold {
                 type string;
                 description "Module temperature low warning threshold";
               }
               leaf laser-temperature-high-alarm-threshold {
                 type string;
                 description "Laser temperature high alarm threshold";
               }
               leaf laser-temperature-low-alarm-threshold {
                 type string;
                 description "Laser temperature low alarm threshold";
               }
               leaf laser-temperature-high-warn-threshold {
                 type string;
                 description "Laser temperature high warning threshold";
               }
               leaf laser-temperature-low-warn-threshold {
                 type string;
                 description "Laser temperature low warning threshold";
               }
               leaf module-voltage-high-alarm-threshold {
                 type string;
                 description "Module voltage high alarm threshold (volts)";
               }
               leaf module-voltage-low-alarm-threshold {
                 type string;
                 description "Module voltage low alarm threshold (volts)";
               }
               leaf module-voltage-high-warn-threshold {
                 type string;
                 description "Module voltage high warning threshold (volts)";
               }
               leaf module-voltage-low-warn-threshold {
                 type string;
                 description "Module voltage low warning threshold (volts)";
               }
               leaf laser-rx-power-high-alarm-threshold {
                 type string;
                 description "Laser receiver power high alarm (milliwatts)";
               }
               leaf laser-rx-power-high-alarm-threshold-dbm {
                 type string;
                 description "Laser receiver power high alarm (dBm)";
               }
               leaf laser-rx-power-low-alarm-threshold {
                 type string;
                 description "Laser receiver power low alarm (milliwatts)";
               }
               leaf laser-rx-power-low-alarm-threshold-dbm {
                 type string;
                 description "Laser receiver power low alarm (dBm)";
               }
               leaf laser-rx-power-high-warn-threshold {
                 type string;
                 description "Laser receiver power high warning (milliwatts)";
               }
               leaf laser-rx-power-high-warn-threshold-dbm {
                 type string;
                 description "Laser receiver power high warning (dBm)";
               }
               leaf laser-rx-power-low-warn-threshold {
                 type string;
                 description "Laser receiver power low warning (milliwatts)";
               }
               leaf laser-rx-power-low-warn-threshold-dbm {
                 type string;
                 description "Laser receiver power low warning (dBm)";
               }
               leaf rx-power-high-alarm-threshold {
                 type string;
                 description "Receiver power high alarm (milliwatts)";
               }
               leaf rx-power-high-alarm-threshold-dbm {
                 type string;
                 description "Receiver power high alarm (dBm)";
               }
               leaf rx-power-low-alarm-threshold {
                 type string;
                 description "Receiver power low alarm (milliwatts)";
               }
               leaf rx-power-low-alarm-threshold-dbm {
                 type string;
                 description "Receiver power low alarm (dBm)";
               }
               leaf rx-power-high-warning-threshold {
                 type string;
                 description "Receiver power high warning (milliwatts)";
               }
               leaf rx-power-high-warning-threshold-dbm {
                 type string;
                 description "Receiver power high warning (dBm)";
               }
               leaf rx-power-low-warning-threshold {
                 type string;
                 description "Receiver power low warning (milliwatts)";
               }
               leaf rx-power-low-warning-threshold-dbm {
                 type string;
                 description "Receiver power low warning (dBm)";
               }
               leaf los-alarm-threshold {
                 type string;
                 description "LOS alarm threshold (milliwatts)";
               }
               leaf los-alarm-threshold-dbm {
                 type string;
                 description "LOS alarm threshold (dBm)";
               }
               leaf los-warning-threshold {
                 type string;
                 description "LOS warning threshold (milliwatts)";
               }
               leaf los-warning-threshold-dbm {
                 type string;
                 description "LOS warning threshold (dBm)";
               }
               leaf dsp-module-state {
                 type string;
                 description "DSP module state";
               }
               leaf output-power {
                 type string;
                 description "Output power (milliwatts)";
               }
               leaf output-power-dbm {
                 type string;
                 description "Output power (dBm)";
               }
               leaf input-power {
                 type string;
                 description "Input power (milliwatts)";
               }
               leaf input-power-dbm {
                 type string;
                 description "Input power (dBm)";
               }
               leaf per-wave-rx-optical-power {
                 type string;
                 description "Per-wavelength receiver optical power (milliwatts)";
               }
               leaf per-wave-rx-optical-power-dbm {
                 type string;
                 description "Per-wavelength receiver optical power (dBm)";
               }
               leaf lane-laser-frequency-error {
                 type string;
                 description "Lane laser frequency error (MHz)";
               }
               leaf tec-current {
                 type string;
                 description "Tec current";
               }
               leaf residual-isi {
                 type string;
                 description "Residual ISI";
               }
               container optics-diagnostics-ot {
                 leaf module-temp-fault {
                   type string;
                   description "Module temperature fault";
                 }
                 leaf specific-hw-fault {
                   type string;
                   description "Specific HW fault";
                 }
                 leaf internal-power-fault {
                   type string;
                   description "Internal power fault";
                 }
                 leaf post-therm-fault {
                   type string;
                   description "Power thermal fault";
                 }
                 leaf post-fault {
                   type string;
                   description "Post fault";
                 }
                 leaf command-error {
                   type string;
                   description "Command error";
                 }
                 leaf rx-pll-lock {
                   type string;
                   description "RX PLL lock";
                 }
                 leaf network-lane-los {
                   type string;
                   description "Network Lane LOS";
                 }
                 leaf network-lane-lof {
                   type string;
                   description "Network Lane LOF";
                 }
                 leaf network-lane-oof {
                   type string;
                   description "Network Lane OOF";
                 }
                 leaf network-lane-lom {
                   type string;
                   description "Network Lane LOM";
                 }
                 leaf network-lane-oom {
                   type string;
                   description "Network Lane OOM";
                 }
                 leaf network-lane-otu-bdi {
                   type string;
                   description "Network Lane OTU BDI";
                 }
                 leaf lane-rx-fifo-error {
                   type string;
                   description "Lane RX FIFO error";
                 }
                 leaf tx-reference-clock-fault {
                   type string;
                   description "TX reference clock fault";
                 }
                 leaf rx-modem-sync-fault {
                   type string;
                   description "Rx modem sync fault";
                 }
                 leaf rx-modem-loss-of-lock {
                   type string;
                   description "RX modem loss of lock";
                 }
                 leaf rx-loss-of-alignment {
                   type string;
                   description "RX loss of alignment";
                 }
                 leaf rx-out-of-alignment {
                   type string;
                   description "RX out of alignment";
                 }
                 leaf rx-timing-fault {
                   type string;
                   description "Rx timing fault";
                 }
                 leaf link-msg-data-available {
                   type string;
                   description "Link msg data available";
                 }
                 leaf modulator-bias-control-loop-fail {
                   type string;
                   description "Modulator Bias Control Loop Fail";
                 }
                 leaf itla-fault {
                   type string;
                   description "ITLA fault";
                 }
                 leaf dac-calib-fault {
                   type string;
                   description "DAC calib fault";
                 }
                 leaf adc-calib-fault {
                   type string;
                   description "ADC calib fault";
                 }
                 leaf prom-fault {
                   type string;
                   description "PROM fault";
                 }
                 leaf tx-mod-bias-voa-ctrl-loop-high-alarm {
                   type string;
                   description "TX mod bias VOA ctrl loop high alarm";
                 }
                 leaf tx-mod-bias-voa-ctrl-loop-low-alarm {
                   type string;
                   description "TX mod bias VOA ctrl loop low alarm";
                 }
                 leaf rx-phase-control-loop-high-alarm {
                   type string;
                   description "RX phase control loop high alarm";
                 }
                 leaf rx-phase-control-loop-low-alarm {
                   type string;
                   description "RX phase control loop low alarm";
                 }
                 leaf rx-phase-control-loop-high-warning {
                   type string;
                   description "RX phase control loop high warning";
                 }
                 leaf rx-phase-control-loop-low-warning {
                   type string;
                   description "RX phase control loop low warning";
                 }
                 leaf oa-pump-bias-current-high-alarm {
                   type string;
                   description "OA pump bias current high alarm";
                 }
                 leaf oa-pump-bias-current-low-alarm {
                   type string;
                   description "OA pump bias current low alarm";
                 }
                 leaf oa-pump-bias-current-high-warning {
                   type string;
                   description "OA pump bias current high warning";
                 }
                 leaf oa-pump-bias-current-low-warning {
                   type string;
                   description "OA pump bias current low warning";
                 }
                 leaf tx-jitter-pll-lol-input-nw-lane {
                   type string;
                   description "Tx jitter PLL LOL i/p nw lane";
                 }
                 leaf tx-out-of-alignment {
                   type string;
                   description "TX out of alignment";
                 }
                 leaf tx-cmu-lock-fault {
                   type string;
                   description "Tx CMU lock fault";
                 }
                 leaf adc-signal-below-threshold {
                   type string;
                   description "ADC signal below threshold";
                 }
                 leaf tx-output-power-adjustment-fault {
                   type string;
                   description "Tx output power adjustment fault";
                 }
                 leaf tx-output-mod-converge-fault {
                   type string;
                   description "TX output mod converge fault";
                 }
                 leaf tx-laser-ready-fault {
                   type string;
                   description "Tx laser ready fault";
                 }
                 leaf tx-laser-ready-off-fault {
                   type string;
                   description "Tx laser ready off fault";
                 }
                 leaf tx-asic-ready-fault {
                   type string;
                   description "Tx asic ready fault";
                 }
                 leaf tx-initialization-fault {
                   type string;
                   description "Tx initialization fault";
                 }
                 leaf rx-demodulator-lock-fault {
                   type string;
                   description "Rx demodulator lock fault";
                 }
                 leaf rx-dispersion-lock-fault {
                   type string;
                   description "Rx dispersion lock fault";
                 }
                 leaf rx-adc-output-fault {
                   type string;
                   description "Rx ADC output fault";
                 }
                 leaf rx-optical-input-fault {
                   type string;
                   description "Rx optical input fault";
                 }
                 leaf rx-asic-ready-fault {
                   type string;
                   description "Rx asic ready fault";
                 }
                 leaf rx-initialization-fault {
                   type string;
                   description "Rx initialization fault";
                 }
                 leaf tx-mod-bias-high-alarm {
                   type string;
                   description "TX modulator bias high alarm";
                 }
                 leaf tx-mod-bias-low-alarm {
                   type string;
                   description "TX modulator bias low alarm";
                 }
                 leaf tx-mod-bias-high-warning {
                   type string;
                   description "TX modulator bias high warning";
                 }
                 leaf tx-mod-bias-low-warning {
                   type string;
                   description "TX modulator bias low warning";
                 }
                 leaf rx-pwr-high-alarm {
                   type string;
                   description "RX power high alarm";
                 }
                 leaf rx-pwr-low-alarm {
                   type string;
                   description "RX power low alarm";
                 }
                 leaf rx-pwr-high-warn {
                   type string;
                   description "RX power high warning";
                 }
                 leaf rx-pwr-low-warn {
                   type string;
                   description "RX power low warning";
                 }
                 leaf tx-laser-power-high-alarm {
                   type string;
                   description "TX laser power high alarm";
                 }
                 leaf tx-laser-power-low-alarm {
                   type string;
                   description "TX laser power low alarm";
                 }
                 leaf tx-laser-power-high-warn {
                   type string;
                   description "TX laser power high warning";
                 }
                 leaf tx-laser-power-low-warn {
                   type string;
                   description "TX laser power low warning";
                 }
                 leaf tx-bias-high-alarm {
                   type string;
                   description "TX laser current high alarm";
                 }
                 leaf tx-bias-low-alarm {
                   type string;
                   description "TX laser current low alarm";
                 }
                 leaf tx-bias-high-warn {
                   type string;
                   description "TX laser current high warning";
                 }
                 leaf tx-bias-low-warn {
                   type string;
                   description "TX laser current low warning";
                 }
                 leaf tx-laser-temp-high-alarm {
                   type string;
                   description "TX laser temperature high alarm";
                 }
                 leaf tx-laser-temp-low-alarm {
                   type string;
                   description "TX laser temperature low alarm";
                 }
                 leaf tx-laser-temp-high-warn {
                   type string;
                   description "TX laser temperature high warning";
                 }
                 leaf tx-laser-temp-low-warn {
                   type string;
                   description "TX laser temperature low warning";
                 }
               }
             }
             list optics-diagnostics-vendor-extension {
               leaf optics-vendor-part-number {
                 type string;
                 description "Optics component vendor part number";
               }
               leaf optics-vendor-material-number {
                 type string;
                 description "Optic component vendor material number";
               }
             }
           }
         }
         container src-information {
           leaf src-chassis-name {
             type string;
             description "Source chassis name";
           }
           leaf src-fpc {
             type int32;
             description "Source FPC";
           }
           leaf-list src-pfe-id {
             type int32;
             description "Source PFE id";
           }
         }
         container peer-configuration-status {
           leaf peer-nonmatching-dlci {
             type int32;
             description "DCE end DLCIs that does not match the DTE";
           }
         }
         container lmi-statistics {
           leaf lmi-statistics-dte-descriptor {
             type string;
             description "DTE interface statistics";
           }
           leaf lmi-enquiries-sent {
             type int32;
             description "Number of enquiry packets sent";
           }
           leaf lmi-full-enquiries-sent {
             type int32;
             description "Number of full enquiry packets sent";
           }
           leaf lmi-enquiry-responses-received {
             type int32;
             description "Number of enquiry response packets received";
           }
           leaf lmi-full-enquiry-responses-received {
             type int32;
             description "Number of full enquiry packets received";
           }
           leaf lmi-statistics-dce-descriptor {
             type string;
             description "DCE interface statistics";
           }
           leaf lmi-enquiries-received {
             type int32;
             description "Number of enquiry packets received";
           }
           leaf lmi-full-enquiries-received {
             type int32;
             description "Number of full enquiry packets received";
           }
           leaf lmi-enquiry-responses-sent {
             type int32;
             description "Number of enquiry response packets sent";
           }
           leaf lmi-full-enquiry-responses-sent {
             type int32;
             description "Number of full enquiry response packets sent";
           }
           leaf lmi-statistics-common-descriptor {
             type string;
             description "Statistics common to DTE and DCE";
           }
           leaf lmi-unknown-messages-received {
             type int32;
             description "Number of packets received that do not contain valid messages";
           }
           leaf lmi-asynchronous-updates-received {
             type int32;
             description "Number of ifstate change updates received";
           }
           leaf lmi-out-of-sequence {
             type int32;
             description "Number of packets received in unexpected sequence";
           }
           leaf lmi-keepalive-responses-timeout {
             type int32;
             description "Number of times, the timer for keepalive packets expired";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description "Drop statistics due to stp state at ingress in bytes";
           }
           leaf stp-output-bytes-dropped {
             type int32;
             description "Drop statistics due to stp state at egress in bytes";
           }
           leaf stp-input-packets-dropped {
             type int32;
             description "Drop statistics due to stp state at ingress in packets";
           }
           leaf stp-output-packets-dropped {
             type int32;
             description "Drop statistics due to stp state at egress in packets";
           }
         }
         container af-info {
           leaf af-bw {
             type string;
           }
           leaf af-gnf-id {
             type string;
           }
           leaf af-collapsed-fwd-mode {
             type string;
           }
         }
         container af-fe-info {
           list fe-info {
             leaf fe-num {
               type string;
             }
             leaf fe-bw {
               type string;
             }
             leaf fe-state {
               type string;
             }
             leaf fe-tx-packets {
               type uint64;
             }
             leaf fe-tx-bytes {
               type uint64;
             }
           }
         }
         list af-fe-res-info {
           leaf fe-res-tx-packets {
             type uint64;
           }
           leaf fe-res-tx-bytes {
             type uint64;
           }
         }
         container af-fe-q-pkts {
           list fe-q-pkts-info {
             leaf fe-number {
               type string;
             }
             leaf fe-high-tx-packets {
               type uint64;
             }
             leaf fe-low-tx-packets {
               type uint64;
             }
           }
         }
         container af-fe-q-bytes {
           list fe-q-bytes-info {
             leaf fe-number {
               type string;
             }
             leaf fe-high-tx-bytes {
               type uint64;
             }
             leaf fe-low-tx-bytes {
               type uint64;
             }
           }
         }
         list af-fe-q-res-pkts {
           leaf fe-res-high-tx-packets {
             type uint64;
           }
           leaf fe-res-low-tx-packets {
             type uint64;
           }
         }
         list af-fe-q-res-bytes {
           leaf fe-res-high-tx-bytes {
             type uint64;
           }
           leaf fe-res-low-tx-bytes {
             type uint64;
           }
         }
         list af-collapsed-fwd-stats-mode-disp {
           leaf af-collapsed-fwd-mode-disp {
             type string;
           }
         }
         list af-collapsed-fwd-stats-pkts {
           leaf af-optimal-packets {
             type uint64;
           }
           leaf af-non-optimal-packets {
             type uint64;
           }
         }
         list af-collapsed-fwd-stats-bytes {
           leaf af-optimal-bytes {
             type uint64;
           }
           leaf af-non-optimal-bytes {
             type uint64;
           }
         }
         container queue-num-forwarding-class-name-map {
           leaf queue-number {
             type int32;
             description "Queue number";
           }
           leaf forwarding-class-name {
             type string;
             description "Forwarding class name associated with queue";
           }
         }
         container chassis-queue-counters {
           container interface-chassis-cos-summary {
             leaf intf-cos-chassis-num-queues-supported {
               type int32;
               description "Number of Packet Forwarding Engine chassis queues the interface supports";
             }
             leaf intf-cos-chassis-num-queues-in-use {
               type int32;
               description "Number of Packet Forwarding Engine chassis queues in use on the interface";
             }
           }
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-state {
           leaf media-type {
             type string;
             description "Type of media this information is for";
           }
           leaf ima-state-line {
             type string;
             description "Line state of IMA link";
           }
           leaf ima-state-near-end {
             type string;
             description "Near-end states of IMA group/link";
           }
           leaf ima-state-far-end {
             type string;
             description "Far-end states of IMA group/link";
           }
         }
         container ima-group-information {
           list media-alarm {
             leaf media-alarm-name {
               type string;
             }
             leaf media-alarm-seconds {
               type int32;
             }
             leaf media-alarm-count {
               type int32;
             }
             leaf media-alarm-state {
               type string;
             }
           }
         }
         container ima-link-information {
           list media-alarm {
             leaf media-alarm-name {
               type string;
             }
             leaf media-alarm-seconds {
               type int32;
             }
             leaf media-alarm-count {
               type int32;
             }
             leaf media-alarm-state {
               type string;
             }
           }
         }
         container ethernet-mac-pfc-statistics {
           leaf mac-pfc-dot1p {
             type int32;
           }
           leaf input-mac-pfc-frames {
             type int32;
           }
           leaf output-mac-pfc-frames {
             type int32;
           }
         }
         container satop-information {
           leaf ce-payload-size {
             type int32;
           }
           leaf ce-idle-pattern {
             type string;
           }
           leaf ce-octet-aligned {
             type string;
           }
           leaf ce-jitter-buffer-packets {
             type int32;
           }
           leaf ce-jitter-buffer-latency {
             type int32;
           }
           leaf ce-jitter-buffer-auto-adjust {
             type string;
           }
           leaf ce-excessive-packet-loss-rate-sample-period {
             type int32;
           }
           leaf ce-excessive-packet-loss-rate-threshold {
             type int32;
           }
         }
         container cesopsn-information {
           leaf ce-packetization-latency {
             type int32;
           }
           leaf ce-idle-pattern {
             type string;
           }
           leaf ce-jitter-buffer-packets {
             type int32;
           }
           leaf ce-jitter-buffer-latency {
             type int32;
           }
           leaf ce-jitter-buffer-auto-adjust {
             type string;
           }
           leaf ce-excessive-packet-loss-rate-sample-period {
             type int32;
           }
           leaf ce-excessive-packet-loss-rate-threshold {
             type int32;
           }
         }
         container ima-group-properties {
           leaf ima-version {
             type string;
             description "IMA specification version";
           }
           leaf ima-frame-length {
             type int32;
             description "IMA frame length";
           }
           leaf ima-differential-delay {
             type int32;
             description "IMA differential delay in milliseconds";
           }
           leaf ima-symmetry {
             type string;
             description "IMA operation symmetry mode";
           }
           leaf ima-transmit-clock {
             type string;
             description "IMA transmit clock mode";
           }
           leaf ima-tx-minimum-links {
             type int32;
             description "IMA transmit minimum links";
           }
           leaf ima-rx-minimum-links {
             type int32;
             description "IMA receive minimum links";
           }
           leaf ima-frame-sync-alpha {
             type int32;
             description "Consecutive invalid ICP cells for IMA frame synchronization";
           }
           leaf ima-frame-sync-beta {
             type int32;
             description "Consecutive errored ICP cells for IMA frame synchronization";
           }
           leaf ima-frame-sync-gamma {
             type int32;
             description "Consecutive valid ICP cells for IMA frame synchronization";
           }
           leaf ima-group-link-enumerator {
             type int32;
             description "Enumerator for link in this IMA group";
           }
           leaf ima-group-link-information {
             type string;
             description "Information for link in this IMA group";
           }
           leaf ima-test-period {
             type int32;
             description "IMA Test period";
           }
           leaf ima-test-elapsed {
             type int32;
             description "IMA Test elapsed time";
           }
           leaf ima-test-status {
             type string;
             description "IMA test procedure status";
           }
           leaf ima-test-pattern {
             type int32;
             description "IMA test tx pattern";
           }
           leaf ima-test-link {
             type string;
             description "IMA test procedure link";
           }
           leaf ima-test-result-pattern {
             type int32;
             description "IMA test rx pattern";
           }
           leaf ima-test-result-status {
             type string;
             description "IMA test result";
           }
           leaf ima-test-result-miscon {
             type int32;
             description "IMA test misconnected seconds";
           }
           leaf ima-test-result-mispat {
             type int32;
             description "IMA test mismatched pattern seconds";
           }
         }
         container ima-link-properties {
           leaf ima-group-id {
             type int32;
             description "IMA group ID";
           }
           leaf ima-link-direction {
             type string;
             description "IMA link direction";
           }
         }
         container cos-information {
           list cos-stream-information {
             leaf cos-direction {
               type string;
               description "Direction of the traffic stream";
             }
             list cos-queue-configuration {
               leaf cos-queue-number {
                 type int32;
                 description "Queue number";
               }
               leaf cos-queue-forwarding-class {
                 type string;
               }
               leaf cos-queue-bandwidth-remainder {
                 type string;
               }
               leaf cos-queue-bandwidth {
                 type int32;
               }
               leaf cos-queue-bandwidth-bps-remainder {
                 type string;
               }
               leaf cos-queue-bandwidth-bps {
                 type uint64;
               }
               leaf cos-queue-buffer-remainder {
                 type string;
               }
               leaf cos-queue-buffer {
                 type int32;
               }
               leaf cos-queue-buffer-bytes {
                 type int32;
               }
               leaf cos-queue-priority {
                 type string;
               }
               leaf cos-queue-limit {
                 type string;
               }
             }
           }
           container cos-forwarding-class-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-forwarding-class-map-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-classifier-information {
             list classifier {
               leaf classifier-name {
                 type string;
                 description "Class-of-service classifier name";
               }
               leaf code-point-type {
                 type string;
                 description "Class-of-service code point type";
               }
               leaf table-index {
                 type uint32;
                 description "Table index";
               }
               container classifier-map {
                 list classifier-map-item {
                   leaf code-point {
                     type string;
                     description "Class-of-service code point alias name or bits";
                   }
                   leaf fc-name {
                     type string;
                     description "Class-of-service forwarding class name";
                   }
                   leaf loss-priority {
                     type string;
                     description "Class-of-service loss priority";
                   }
                   leaf cntag-present {
                     type string;
                     description "Class-of-service cntag present";
                   }
                 }
               }
             }
           }
           container cos-loss-priority-map-information {
             list loss-priority-map {
               leaf loss-priority-map-name {
                 type string;
                 description "Name of class-of-service loss priority map";
               }
               leaf code-point-type {
                 type string;
                 description "Class-of-service code point type";
               }
               leaf table-index {
                 type uint32;
                 description "Table index";
               }
               list loss-priority-map-table {
                 list loss-priority-map-item {
                   leaf code-point {
                     type string;
                     description "Class-of-service code point alias name or bits";
                   }
                   leaf loss-priority {
                     type string;
                     description "Class-of-service loss priority";
                   }
                 }
                 list loss-priority-map-table-entry {
                   leaf table-index {
                     type uint32;
                     description "Table index";
                   }
                   leaf code-point {
                     type string;
                     description "Class-of-service code point alias name or bits";
                   }
                   leaf loss-priority {
                     type string;
                     description "Class-of-service loss priority";
                   }
                 }
               }
             }
           }
           container cos-drop-profile-information {
             list drop-profile {
               leaf profile-name {
                 type string;
                 description "Class-of-service drop profile name";
               }
               leaf profile-type {
                 type string;
                 description "Class-of-service drop profile type";
               }
               leaf table-index {
                 type uint32;
                 description "Table index";
               }
               container profile-map {
                 container profile-map-item {
                   leaf fill-level {
                     type uint32;
                     description "Class-of-service drop profile fill level value";
                   }
                   leaf probability {
                     type uint32;
                     description "Class-of-service drop profile probability value";
                   }
                 }
               }
             }
           }
           container cos-mpls-ecn-map-information {
             list cos-mpls-ecn-map-info {
               leaf ecn-capable-exp {
                 type int32;
                 description "ECN capable exp";
               }
               leaf congestion-experienced-exp {
                 type int32;
                 description "Congestion Expereienced exp";
               }
             }
           }
           container cos-monitoring-profile-information {
             list monitoring-profile {
               leaf monitoring-profile-name {
                 type string;
                 description "Class-of-service monitoring profile name";
               }
               container export-filters {
                 container export-filter {
                   leaf filter-name {
                     type string;
                     description "Class-of-service monitoring profile filter name";
                   }
                   leaf monitoring-queue-number {
                     type uint32;
                     description "Class-of-service monitoring profile filter queue value";
                   }
                   leaf peak-queue-length-value {
                     type uint32;
                     description "Class-of-service monitoring profile peak queue length value";
                   }
                 }
               }
             }
           }
           container cos-rewrite-information {
             list rewrite {
               leaf rewrite-name {
                 type string;
                 description "Class-of-service rewrite rule name";
               }
               leaf code-point-type {
                 type string;
                 description "Class-of-service code point type";
               }
               leaf table-index {
                 type uint32;
                 description "Table index";
               }
               container rewrite-map {
                 list rewrite-map-item {
                   leaf fc-name {
                     type string;
                     description "Class-of-service forwarding class name";
                   }
                   leaf loss-priority {
                     type string;
                     description "Class-of-service loss priority";
                   }
                   leaf code-point {
                     type string;
                     description "Class-of-service code point alias name or bits";
                   }
                 }
               }
             }
           }
           container cos-loss-priority-rewrite-information {
             list loss-priority-rewrite {
               leaf loss-priority-rewrite-name {
                 type string;
                 description "Name of class-of-service loss priority rewrite";
               }
               leaf code-point-type {
                 type string;
                 description "Class-of-service code point type";
               }
               leaf table-index {
                 type uint32;
                 description "Table index";
               }
               list loss-priority-rewrite-table {
                 list loss-priority-rewrite-item {
                   leaf loss-priority {
                     type string;
                     description "Class-of-service loss priority";
                   }
                   leaf code-point {
                     type string;
                     description "Class-of-service code point alias name or bits";
                   }
                 }
                 list loss-priority-rewrite-table-entry {
                   leaf table-index {
                     type uint32;
                     description "Table index";
                   }
                   leaf loss-priority {
                     type string;
                     description "Class-of-service loss priority";
                   }
                   leaf code-point {
                     type string;
                     description "Class-of-service code point alias name or bits";
                   }
                 }
               }
             }
           }
           container cos-code-point-map-information {
             list code-point-map {
               leaf code-point-type {
                 type string;
                 description "Class-of-service code point type";
               }
               container alias-map {
                 list alias-map-item {
                   leaf code-point-alias {
                     type string;
                     description "Class-of-service code point alias name";
                   }
                   leaf code-point-bits {
                     type string;
                     description "Class-of-service code point bit sequence";
                   }
                 }
               }
             }
           }
           container cos-fragmentation-map-information {
             list fragmentation-map {
               leaf fragmentation-map-name {
                 type string;
                 description "Class-of-service fragmentation map name";
               }
               leaf fragmentation-map-index {
                 type uint32;
                 description "Index number for Class-of-service fragmentation map";
               }
               list fragment-map {
                 leaf fc-name {
                   type string;
                   description "Class-of-service forwarding class name";
                 }
                 leaf no-fragmentation {
                   type empty;
                   description "Do not fragment packets of this class";
                 }
                 leaf fragment-threshold {
                   type string;
                   description "Fragmentation threshold";
                 }
                 leaf fragment-multilink-class {
                   type int32;
                   description "Identifier for multilink class";
                 }
               }
             }
           }
           container cos-translation-table-map-information {
             list translation-table {
               leaf translation-table-name {
                 type string;
                 description "Class-of-service translation table name";
               }
               leaf translation-table-type {
                 type string;
                 description "Class-of-service translation table type";
               }
               leaf table-index {
                 type uint32;
                 description "Table index";
               }
               container translation-table-map {
                 container translation-table-map-item {
                   leaf from-code-point {
                     type string;
                     description "Class-of-service code point alias name or bits";
                   }
                   leaf to-code-point {
                     type string;
                     description "Class-of-service code point alias name or bits";
                   }
                 }
               }
               list translation-table-entry {
                 leaf table-index {
                   type uint32;
                   description "Table index";
                 }
                 leaf from-code-point {
                   type string;
                   description "Class-of-service code point alias name or bits";
                 }
                 leaf to-code-point {
                   type string;
                   description "Class-of-service code point alias name or bits";
                 }
               }
             }
           }
           container cos-multi-destination-information {
             container sm-md-map {
               leaf scheduler-map-name {
                 type string;
                 description "Class-of-service scheduler map name";
               }
               leaf scheduler-map-index {
                 type uint64;
                 description "Class-of-service scheduler map index";
               }
             }
             container fc-md-map {
               leaf fc-name {
                 type string;
                 description "Class-of-service forwarding class name";
               }
               leaf fc-queue-number {
                 type uint32;
                 description "Class-of-service forwarding class queue number";
               }
             }
             container cls-md-map {
               leaf multidest-classifier-name {
                 type string;
                 description "Multi destination classifier name";
               }
               leaf multidest-classifier-type {
                 type string;
                 description "Multi destination classifier type";
               }
               leaf multidest-classifier-index {
                 type uint32;
                 description "Multi destination classifier id";
               }
             }
           }
           container cos-forwarding-class-set-information {
             list forwarding-class-set {
               list forwarding-class-set-entry {
                 leaf forwarding-class-set-name {
                   type string;
                   description "Class-of-service forwarding class set name";
                 }
                 leaf forwarding-class-set-type {
                   type string;
                   description "Identifier for Class-of-service forwarding class set type";
                 }
                 leaf forwarding-class-set-index {
                   type uint32;
                   description "Identifier for Class-of-service forwarding class set";
                 }
                 container fc-map {
                   list fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-rqueue-number {
                       type uint32;
                       description "Class-of-service forwarding class restricted queue number";
                     }
                     leaf fc-priority {
                       type string;
                       description "Class-of-service forwarding class queue priority";
                     }
                     leaf fc-policing-priority {
                       type string;
                       description "Class-of-service forwarding class policing priority";
                     }
                     leaf fc-spu-priority {
                       type string;
                       description "Class-of-service forwarding class spu priority";
                     }
                     leaf fc-no-loss {
                       type string;
                       description "Class-of-service forwarding class no-loss";
                     }
                     leaf fc-pfc-priority {
                       type uint32;
                       description "Class-of-service forwarding class pfc-priority";
                     }
                     leaf fc-multicast {
                       type string;
                       description "Class-of-service forwarding class multicast";
                     }
                   }
                 }
               }
             }
           }
           container cos-policy-map-information {
             list policy-map {
               leaf policy-map-name {
                 type string;
                 description "Class-of-service Policy-map name";
               }
               leaf table-index {
                 type uint32;
                 description "Table index";
               }
               leaf policy-map-user-attribute {
                 type uint32;
                 description "User-defined attribute";
               }
               container policy-map-cp-entries {
                 leaf code-point-type {
                   type string;
                   description "Class-of-service code point type";
                 }
                 leaf code-point {
                   type string;
                   description "Class-of-service code point alias name or bits";
                 }
                 leaf code-point-option {
                   type string;
                   description "Class-of-service code point option flag";
                 }
               }
             }
           }
           container cos-client-info {
             list cos-client {
               leaf cos-client-info-internal-id {
                 type uint32;
                 description "Junos client internal identifier";
               }
               leaf cos-client-info-requests {
                 type uint32;
                 description "Number of requests from Junos client";
               }
               leaf cos-client-info-responses {
                 type uint32;
                 description "Number of responses to Junos client";
               }
               leaf cos-client-info-failures {
                 type uint32;
                 description "Number of failures while handling Junos client requests";
               }
               leaf cos-client-info-identifier {
                 type string;
                 description "Junos client identifier";
               }
               leaf cos-client-name {
                 type string;
                 description "Junos client name";
               }
               leaf cos-client-state {
                 type string;
                 description "Junos client state information";
               }
               leaf cos-client-internal-name {
                 type string;
                 description "Junos client internal name";
               }
               leaf cos-client-stats {
                 type string;
                 description "Junos client statistics";
               }
               leaf cos-client-failure-stats {
                 type string;
                 description "Junos client failure/error statistics";
               }
               leaf cos-client-validate-failures {
                 type uint32;
                 description "Junos client request validation failures";
               }
               leaf cos-client-ownership-failures {
                 type uint32;
                 description "Junos client ownership validation failures";
               }
               leaf cos-client-info-name {
                 type string;
                 description "CoS client name";
               }
               leaf cos-client-internal-id {
                 type uint32;
                 description "Junos client internal identifier";
               }
               leaf cos-client-requests {
                 type uint64;
                 description "Number of requests from Junos client";
               }
               leaf cos-client-responses {
                 type uint64;
                 description "Number of responses to Junos client";
               }
               leaf cos-client-failures {
                 type uint64;
                 description "Number of failures while handling Junos client requests";
               }
               leaf cos-client-identifier {
                 type string;
                 description "Junos client identifier";
               }
               leaf cos-client-status {
                 type string;
                 description "Junos client status";
               }
               leaf cos-client-connected-time {
                 type string;
                 description "Junos client time of connect";
               }
               leaf cos-client-reconnected-time {
                 type string;
                 description "Junos client time of reconnect";
               }
               leaf cos-client-disconnected-time {
                 type string;
                 description "Junos client time of disconnect";
               }
               leaf cos-client-message-type {
                 type string;
                 description "Junos client message type";
               }
               leaf cos-client-operation-type {
                 type string;
                 description "Junos client operation type";
               }
               leaf-list cos-bind-point-type {
                 type string;
                 description "Class-of-service bind point type";
               }
               leaf-list cos-bind-point-owner-type {
                 type string;
                 description "Class-of-service bind point owner type";
               }
               leaf-list cos-bind-point-owner-internal-id {
                 type uint32;
                 description "Junos client internal identifier";
               }
               leaf-list cos-bind-point-name {
                 type string;
                 description "Class-of-service bind point name";
               }
               leaf cos-bind-point-feature {
                 type string;
                 description "Class-of-service bind point feature name";
               }
               leaf cos-bind-point-feature-object-name {
                 type string;
                 description "Class-of-service bind point feature object name";
               }
             }
           }
           container cos-host-outbound-info {
             list cos-host-outbound-traffic-info {
               leaf cos-host-outbound-traffic-protocol-name {
                 type string;
                 description "CoS host outbound traffic protocol name";
               }
               leaf cos-host-outbound-traffic-dscp {
                 type string;
                 description "CoS host outbound traffic dscp";
               }
               leaf cos-host-outbound-traffic-dot1p {
                 type string;
                 description "CoS host outbound traffic ieee 802.1p";
               }
               leaf cos-host-outbound-traffic-fc-id {
                 type string;
                 description "CoS host outbound traffic forwarding class id";
               }
               leaf cos-host-outbound-traffic-queue-id {
                 type string;
                 description "CoS host outbound traffic queue id";
               }
               leaf cos-host-outbound-traffic-restrict-queue-id {
                 type string;
                 description "CoS host outbound traffic restrict queue id";
               }
               leaf cos-host-outbound-traffic-override-firewall {
                 type string;
                 description "CoS host outbound traffic override firwall action";
               }
               leaf cos-host-outbound-traffic-rw-dot1p {
                 type string;
                 description "CoS host outbound traffic - use ieee 802.1p rewrite rules";
               }
             }
           }
           container cos-drop-congestion-notification-information {
             list cos-drop-congestion-notification-info {
               leaf cos-dcn-fc-name {
                 type string;
                 description "Cos DCN forwarding class";
               }
               leaf cos-dcn-udp-port {
                 type int32;
                 description "Cos DCN udp port number";
               }
             }
           }
           container cos-dedicated-buffer-profile-information {
             list dedicated-buffer-profile {
               leaf dedicated-buffer-profile-name {
                 type string;
                 description "Class-of-service dedicated buffer profile name";
               }
               leaf dedicated-buffer-profile-index {
                 type int32;
                 description "Class-of-service dedicated buffer profile index";
               }
               leaf ingress-buffer-size {
                 type string;
                 description "Ingress per port dedicated buffer in cells";
               }
               leaf egress-buffer-size {
                 type string;
                 description "Egress per port dedicated buffer in cells";
               }
             }
           }
           container cos-dynamic-threshold-profile-information {
             list dynamic-threshold-profile {
               leaf dynamic-threshold-profile-name {
                 type string;
                 description "Class-of-service dynamic threshold profile name";
               }
               leaf dynamic-threshold-profile-index {
                 type uint64;
                 description "Class-of-service dynamic threshold profile index";
               }
               list dynamic-threshold-profile-entry {
                 leaf dynamic-threshold-profile-priority-group {
                   type string;
                   description "Class-of-service dynamic threshold profile priority group";
                 }
                 leaf dynamic-threshold-profile-threshold-value {
                   type uint32;
                   description "Class-of-service dynamic threshold profile threshold value";
                 }
               }
             }
           }
           container cos-decn-profile-information {
             list decn-profile {
               leaf decn-profile-name {
                 type string;
                 description "Class-of-service decn profile name";
               }
               leaf decn-profile-index {
                 type uint64;
                 description "Class-of-service decn profile index";
               }
               list decn-profile-queue {
                 leaf dynamic-explicit-congestion-notification-queue {
                   type uint32;
                   description "Class-of-service DECN queue";
                 }
                 leaf dynamic-explicit-congestion-notification-offset {
                   type uint32;
                   description "Class-of-service DECN offset";
                 }
                 leaf dynamic-explicit-congestion-notification-floor {
                   type uint32;
                   description "Class-of-service DECN floor";
                 }
               }
             }
           }
           container cos-scheduler-map-information {
             list scheduler-map {
               leaf scheduler-map-name {
                 type string;
                 description "Class-of-service scheduler map name";
               }
               leaf scheduler-map-index {
                 type uint64;
                 description "Class-of-service scheduler map index";
               }
               leaf user-plane-name {
                 type string;
                 description "Class-of-service user-plane name for XDA";
               }
               list scheduler {
                 leaf scheduler-name {
                   type string;
                   description "Class-of-service scheduler name";
                 }
                 leaf fc-name {
                   type string;
                   description "Class-of-service forwarding class name";
                 }
                 leaf scheduler-index {
                   type uint64;
                   description "Class of service scheduler index";
                 }
                 leaf scheduler-tx-rate {
                   type string;
                   description "Class-of-service scheduler transmit rate";
                 }
                 leaf scheduler-tx-limit {
                   type string;
                   description "Class-of-service scheduler transmit limit";
                 }
                 leaf scheduler-buffer-size {
                   type string;
                   description "Class-of-service scheduler buffer size";
                 }
                 leaf scheduler-buffer-multicast-share {
                   type uint32;
                   description "Class-of-service scheduler multicast buffer share";
                 }
                 leaf scheduler-buffer-limit {
                   type string;
                   description "Class-of-service scheduler buffer limit";
                 }
                 leaf scheduler-buffer-rate {
                   type string;
                   description "Class-of-service scheduler buffer rate";
                 }
                 leaf scheduler-shared-buffer-maximum-percentage {
                   type uint32;
                   description "Shared Buffer maximum percentage";
                 }
                 leaf scheduler-shared-buffer-multicast-maximum-percentage {
                   type uint32;
                   description "Shared Buffer multicast maximum percentage";
                 }
                 leaf scheduler-buffer-dynamic-threshold {
                   type uint32;
                   description "Queue shared-buffer dynamic threshold";
                 }
                 leaf scheduler-priority {
                   type string;
                   description "Class-of-service scheduler priority";
                 }
                 leaf scheduler-shaping-rate {
                   type string;
                   description "Class-of-service scheduler shaping rate";
                 }
                 leaf scheduler-shaping-rate-burst {
                   type string;
                   description "Class-of-service scheduler shaping rate burst";
                 }
                 leaf scheduler-adjust-minimum {
                   type int32;
                   description "Class-of-service scheduler adjustment minimum rate";
                 }
                 leaf scheduler-adjust-percent {
                   type int32;
                   description "Class-of-service scheduler percent adjustment for a queue";
                 }
                 leaf scheduler-excess-priority {
                   type string;
                   description "Class-of-service scheduler excess priority";
                 }
                 leaf scheduler-excess-rate {
                   type string;
                   description "Class-of-service scheduler excess rate";
                 }
                 leaf scheduler-explicit-congestion-notification {
                   type string;
                   description "Class-of-service ECN status of queue";
                 }
                 leaf scheduler-ecn-rtlog-rate-limit {
                   type uint32;
                   description "Class-of-service ECN Security Log Rate Limit";
                 }
                 leaf scheduler-ecn-no-pfc-assist {
                   type string;
                   description "Class-of-service ECN no pfc assist";
                 }
                 leaf scheduler-queue-monitoring {
                   type string;
                   description "Class-of-service queue depth monitoring of queue";
                 }
                 leaf scheduler-drop-profile-ln-index {
                   type uint32;
                   description "Class-of-service scheduler drop profile index low, non-TCP";
                 }
                 leaf scheduler-drop-profile-ln {
                   type string;
                   description "Class-of-service scheduler drop profile low, non-TCP";
                 }
                 leaf scheduler-drop-profile-lt-index {
                   type uint32;
                   description "Class-of-service scheduler drop profile index low, TCP";
                 }
                 leaf scheduler-drop-profile-lt {
                   type string;
                   description "Class-of-service scheduler drop profile low, TCP";
                 }
                 leaf scheduler-drop-profile-hn-index {
                   type uint32;
                   description "Class-of-service scheduler drop profile index high, non-TCP";
                 }
                 leaf scheduler-drop-profile-hn {
                   type string;
                   description "Class-of-service scheduler drop profile high, non-TCP";
                 }
                 leaf scheduler-drop-profile-ht-index {
                   type uint32;
                   description "Class-of-service scheduler drop profile index high, TCP";
                 }
                 leaf scheduler-drop-profile-ht {
                   type string;
                   description "Class-of-service scheduler drop profile high, TCP";
                 }
                 leaf scheduler-drop-profile-la-index {
                   type uint32;
                   description "Class-of-service scheduler drop profile index low";
                 }
                 leaf scheduler-drop-profile-la {
                   type string;
                   description "Class-of-service scheduler drop profile low";
                 }
                 leaf scheduler-drop-profile-ma-index {
                   type uint32;
                   description "Class-of-service scheduler drop profile index medium";
                 }
                 leaf scheduler-drop-profile-ma {
                   type string;
                   description "Class-of-service scheduler drop profile medium";
                 }
                 leaf scheduler-drop-profile-mla-index {
                   type uint32;
                   description "Class-of-service scheduler drop profile index medium-low";
                 }
                 leaf scheduler-drop-profile-mla {
                   type string;
                   description "Class-of-service scheduler drop profile medium-low";
                 }
                 leaf scheduler-drop-profile-mha-index {
                   type uint32;
                   description "Class-of-service scheduler drop profile index medium-high";
                 }
                 leaf scheduler-drop-profile-mha {
                   type string;
                   description "Class-of-service scheduler drop profile medium-high";
                 }
                 leaf scheduler-drop-profile-ha-index {
                   type uint32;
                   description "Class-of-service scheduler drop profile index high";
                 }
                 leaf scheduler-drop-profile-ha {
                   type string;
                   description "Class-of-service scheduler drop profile high";
                 }
               }
             }
           }
           container cos-traffic-control-profile-information {
             list traffic-control-profile {
               leaf traffic-control-profile-name {
                 type string;
                 description "Class-of-service traffic control profile name";
               }
               leaf traffic-control-profile-index {
                 type uint64;
                 description "Index number for Class-of-service traffic control profile";
               }
               leaf user-plane-name {
                 type string;
                 description "Class-of-service user-plane name for XDA";
               }
               leaf scheduler-map-name {
                 type string;
                 description "Class-of-service scheduler map name";
               }
               leaf atm-service {
                 type string;
                 description "Class-of-service traffic control profile atm service";
               }
               leaf shaping-rate {
                 type uint64;
                 description "Class-of-service shaping rate";
               }
               leaf shaping-rate-burst {
                 type uint32;
                 description "Class-of-service shaping rate burst, in bytes";
               }
               leaf low-granularity {
                 type uint32;
                 description "Class-of-service low-granularity mode support";
               }
               leaf queue-mode-4q {
                 type uint32;
                 description "Class-of-service tcp-voq-mode(4Q) mode support";
               }
               leaf shaping-rate-priority-strict-high {
                 type uint64;
                 description "Class-of-service shaping rate for priority strict high";
               }
               leaf shaping-rate-priority-strict-high-burst {
                 type uint32;
                 description "Class-of-service shaping rate burst for priority strict-high";
               }
               leaf shaping-rate-priority-high {
                 type uint64;
                 description "Class-of-service shaping rate for priority high";
               }
               leaf shaping-rate-priority-high-burst {
                 type uint32;
                 description "Class-of-service shaping rate for priority high burst";
               }
               leaf shaping-rate-priority-medium {
                 type uint64;
                 description "Class-of-service shaping rate for priority medium";
               }
               leaf shaping-rate-priority-medium-burst {
                 type uint32;
                 description "Class-of-service shaping rate for priority medium burst";
               }
               leaf shaping-rate-priority-medium-low {
                 type uint64;
                 description "Class-of-service shaping rate for priority medium-low";
               }
               leaf shaping-rate-priority-medium-low-burst {
                 type uint32;
                 description "Class-of-service shaping rate burst for priority medium-low";
               }
               leaf shaping-rate-priority-low {
                 type uint64;
                 description "Class-of-service shaping rate for priority low";
               }
               leaf shaping-rate-priority-low-burst {
                 type uint32;
                 description "Class-of-service shaping rate for priority low burst";
               }
               leaf shaping-rate-excess-high {
                 type uint64;
                 description "Class-of-service shaping rate for excess high";
               }
               leaf shaping-rate-excess-high-burst {
                 type uint32;
                 description "Class-of-service shaping rate for excess high burst";
               }
               leaf shaping-rate-excess-medium-high {
                 type uint64;
                 description "Class-of-service shaping rate for excess medium-high";
               }
               leaf shaping-rate-excess-medium-high-burst {
                 type uint32;
                 description "Class-of-service shaping rate burst for excess medium-high";
               }
               leaf shaping-rate-excess-medium-low {
                 type uint64;
                 description "Class-of-service shaping rate for excess medium-low";
               }
               leaf shaping-rate-excess-medium-low-burst {
                 type uint32;
                 description "Class-of-service shaping rate burst for excess medium-low";
               }
               leaf shaping-rate-excess-low {
                 type uint64;
                 description "Class-of-service shaping rate for excess low";
               }
               leaf shaping-rate-excess-low-burst {
                 type uint32;
                 description "Class-of-service shaping rate for excess low burst";
               }
               leaf guaranteed-rate {
                 type uint64;
                 description "Class-of-service guaranteed rate";
               }
               leaf guaranteed-rate-burst {
                 type uint32;
                 description "Class-of-service guaranteed rate burst, in bytes";
               }
               leaf delay-buffer-rate {
                 type uint64;
                 description "Class-of-service delay buffer rate";
               }
               leaf excess-rate {
                 type uint32;
                 description "Class-of-service excess rate";
               }
               leaf excess-rate-high {
                 type uint32;
                 description "Class-of-service excess rate for excess-high priority traffic";
               }
               leaf excess-rate-medium-high {
                 type uint32;
                 description "Class-of-service excess rate for excess-medium-high priority traffic";
               }
               leaf excess-rate-medium-low {
                 type uint32;
                 description "Class-of-service excess rate for excess-medium-low priority traffic";
               }
               leaf excess-rate-low {
                 type uint32;
                 description "Class-of-service excess rate for excess-low priority traffic";
               }
               leaf adjust-minimum {
                 type uint64;
                 description "Class-of-service adjustment minimum rate";
               }
               leaf overhead-bytes {
                 type int32;
                 description "Class-of-service Overhead bytes";
               }
               leaf frame-mode-bytes {
                 type int32;
                 description "Class-of-service overhead bytes when in frame-mode";
               }
               leaf cell-mode-bytes {
                 type int32;
                 description "Class-of-service overhead bytes when in cell-mode";
               }
               leaf overhead-accounting-mode {
                 type string;
                 description "Class-of-service Overhead Accounting Mode";
               }
               list traffic-control-profile-instance {
                 leaf traffic-control-profile-instance-name {
                   type string;
                   description "Class-of-service traffic control profile instance";
                 }
                 leaf traffic-control-profile-instance-index {
                   type uint32;
                   description "Index number for Class-of-service traffic control profile instance";
                 }
                 leaf instance-reference-count {
                   type uint32;
                   description "Instance reference count";
                 }
               }
             }
           }
           container cos-routing-instance-information {
             list routing-instance-map {
               leaf routing-instance-name {
                 type string;
                 description "Name of class-of-service routing instance";
               }
               list i-logical-map {
                 leaf i-logical-name {
                   type string;
                   description "Class-of-service logical interface name";
                 }
                 leaf i-logical-index {
                   type uint32;
                   description "Class-of-service logical interface index";
                 }
                 leaf monitoring-profile-map-name {
                   type string;
                   description "Monitoring Profile Name";
                 }
                 list cos-objects {
                   leaf cos-object-type {
                     type string;
                     description "Class-of-service object type";
                   }
                   leaf cos-object-name {
                     type string;
                     description "Class-of-service object name";
                   }
                   leaf cos-object-subtype {
                     type string;
                     description "Class-of-service object subtype";
                   }
                   leaf cos-object-index {
                     type uint64;
                     description "Class-of-service object index";
                   }
                 }
               }
             }
           }
           container cos-fabric-scheduler-map-information {
             container fabric-scheduler-map {
               list fabric-scheduler {
                 leaf fabric-scheduler-name {
                   type string;
                   description "Class-of-service scheduler name";
                 }
                 leaf fabric-scheduler-index {
                   type uint32;
                   description "Class of service scheduler index";
                 }
                 leaf fabric-scheduler-drop-profile-ln-index {
                   type uint32;
                   description "Class-of-service scheduler drop profile index low, non-TCP";
                 }
                 leaf fabric-scheduler-drop-profile-ln {
                   type string;
                   description "Class-of-service scheduler drop profile low, non-TCP";
                 }
                 leaf fabric-scheduler-drop-profile-lt-index {
                   type uint32;
                   description "Class-of-service scheduler drop profile index low, TCP";
                 }
                 leaf fabric-scheduler-drop-profile-lt {
                   type string;
                   description "Class-of-service scheduler drop profile low, TCP";
                 }
                 leaf fabric-scheduler-drop-profile-hn-index {
                   type uint32;
                   description "Class-of-service scheduler drop profile index high, non-TCP";
                 }
                 leaf fabric-scheduler-drop-profile-hn {
                   type string;
                   description "Class-of-service scheduler drop profile high, non-TCP";
                 }
                 leaf fabric-scheduler-drop-profile-ht-index {
                   type uint32;
                   description "Class-of-service scheduler drop profile index high, TCP";
                 }
                 leaf fabric-scheduler-drop-profile-ht {
                   type string;
                   description "Class-of-service scheduler drop profile high, TCP";
                 }
                 leaf fabric-scheduler-priority {
                   type string;
                 }
               }
             }
           }
           container cos-tcm-information {
             list tcm {
               leaf tcm-name {
                 type string;
                 description "Class-of-service traffic-class-map name";
               }
               leaf tcm-type {
                 type string;
                 description "Class-of-service traffic-class-map type";
               }
               leaf table-index {
                 type uint32;
                 description "Table index";
               }
               container tcm-map {
                 list tcm-map-item {
                   leaf code-point {
                     type string;
                     description "Class-of-service code point alias name or bits";
                   }
                   leaf tc-name {
                     type string;
                     description "Class-of-service traffic-class-map traffic-class name";
                   }
                 }
               }
             }
           }
         }
         container physical-interface-cos-information {
           leaf physical-interface-cos-hw-max-queues {
             type int32;
             description "Maximum number of class-of-service queues supported by the hardware";
           }
           leaf physical-interface-cos-use-max-queues {
             type int32;
             description "Maximum number of usable class-of-service queues";
           }
           leaf physical-interface-schedulers {
             type int32;
             description "Schedulers allocated to this interface";
           }
           leaf physical-interface-bypass-queueing-chip {
             type string;
             description "Bypass queueing chip enabled on this interface";
           }
           container physical-interface-red-buffer-occupancy {
             leaf instant-usage-weight-exponent {
               type int32;
               description "Weight used for instant buffer usage information for computing buffer occupancy expressed as a negative exponent of 2";
             }
           }
         }
         container precl-statistics {
           container precl-information {
             container precl-per-class-statistics {
               leaf precl-traffic-class {
                 type string;
                 description "Traffic class";
               }
               leaf precl-rx-packets {
                 type int32;
                 description "Packets received by the preclassifier";
               }
               leaf precl-tx-packets {
                 type int32;
                 description "Packets transmitted by the preclassifier";
               }
               leaf precl-dropped-packets {
                 type int32;
                 description "Packets dropped by the preclassifier";
               }
             }
           }
         }
         container mlfr-uni-nni-traffic-statistics {
           container bundle {
             container multilink-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           container mlfr-uni-nni-link-information {
             leaf active-bundle-links {
               type int32;
               description "Number of active bundle links in this multilink Frame Relay UNI NNI bundle instance";
             }
             leaf removed-bundle-links {
               type int32;
               description "Number of bundle links that are removed from service in this multilink Frame Relay UNI NNI bundle instance";
             }
             leaf disabled-bundle-links {
               type int32;
               description "Number of bundle links that are not allowed to transmit in this multilink Frame Relay UNI NNI bundle instance";
             }
           }
           list mlfr-uni-nni-link {
             leaf name {
               type string;
               description "Name of this item";
             }
             leaf down {
               type empty;
               description "Link is down";
             }
             leaf link-uptime {
               type string;
               description "Total uptime for the member link";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
             leaf current-differential-delay {
               type int32;
               description "Current differential delay of this bundle link";
             }
             leaf recent-high-differential-delay {
               type int32;
               description "Recent highest differential delay of this bundle link (in every 256 measurements)";
             }
             leaf over-red-differential {
               type int32;
               description "Number of times over red differential delay";
             }
             leaf over-yellow-differential {
               type int32;
               description "Number of times over yellow differential delay";
             }
             leaf lip-header-string {
               type string;
               description "Header string of the LIP display";
             }
             leaf rcv-lip-addlink {
               type int32;
               description "Number of LIP ADD_LINKs received";
             }
             leaf rcv-lip-link-ack {
               type int32;
               description "Number of LIP ADD_LINK_ACKs received";
             }
             leaf rcv-lip-link-rej {
               type int32;
               description "Number of LIP ADD_LINK_REJs received";
             }
             leaf rcv-lip-hello {
               type int32;
               description "Number of LIP HELLOs received";
             }
             leaf rcv-lip-hello-ack {
               type int32;
               description "Number of LIP HELLO_ACKs received";
             }
             leaf rcv-lip-link-rem {
               type int32;
               description "Number of LIP LINK_REMOVEs received";
             }
             leaf rcv-lip-rem-ack {
               type int32;
               description "Number of LIP LINK_REMOVE_ACKs received";
             }
             leaf xmt-lip-addlink {
               type int32;
               description "Number of LIP ADD_LINKs transmitted";
             }
             leaf xmt-lip-link-ack {
               type int32;
               description "Number of LIP LINK_ACKs transmitted";
             }
             leaf xmt-lip-link-rej {
               type int32;
               description "Number of LIP LINK_REJs transmitted";
             }
             leaf xmt-lip-hello {
               type int32;
               description "Number of LIP HELLOs transmitted";
             }
             leaf xmt-lip-hello-ack {
               type int32;
               description "Number of LIP HELLO_ACKs transmitted";
             }
             leaf xmt-lip-link-rem {
               type int32;
               description "Number of LIP LINK_REMOVEs transmitted";
             }
             leaf xmt-lip-rem-ack {
               type int32;
               description "Number of LIP LINK_REMOVE_ACKs transmitted";
             }
           }
         }
       }
       list logical-interface {
         leaf name {
           type string;
           description "Name of this item";
         }
         leaf local-index {
           type int32;
           description "Local kernel index for this interface";
         }
         leaf snmp-index {
           type int32;
           description "SNMP ifIndex for this interface";
         }
         leaf hardware-token {
           type int32;
           description "Hardware token for layer 3 ifl";
         }
         leaf generation {
           type int32;
           description "Generation number used to distinguish between successive instances of this interface";
         }
         leaf description {
           type string;
           description "Description of this interface";
         }
         leaf multilink-flapped {
           type string;
           description "Time when the interface last flapped";
         }
         leaf logical-interface-bandwidth {
           type string;
           description "Bandwidth of this logical interface";
         }
         leaf link-address {
           type string;
           description "Link address on this logical interface";
         }
         leaf encapsulation {
           type string;
           description "Encapsulation on the logical interface";
         }
         leaf esi-value {
           type string;
           description "Ethernet segment identifier for this interface";
         }
         leaf esi-mode {
           type string;
           description "Ethernet segment mode for this interface";
         }
         leaf evpn-multihomed-status {
           type string;
         }
         leaf virtual-gateway-esi-value {
           type string;
           description "Ethernet segment identifier for this interface";
         }
         leaf virtual-gateway-esi-mode {
           type string;
           description "Ethernet segment mode for this interface";
         }
         leaf interface-set-name {
           type string;
           description "Class-of-service interface-set name";
         }
         leaf copy-tos-to-outer-ip-header {
           type string;
           description "Flag that enables copying of the value in the ToS field of the IP packet's payload header to the delivery header in the generic routingencapsulation packet";
         }
         leaf copy-tos-to-outer-ip-header-transit {
           type string;
           description "Flag that enables copying of the value in the ToS field of the IP packet's payload header to the delivery header in the generic routing encapsulation transit packet";
         }
         leaf gre-keepalive-configured {
           type string;
           description "Gre Keepalives enabled on the logical interface";
         }
         leaf gre-keepalive-adj-state {
           type string;
           description "Gre Keepalives enabled on the logical interface";
         }
         leaf demux-table-type {
           type string;
           description "Demux table enabled on the logical interface";
         }
         leaf redundant-logical-interface-name {
           type string;
           description "Name of the redundant logical interface";
         }
         leaf tenant-name {
           type string;
           description "Tenant name assigned to logical interface";
         }
         leaf lcp-state {
           type string;
           description "State of the Line Control Protocol";
         }
         leaf chap-state {
           type string;
           description "State of the Challenge Handshake Authentication Protocol";
         }
         leaf pap-state {
           type string;
           description "State of the Password Authentication Protocol";
         }
         leaf logical-interface-mac {
           type string;
           description "MAC on the logical interface";
         }
         leaf logical-interface-vgw-v4-mac {
           type string;
           description "MAC on the logical interface";
         }
         leaf logical-interface-vgw-v6-mac {
           type string;
           description "MAC on the logical interface";
         }
         leaf vrfname {
           type string;
           description "Routing instance name";
         }
         leaf zonename {
           type string;
           description "Zone name";
         }
         leaf subunit {
           type int32;
           description "Subunit for this interface";
         }
         leaf dialer-time-to-disconnect {
           type string;
           description "Time for dialer to disconnect due to idle timeout";
         }
         container if-config-flags {
           leaf iff-none {
             type empty;
           }
           leaf iff-hardware-down {
             type empty;
           }
           leaf iff-down {
             type empty;
           }
           leaf iff-up {
             type empty;
           }
           leaf iff-admin-down {
             type empty;
           }
           leaf iff-admin-up {
             type empty;
           }
           leaf iff-link-down {
             type empty;
           }
           leaf iff-device-down {
             type empty;
           }
           leaf iff-point-to-point {
             type empty;
           }
           leaf iff-point-to-multipoint {
             type empty;
           }
           leaf plp-to-clp {
             type empty;
           }
           leaf iff-multiaccess {
             type empty;
           }
           leaf iff-change {
             type empty;
           }
           leaf iff-inverse-arp {
             type empty;
           }
           leaf iff-no-multicast {
             type empty;
           }
           leaf iff-multicast {
             type empty;
           }
           leaf iff-promiscuous {
             type empty;
           }
           leaf iff-all-multicast {
             type empty;
           }
           leaf iff-snmp-traps {
             type empty;
           }
           leaf iff-rx-passive {
             type empty;
           }
           leaf iff-tx-passive {
             type empty;
           }
           leaf iff-ccc-down {
             type empty;
           }
           leaf iff-clear-df {
             type empty;
           }
           leaf iff-tunnel-reassembly {
             type empty;
           }
           leaf iff-acfc {
             type empty;
           }
           leaf iff-pfc {
             type empty;
           }
           leaf iff-rdd {
             type empty;
           }
           leaf iff-looped {
             type empty;
           }
           leaf iff-framing-conflict {
             type empty;
           }
           leaf internal-flags {
             type int32;
             description "Hexadecimal value of internal flag bits";
           }
         }
         container layer2-input-policer-information {
           leaf layer2-input-policer {
             type string;
             description "Name of the Layer 2 input policer";
           }
         }
         container layer2-output-policer-information {
           leaf layer2-output-policer {
             type string;
             description "Name of the Layer 2 output policer";
           }
         }
         container atm-input-policer-information {
           leaf atm-input-policer {
             type string;
             description "Name of the atm input policer";
           }
         }
         container pppoe-information {
           list pppoe-interface {
             leaf state {
               type string;
               description "State";
             }
             leaf session-id {
               type string;
               description "Session ID";
             }
             leaf ac-name-session {
               type string;
               description "Session AC name";
             }
             leaf remote-mac {
               type string;
               description "Remote MAC address";
             }
             leaf ac-name-config {
               type string;
               description "Configured AC name";
             }
             leaf service-name {
               type string;
               description "Service name";
             }
             leaf auto-reconnect {
               type string;
               description "Autoreconnect timeout";
             }
             leaf idle-timeout {
               type string;
               description "Idle timeout";
             }
             leaf underlying-interface-name {
               type string;
               description "Underlying interface name";
             }
             leaf underlying-interface-index {
               type string;
               description "Underlying interface index";
             }
             leaf padg-credits {
               type int32;
               description "PADG transmit credits";
             }
             leaf pppoe-credit-scale-factor {
               type string;
               description "Scaling factor";
             }
             leaf ignore-eol-tag {
               type string;
               description "Ignore End-of-List TAG";
             }
             leaf ppp-max-payload-tag {
               type int32;
               description "PPP-Max-Payload TAG";
             }
             leaf interface-name {
               type string;
               description "Class-of-service interface name";
             }
             leaf interface-index {
               type uint32;
               description "Class-of-service interface index";
             }
             leaf aci-iflset-name {
               type string;
               description "ACI Interface Set name";
             }
             leaf aci-iflset-index {
               type string;
               description "ACI Interface Set index";
             }
             leaf ifl-type {
               type string;
               description "Type";
             }
             leaf session-uptime {
               type string;
               description "Duration for which the session has been up";
             }
             leaf dynamic-profile {
               type string;
               description "Dynamic Profile name";
             }
             leaf pppoe-credits {
               type string;
               description "Forwarding credit balances";
             }
             leaf dynamic-interface-bandwidth {
               type string;
               description "Dynamic interface bandwidth";
             }
             leaf agent-circuit-id {
               type string;
               description "Agent Circuit ID";
             }
             leaf agent-remote-id {
               type string;
               description "Agent Remote ID";
             }
             leaf padm-motm {
               type string;
               description "PADM Message of the Moment tag";
             }
             leaf padm-hurl {
               type string;
               description "PADM HTTP URL tag";
             }
           }
         }
         container pppoe-underlying-information {
           list pppoe-underlying-interface {
             leaf dynamic-profile {
               type string;
               description "Dynamic Profile name";
             }
             leaf service-name-table {
               type string;
               description "Name of Service Name Table";
             }
             leaf max-sessions {
               type int32;
               description "Maximum number of PPPoE sessions";
             }
             leaf max-sessions-vsa-ignore {
               type string;
               description "Ignore max-sessions VSA";
             }
             leaf duplicate-protection {
               type string;
               description "Duplicate protection mode";
             }
             leaf short-cycle-protection {
               type string;
               description "Short cycle protection mode";
             }
             leaf direct-connect {
               type string;
               description "Direct connect mode";
             }
             leaf ac-name {
               type string;
               description "Access Concentrator name";
             }
             leaf underlying-interface-name {
               type string;
               description "Underlying interface name";
             }
             leaf underlying-interface-index {
               type string;
               description "Underlying interface index";
             }
             leaf encapsulation-type-identifier {
               type string;
               description "Encapsulation type identifier";
             }
             leaf state {
               type string;
               description "State";
             }
             leaf active-sessions {
               type int32;
               description "Number of active PPPoE sessions";
             }
             leaf aci-autosensing {
               type string;
               description "ACI VLAN Autosensing mode";
             }
             leaf line-identity-autosensing {
               type string;
               description "Line Identity Autosensing mode";
             }
           }
         }
         container aci-vlan-information {
           leaf dynamic-profile {
             type string;
             description "Dynamic Profile name";
           }
         }
         container line-identity-information {
           leaf dynamic-profile {
             type string;
             description "Dynamic Profile name";
           }
           leaf circuit-id {
             type string;
             description "Aci vlan attribute";
           }
           leaf remote-id {
             type string;
             description "Aci vlan attribute";
           }
           leaf accept-no-ids {
             type string;
             description "Aci vlan attribute";
           }
         }
         container demux-information {
           container demux-interface {
             leaf demux-underlying-interface-name {
               type string;
               description "Underlying interface name";
             }
             leaf demux-underlying-interface-index {
               type string;
               description "Underlying interface index";
             }
             leaf demux-inet-prefix-type {
               type string;
               description "Prefix type";
             }
             leaf demux-inet-prefix-count {
               type string;
               description "IPv4 Prefix count";
             }
             leaf demux-inet-prefix {
               type string;
               description "IPv4 Prefix";
             }
             leaf demux-inet6-prefix-type {
               type string;
               description "Prefix type";
             }
             leaf demux-inet6-prefix-count {
               type string;
               description "IPv6 Prefix count";
             }
             leaf demux-inet6-prefix {
               type string;
               description "IPv6 Prefix";
             }
           }
         }
         container dual-ad-icl-color-information {
           container dual-ad-icl-color-info {
             leaf dual-ad-icl-color-type {
               type uint32;
               description "Dual-AD ICL Color Type";
             }
             leaf dual-ad-icl-color {
               type uint32;
               description "Dual-AD ICL Color";
             }
           }
         }
         container dialer-information {
           leaf dialer-time-to-disconnect {
             type string;
             description "Time for dialer to disconnect due to idle timeout";
           }
           container dialer-interface {
             leaf dialer-interface-name {
               type string;
               description "Interface name";
             }
             leaf dialer-interface-state {
               type string;
               description "Dialer interface state";
             }
             leaf pool-id {
               type string;
               description "Pool identifier";
             }
             leaf primary-interface {
               type string;
               description "Primary interface";
             }
             leaf activation-delay {
               type string;
               description "Activation delay";
             }
             leaf deactivation-delay {
               type string;
               description "Deactivation delay";
             }
             leaf activation-delay-elapsed {
               type string;
               description "Activation delay elapsed";
             }
             leaf deactivation-delay-elapsed {
               type string;
               description "Deactivation delay elapsed";
             }
             leaf call-idle-timeout {
               type string;
               description "Call idle timeout";
             }
             leaf initial-route-check {
               type string;
               description "Initial route check delay";
             }
             leaf redial-delay {
               type string;
               description "Delay before dialer dials out again (seconds)";
             }
             leaf callback-wait-period {
               type string;
               description "Delay before dialer attempts callback (seconds)";
             }
             leaf callback-wait-period-elapsed {
               type string;
               description "Number of seconds in callback wait period that have elapsed";
             }
             leaf load-threshold {
               type string;
               description "Load threshold that determines when interfaces are added to bundle";
             }
             leaf load-interval {
               type string;
               description "Interval over which average load is calculated";
             }
             container dialer-interface-flags {
               leaf backup {
                 type empty;
                 description "Dialer backup";
               }
               leaf multilink {
                 type empty;
                 description "Dialer multilink";
               }
               leaf watchlist {
                 type empty;
                 description "Dialer watchlist";
               }
               leaf interesting-detected {
                 type empty;
                 description "Interesting packet detected";
               }
             }
           }
         }
         container shared-interface-information {
           container shared-interface-logical-interface {
             leaf peer-interface-name {
               type string;
               description "Peer interface name";
             }
             leaf interface-shared-with {
               type string;
               description "Logical interface owner";
             }
             leaf rx-fe {
               type string;
               description "Rx tunnel token forwarding element";
             }
             leaf rx-nhid {
               type string;
               description "Rx tunnel token next hop index";
             }
             leaf tx-fe {
               type string;
               description "Tx tunnel token forwarding element";
             }
             leaf tx-nhid {
               type string;
               description "Tx tunnel token next hop index";
             }
           }
         }
         container mac-database {
           list mac-record {
             leaf mac-address {
               type jt:mac-addr;
             }
             leaf receive-frames {
               type int32;
             }
             leaf receive-bytes {
               type int32;
             }
             leaf transmit-frames {
               type int32;
             }
             leaf transmit-bytes {
               type int32;
             }
           }
         }
         container policer-overhead {
           leaf ingress-policer-overhead {
             type int32;
             description "Ingress policer overhead information";
           }
           leaf egress-policer-overhead {
             type int32;
             description "Egress policer overhead information";
           }
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-link-information {
           leaf multilink-active-bundle-links {
             type int32;
             description "Number of active bundle links in this multilink bundle instance";
           }
           leaf multilink-removed-bundle-links {
             type int32;
             description "Number of bundle links that are removed from service in this multilink bundle instance";
           }
           leaf multilink-disabled-bundle-links {
             type int32;
             description "Number of bundle links that are not allowed to transmit in this multilink bundle instance";
           }
         }
         container multilink-bundle-options {
           leaf mrru {
             type int32;
           }
           leaf remote-mrru {
             type int32;
             description "Remote max received reconstructed unit";
           }
           leaf drop-timeout {
             type int32;
           }
           leaf mlppp-inner-ppp-pfc {
             type string;
             description "MLPPP inner PPP protocol field compression";
           }
           leaf sequence-number-format {
             type string;
           }
           leaf ml-fragment-threshold {
             type int32;
           }
           leaf minimum-links {
             type int32;
           }
           leaf interleave-fragments {
             type string;
           }
           leaf multilink-classes {
             type int32;
             description "Number of multilink classes";
           }
           leaf link-layer-overhead {
             type string;
             description "Link layer overhead";
           }
           leaf filler-packet-interval {
             type int32;
           }
         }
         container multilink-bundle-errors {
           leaf packet-drops {
             type int32;
             description "Number of packets dropped";
           }
           leaf packet-drop-bytes {
             type int32;
             description "Number of bytes in dropped packets";
           }
           leaf fragment-drops {
             type int32;
             description "Number of fragments dropped";
           }
           leaf fragment-drop-bytes {
             type int32;
             description "Number of bytes in dropped fragments";
           }
           leaf mrru-exceeded {
             type int32;
             description "Number of assembled packets that exceeded MRRU";
           }
           leaf processing-errors {
             type int32;
             description "Number of errors encountered in assembling packets";
           }
         }
         container multilink-traffic-statistics {
           container bundle {
             container multilink-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-v6-frames {
               leaf inputv6-packets {
                 type int32;
               }
               leaf inputv6-bytes {
                 type int32;
               }
               leaf outputv6-packets {
                 type int32;
               }
               leaf outputv6-bytes {
                 type int32;
               }
             }
           }
           container class {
             container class-info {
               leaf multilink-class-id {
                 type int32;
                 description "Multilink class ID";
               }
             }
             container multilink-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
             container network-frames {
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
           list link {
             leaf name {
               type string;
               description "Name of this item";
             }
             leaf down {
               type empty;
               description "Link is down";
             }
             leaf link-uptime {
               type string;
               description "Total uptime for the member link";
             }
             leaf input-frames {
               type int32;
             }
             leaf input-fps {
               type int32;
             }
             leaf input-bytes {
               type int32;
             }
             leaf input-bps {
               type int32;
             }
             leaf output-frames {
               type int32;
             }
             leaf output-fps {
               type int32;
             }
             leaf output-bytes {
               type int32;
             }
             leaf output-bps {
               type int32;
             }
           }
           container multilink-detail-statistics {
             container bundle-detail {
               container fragments {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container lfi {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
             container class-detail {
               container class-info {
                 leaf multilink-class-id {
                   type int32;
                   description "Multilink class ID";
                 }
               }
               container fragments {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
               container non-fragments {
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container crtp {
             container crtp-sessions {
               leaf input-frames {
                 type int32;
               }
               leaf output-frames {
                 type int32;
               }
             }
             list crtp-statistics {
               leaf name {
                 type string;
                 description "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container statistics-account-overhead {
           leaf ingress-account-overhead {
             type int32;
             description "Ingress Statistics account overhead information";
           }
           leaf egress-account-overhead {
             type int32;
             description "Egress Statistics account overhead information";
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container local-traffic-statistics {
           leaf input-bytes {
             type int32;
           }
           leaf input-bps {
             type int32;
           }
           leaf output-bytes {
             type int32;
           }
           leaf output-bps {
             type int32;
           }
           leaf input-packets {
             type int32;
           }
           leaf input-pps {
             type int32;
           }
           leaf output-packets {
             type int32;
           }
           leaf output-pps {
             type int32;
           }
         }
         container transit-traffic-statistics {
           leaf input-bytes {
             type int32;
           }
           leaf input-bps {
             type int32;
           }
           leaf output-bytes {
             type int32;
           }
           leaf output-bps {
             type int32;
           }
           leaf input-packets {
             type int32;
           }
           leaf input-pps {
             type int32;
           }
           leaf output-packets {
             type int32;
           }
           leaf output-pps {
             type int32;
           }
           container ipv6-transit-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-total-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container keepalive-config {
           leaf keepalive-interval {
             type int32;
           }
           leaf keepalive-up-count {
             type int32;
           }
           leaf keepalive-down-count {
             type int32;
           }
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container ppp-flags {
           leaf iff-ppp-flags-acfc {
             type empty;
           }
           leaf iff-ppp-flags-pfc {
             type empty;
           }
         }
         list ncp-information {
           leaf ncp-protocol {
             type string;
             description "Network protocol for this NCP instance";
           }
           leaf ncp-state {
             type string;
             description "State of this NCP instance";
           }
         }
         container virtual-circuit-information {
           leaf vpi {
             type int32;
             description "Virtual path identifier";
           }
           leaf vci {
             type int32;
             description "Virtual circuit identifier";
           }
           leaf psn-tag {
             type string;
             description "VPI/VCI swapping configuration";
           }
           leaf psn-vpi {
             type int32;
             description "PSN virtual path identifier";
           }
           leaf psn-vci {
             type int32;
             description "PSN virtual circuit identifier";
           }
           leaf trunk {
             type int32;
             description "ATM trunk identifier";
           }
           leaf dlci {
             type int32;
           }
           leaf swapping {
             type string;
             description "VPI/VCI swapping configuration";
           }
           leaf trunk-bandwidth {
             type int32;
             description "ATM trunk bandwidth";
           }
           leaf atm-tm-cbr {
             type empty;
             description "Constant bit rate";
           }
           leaf atm-tm-vbr {
             type empty;
             description "Variable bit rate";
           }
           leaf atm-tm-rtvbr {
             type empty;
             description "Real-time variable bit rate";
           }
           leaf peak {
             type int32;
           }
           leaf sustained {
             type int32;
           }
           leaf burst {
             type int32;
           }
           leaf cdvt {
             type int32;
           }
           leaf queue-limit {
             type int32;
           }
           leaf down-time {
             type int32;
             description "Total down time for this circuit";
           }
           leaf last-down-time {
             type int32;
             description "Time elapsed since circuit last went down";
           }
           leaf ifvc-epd {
             type int32;
             description "Early packet discard threshold";
           }
           leaf ifvc-weight {
             type int32;
             description "Transmit weight";
           }
           leaf ifvc-epd-plp0 {
             type int32;
             description "Early packet discard threshold for PLP 0";
           }
           leaf ifvc-epd-plp1 {
             type int32;
             description "Early packet discard threshold for PLP 1";
           }
           container vci-range {
             leaf vpi {
               type int32;
               description "Virtual path identifier";
             }
             leaf start-vci {
               type int32;
               description "ATM VCI range's start value";
             }
             leaf end-vci {
               type int32;
               description "ATM VCI range's end value";
             }
           }
           container ifvc-flags {
             leaf ifvc-down {
               type empty;
             }
             leaf ifvc-none {
               type empty;
             }
             leaf ifvc-active {
               type empty;
             }
             leaf ifvc-closed {
               type empty;
             }
             leaf ifvc-inverse-arp {
               type empty;
             }
             leaf ifvc-ilmi {
               type empty;
             }
             leaf ifvc-oam {
               type empty;
             }
             leaf ifvc-shaping {
               type empty;
             }
             leaf ifvc-passiveoam {
               type empty;
             }
             leaf ifvc-multicast {
               type empty;
             }
             leaf ifvc-ccc-down {
               type empty;
             }
             leaf ifvc-configured {
               type empty;
               description "DCE-end is configured";
             }
             leaf ifvc-unconfigured {
               type empty;
               description "DCE-end is unconfigured";
             }
             leaf generic-value {
               type int32;
               description "Hexadecimal value of unknown flag bits";
             }
           }
           container ifvc-multipoint-destination {
             leaf multipoint-address {
               type string;
               description "Protocol address of the remote side of this connection";
             }
           }
           container oam-parameters {
             leaf period {
               type int32;
             }
             leaf up-count {
               type int32;
             }
             leaf down-count {
               type int32;
             }
           }
           container oam-statistics {
             leaf oam-total-received-count {
               type int32;
             }
             leaf oam-total-transmitted-count {
               type int32;
             }
             leaf oam-total-received-count-4 {
               type int32;
             }
             leaf oam-total-transmitted-count-4 {
               type int32;
             }
             leaf oam-loopback-received-count {
               type int32;
             }
             leaf oam-loopback-transmitted-count {
               type int32;
             }
             leaf oam-loopback-received-last {
               type string;
             }
             leaf oam-loopback-transmitted-last {
               type string;
             }
             leaf oam-rdi-received-count {
               type int32;
             }
             leaf oam-rdi-transmitted-count {
               type int32;
             }
             leaf oam-rdi-received-last {
               type string;
             }
             leaf oam-rdi-transmitted-last {
               type string;
             }
             leaf oam-ais-received-count {
               type int32;
             }
             leaf oam-ais-transmitted-count {
               type int32;
             }
             leaf oam-ais-received-last {
               type string;
             }
             leaf oam-ais-transmitted-last {
               type string;
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-policer-statistics {
             leaf non-conform-clp0-cells {
               type int32;
               description "UPC non-conforming ATM CLP0 cell";
             }
             leaf non-conform-clp1-cells {
               type int32;
               description "UPC non-conforming ATM CLP1 cell";
             }
             leaf tagged-cells {
               type int32;
               description "UPC tagged cell";
             }
           }
           container atm-statistics {
             leaf vc-queue-drops {
               type int32;
             }
           }
           container atm-cos-information {
             leaf vc-cos-mode {
               type string;
               description "Virtual circuit CoS scheduling mode";
             }
             list atm-cos-queue {
               container atm-cos-queue-parameters {
                 leaf cos-forwarding-class-name {
                   type string;
                   description "Forwarding class name associated with queue";
                 }
                 leaf cos-queue-number {
                   type int32;
                   description "Queue number";
                 }
                 leaf scheduling-priority {
                   type string;
                   description "Scheduling priority";
                 }
                 leaf transmit-weight-cells {
                   type int32;
                   description "Weight to apply to scheduling as number of cells";
                 }
                 leaf transmit-weight-percent {
                   type int32;
                   description "Weight to apply to scheduling as fill percentage";
                 }
                 leaf epd-threshold {
                   type int32;
                   description "Early packet drop threshold";
                 }
                 leaf epd-threshold-plp0 {
                   type int32;
                   description "Early packet drop threshold for PLP 0";
                 }
                 leaf epd-threshold-plp1 {
                   type int32;
                   description "Early packet drop threshold for PLP 1";
                 }
                 container linear-red-drop-profile {
                   leaf queue-depth {
                     type uint32;
                     description "Instantaneous queue depth";
                   }
                   leaf low-red {
                     type int32;
                     description "Fill level percentage when linear RED is applied for low PLP";
                   }
                   leaf high-red {
                     type int32;
                     description "Fill level percentage when linear RED is applied for high PLP";
                   }
                   leaf max-low-red {
                     type int32;
                     description "Fill level percentage with 100% packet drop for low PLP";
                   }
                   leaf max-high-red {
                     type int32;
                     description "Fill level percentage with 100% packet drop for high PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
           container in-arp-statistics {
             leaf received-count {
               type int32;
               description "Number of ARPs received";
             }
             leaf transmitted-count {
               type int32;
               description "Number of ARPs sent";
             }
             leaf denied-count {
               type int32;
               description "Number of ARPs denied";
             }
             leaf operation-not-supported-count {
               type int32;
               description "Number of ARPs with operation not supported";
             }
             leaf bad-packet-length-count {
               type int32;
               description "Number of ARPs with bad packet length";
             }
             leaf bad-protocol-count {
               type int32;
               description "Number of ARPs with bad protocol";
             }
             leaf bad-protocol-length-count {
               type int32;
               description "Number of ARPs with bad protocol length";
             }
             leaf bad-hardware-length-count {
               type int32;
               description "Number of ARPs with bad hardware length";
             }
             leaf dropped-count {
               type int32;
               description "Number of ARPs dropped";
             }
             leaf last-received {
               type string;
               description "Time an ARP was last received";
             }
             leaf last-transmitted {
               type string;
               description "Time an ARP was last sent";
             }
           }
           container dlci-statistics {
             leaf dlci-active {
               type int32;
               description "Number of DLCIs in active state";
             }
             leaf dlci-inactive {
               type int32;
               description "Number of DLCIs in inactive state";
             }
           }
         }
         list filter-information {
           leaf-list filter-input {
             type string;
             description "Name of the input filter";
           }
           leaf-list filter-input-precedence {
             type uint32;
             description "Precedence of the input filter";
           }
           leaf-list filter-output {
             type string;
             description "Name of the output filter";
           }
           leaf-list filter-output-precedence {
             type uint32;
             description "Precedence of the output filter";
           }
         }
         list address-family {
           leaf compression-device-name {
             type string;
             description "Name of the link service device";
           }
           leaf address-family-name {
             type string;
           }
           leaf multilink-bundle-name {
             type string;
             description "Name of the multilink bundle for this address family";
           }
           leaf as-bundle-name {
             type string;
             description "Name of the aggregated SONET bundle for this address family";
           }
           leaf ae-bundle-name {
             type string;
             description "Name of the aggregated Ethernet bundle";
           }
           leaf es-sa-name {
             type string;
             description "Name of the IPSec security association for this address family";
           }
           leaf mtu {
             type string;
             description "MTU size on this interface";
           }
           leaf maximum-labels {
             type uint32;
             description "Maximum labels on MPLS iffamily";
           }
           leaf generation {
             type int32;
             description "Generation number used to distinguish between successive instances of this interface";
           }
           leaf route-table {
             type int32;
           }
           leaf vpls-mesh-group {
             type string;
           }
           leaf es-sa-fail-count {
             type int32;
             description "Number of failures for IPSec security association for this family";
           }
           leaf es-sa-xmt-seq-num {
             type int32;
             description "Transmit sequence number of IPSec security association family";
           }
           leaf es-sa-recv-seq-num {
             type int32;
             description "Receive sequence number of IPSec security association family";
           }
           leaf evpn-multihomed-status {
             type string;
           }
           leaf evpn-mh-esi-sh-label {
             type string;
           }
           leaf iff-next-hop {
             type int32;
             description "Interface family next-hop";
           }
           leaf iff-vpls-status {
             type string;
             description "Interface family vpls status";
           }
           leaf max-local-cache {
             type uint32;
             description "Max local nh cache size";
           }
           leaf new-hold-limit {
             type uint32;
             description "Max limit on new unresolved nh";
           }
           leaf intf-curr-cnt {
             type uint32;
             description "Current nh total cache size on this interface";
           }
           leaf intf-unresolved-cnt {
             type uint32;
             description "Current new unresolved nh cache size on this interface";
           }
           leaf intf-dropcnt {
             type uint32;
             description "Current interface nh drop count";
           }
           leaf mlppp-service-interface {
             type string;
             description "Name of the multilink service interface for this address family";
           }
           leaf mlppp-service-dev-pool {
             type string;
             description "Name of the multilink service device pool for this address family";
           }
           leaf mlppp-dynamic-profile {
             type string;
             description "Name of the multilink dynamic profile for this address family";
           }
           leaf arp-respond-any-local-address {
             type string;
             description "Respond to ARP requests for any local address";
           }
           leaf local-bias-information {
             type string;
           }
           leaf ft-iff-dest-port {
             type uint32;
             description "Destination UDP port to be used for this family";
           }
           container address-family-flags {
             leaf ifff-none {
               type empty;
             }
             leaf ifff-primary {
               type empty;
             }
             leaf ifff-redirects {
               type empty;
             }
             leaf ifff-no-redirects {
               type empty;
             }
             leaf ifff-no-neighbor-learn {
               type empty;
             }
             leaf ifff-targeted-broadcast {
               type empty;
             }
             leaf ifff-sendbcast-pkt-to-re {
               type empty;
             }
             leaf ifff-hard-down {
               type empty;
             }
             leaf ifff-down {
               type empty;
             }
             leaf ifff-up {
               type empty;
             }
             leaf ifff-func1 {
               type empty;
             }
             leaf ifff-func2 {
               type empty;
             }
             leaf ifff-is-primary {
               type empty;
             }
             leaf ifff-recv-options {
               type empty;
             }
             leaf ifff-recv-ttl-exceeded {
               type empty;
             }
             leaf ifff-dst-class-usage {
               type empty;
             }
             leaf ifff-src-class-input {
               type empty;
             }
             leaf ifff-src-class-output {
               type empty;
             }
             leaf ifff-mtu-user-conf {
               type empty;
             }
             leaf ifff-mac-validate-strict {
               type empty;
             }
             leaf ifff-mac-validate-loose {
               type empty;
             }
             leaf ifff-rpf-check {
               type empty;
             }
             leaf ifff-rpf-loose-mode {
               type empty;
             }
             leaf ifff-sample-input {
               type empty;
             }
             leaf ifff-sample-output {
               type empty;
             }
             leaf ifff-no-asynch-notification {
               type empty;
             }
             leaf ifff-negotiate-address {
               type empty;
             }
             leaf ifff-port-mode-trunk {
               type empty;
             }
             leaf ifff-inter-switch-link {
               type empty;
             }
             leaf ifff-mtu-protocol-adj {
               type empty;
             }
             leaf ifff-unnumbered {
               type empty;
             }
             leaf ifff-tcc-mpls {
               type empty;
             }
             leaf ifff-tcc-inet {
               type empty;
             }
             leaf ifff-tcc-inet6 {
               type empty;
             }
             leaf ifff-tcc-iso {
               type empty;
             }
             leaf ifff-port-mode-isid-trunk {
               type empty;
             }
             leaf generic-value {
               type int32;
               description "Hexadecimal value of unknown flag bits";
             }
           }
           list address-family-unnumbered {
             leaf unnumbered-family-donor-interface-name {
               type string;
               description "Donor interface name";
             }
             leaf unnumbered-family-donor-interface-index {
               type string;
               description "Donor interface index";
             }
             leaf unnumbered-family-preferred-source-address {
               type string;
               description "Unnumbered interface preferred source address";
             }
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           list filter-information {
             leaf-list filter-input {
               type string;
               description "Name of the input filter";
             }
             leaf-list filter-input-precedence {
               type uint32;
               description "Precedence of the input filter";
             }
             leaf-list filter-output {
               type string;
               description "Name of the output filter";
             }
             leaf-list filter-output-precedence {
               type uint32;
               description "Precedence of the output filter";
             }
           }
           list policer-information {
             leaf policer-input {
               type string;
               description "Name of the input policer";
             }
             leaf policer-output {
               type string;
               description "Name of the output policer";
             }
           }
           list interface-address {
             leaf ifa-destination {
               type string;
               description "Protocol address of the remote side of this connection";
             }
             leaf ifa-local {
               type string;
               description "Protocol address on this interface";
             }
             leaf ifa-broadcast {
               type string;
               description "Network broadcast address";
             }
             leaf ifa-primary-dns {
               type string;
               description "Primary DNS server address";
             }
             leaf ifa-primary-nbns {
               type string;
               description "Primary Netbios Name server address";
             }
             leaf ifa-secondary-dns {
               type string;
               description "Secondary DNS server address";
             }
             leaf ifa-secondary-nbns {
               type string;
               description "Secondary Netbios Name server address";
             }
             leaf ifa-address-pool {
               type string;
               description "Address pool name";
             }
             leaf generation {
               type int32;
               description "Generation number used to distinguish between successive instances of this interface";
             }
             container ifa-flags {
               leaf ifaf-none {
                 type empty;
               }
               leaf ifaf-primary {
                 type empty;
               }
               leaf ifaf-preferred {
                 type empty;
               }
               leaf ifaf-master-only {
                 type empty;
               }
               leaf ifaf-down {
                 type empty;
               }
               leaf ifaf-kernel {
                 type empty;
               }
               leaf ifaf-current-default {
                 type empty;
               }
               leaf ifaf-current-preferred {
                 type empty;
               }
               leaf ifaf-current-primary {
                 type empty;
               }
               leaf ifaf-duplicate {
                 type empty;
               }
               leaf ifaf-webauth-http {
                 type empty;
               }
               leaf generic-value {
                 type int32;
                 description "Hexadecimal value of unknown flag bits";
               }
             }
             container in6-addr-flags {
               leaf in6-anycast {
                 type empty;
               }
               leaf in6-tentative {
                 type empty;
               }
               leaf in6-duplicate {
                 type empty;
               }
               leaf in6-detached {
                 type empty;
               }
               leaf in6-deprecated {
                 type empty;
               }
               leaf in6-nodad {
                 type empty;
               }
               leaf in6-temporary {
                 type empty;
               }
               leaf in6-autoconf {
                 type empty;
               }
               leaf in6-nopfxmgmt {
                 type empty;
               }
             }
           }
           container mac-validate-statistics {
             leaf mac-validate-packets {
               type int32;
               description "Number of packets that have failed the mac-validate check";
             }
             leaf mac-validate-bytes {
               type int32;
               description "Number of bytes that have failed the mac-validate check";
             }
           }
           container route-rpf-statistics {
             leaf route-rpf-packets {
               type int32;
               description "Number of packets that have failed the RPF check";
             }
             leaf route-rpf-bytes {
               type int32;
               description "Number of bytes that have failed the RPF check";
             }
           }
           container destination-class-statistics {
             list destination-class {
               leaf dcu-class-name {
                 type string;
                 description "Name of DCU class";
               }
               leaf dcu-class-packets {
                 type int32;
                 description "Number of packets counted by DCU for this class";
               }
               leaf dcu-class-bytes {
                 type int32;
                 description "Number of bytes counted by DCU for this class";
               }
               leaf dcu-class-pps {
                 type int32;
                 description "Packet-per-seconds counted by DCU for this class";
               }
               leaf dcu-class-bps {
                 type int32;
                 description "Bit-per-seconds counted by DCU for this class";
               }
             }
           }
           container source-class-statistics {
             list source-class {
               leaf scu-class-name {
                 type string;
                 description "Name of SCU class";
               }
               leaf scu-class-packets {
                 type int32;
                 description "Number of packets counted by SCU for this class";
               }
               leaf scu-class-bytes {
                 type int32;
                 description "Number of bytes counted by SCU for this class";
               }
               leaf scu-class-pps {
                 type int32;
                 description "Packet-per-seconds counted by SCU for this class";
               }
               leaf scu-class-bps {
                 type int32;
                 description "Bit-per-seconds counted by SCU for this class";
               }
             }
           }
         }
         list bridge-iff-properties {
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container irb-domain {
           leaf irb-routing-instance {
             type string;
             description "Name of the Routing Instance";
           }
           leaf irb-bridge {
             type string;
             description "Name of the Bridging Domain";
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         container vtep-info {
           leaf vtep-type {
             type string;
             description "Type of VXLAN endpoint";
           }
           leaf vtep-address {
             type string;
             description "Protocol address of the connection";
           }
           leaf vtep-l2-routing-instance {
             type string;
             description "Name of the layer-2 routing instance";
           }
           leaf vtep-l3-routing-instance {
             type string;
             description "Name of the layer-3 routing instance";
           }
         }
         container ft-info {
           leaf ft-encap {
             type string;
             description "Type of encap used for FTI";
           }
           leaf ft-dest-port {
             type int32;
             description "Destnation UDP port used in encap";
           }
           leaf ft-vnid {
             type int32;
             description "VNI value used in encap";
           }
           leaf ft-src-addr {
             type string;
             description "Source address used for encap";
           }
           leaf ft-dst-addr {
             type string;
             description "Destination address used for encap";
           }
         }
         container rbeb-info {
           leaf rbeb-address {
             type string;
             description "Protocol address of the connection";
           }
           leaf rbeb-l2-routing-instance {
             type string;
             description "Name of the layer-2 routing instance";
           }
         }
         list macsec-statistics {
           leaf interface-name {
             type string;
             description "Class-of-service interface name";
           }
           leaf encrypted-packets {
             type uint64;
             description "Macsec encrypted packets sent";
           }
           leaf encrypted-bytes {
             type uint64;
             description "Macsec encrypted bytes sent";
           }
           leaf protected-packets {
             type uint64;
             description "Macsec packets sent with only integrity protection";
           }
           leaf protected-bytes {
             type uint64;
             description "Macsec bytes sent with only integrity protection";
           }
           leaf ok-packets {
             type uint64;
             description "Macsec packets accepted";
           }
           leaf decrypted-bytes {
             type uint64;
             description "Macsec received bytes decrypted";
           }
           leaf decrypted-packets {
             type uint64;
             description "Macsec received packets decrypted";
           }
           leaf validated-packets {
             type uint64;
             description "Macsec received packets validated";
           }
           leaf validated-bytes {
             type uint64;
             description "Macsec received bytes validated";
           }
           leaf untagged-packets {
             type uint64;
             description "Macsec untagged packets";
           }
           leaf toolong-packets {
             type uint64;
             description "Macsec too long packets transmitted on a secure channel";
           }
           leaf control-packets {
             type uint64;
             description "Macsec control packets received on a secure channel";
           }
           leaf tagged-miss-packets {
             type uint64;
             description "Macsec tagged miss packets received on a secure channel";
           }
           leaf untagged-hit-packets {
             type uint64;
             description "Macsec untagged hit packets received on a secure channel";
           }
           leaf notag-packets {
             type uint64;
             description "Macsec no tag packets received on a secure channel";
           }
           leaf badtag-packets {
             type uint64;
             description "Macsec bad tag packets received on a secure channel";
           }
           leaf unknown-sci-packets {
             type uint64;
             description "Macsec unknown sci packets received on a secure channel";
           }
           leaf no-sci-packets {
             type uint64;
             description "Macsec no sci packets received on a secure channel";
           }
           leaf control-pass-packets {
             type uint64;
             description "Macsec allowed control packets received on a secure channel";
           }
           leaf uncontrol-pass-packets {
             type uint64;
             description "Macsec allowed uncontrol packets received on a secure channel";
           }
           leaf control-fail-packets {
             type uint64;
             description "Macsec dropped control packets received on a secure channel";
           }
           leaf uncontrol-fail-packets {
             type uint64;
             description "Macsec dropped uncontrol packets received on a secure channel";
           }
           leaf hit-dropped-packets {
             type uint64;
             description "Macsec hit dropped packets received on a security channel";
           }
           leaf notusing-sa-packets {
             type uint64;
             description "Macsec not using sa packets received on a security channel";
           }
           leaf unused-sa-packets {
             type uint64;
             description "Macsec unused sa packets received on a security channel";
           }
           leaf late-packets {
             type uint64;
             description "Macsec late packets dropped on a security channel";
           }
           leaf delayed-packets {
             type uint64;
             description "Macsec delayed packets accepted on a security channel";
           }
           leaf unchecked-packets {
             type uint64;
             description "Macsec unchecked packets accepted on a security channel";
           }
           leaf notvalid-packets {
             type uint64;
             description "Macsec not valid packets dropped on a security channel";
           }
           leaf invalid-packets {
             type uint64;
             description "Macsec invalid packets accepted on a security channel";
           }
           list secure-channel-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-association-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-channel-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list secure-association-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list macsec-error-information {
             list secure-channel-sent-errors {
               leaf untagged-packets {
                 type uint64;
                 description "Macsec untagged packets";
               }
               leaf toolong-packets {
                 type uint64;
                 description "Macsec too long packets transmitted on a secure channel";
               }
             }
             list secure-channel-received-errors {
               leaf control-packets {
                 type uint64;
                 description "Macsec control packets received on a secure channel";
               }
               leaf tagged-miss-packets {
                 type uint64;
                 description "Macsec tagged miss packets received on a secure channel";
               }
               leaf untagged-hit-packets {
                 type uint64;
                 description "Macsec untagged hit packets received on a secure channel";
               }
               leaf untagged-packets {
                 type uint64;
                 description "Macsec untagged packets";
               }
               leaf notag-packets {
                 type uint64;
                 description "Macsec no tag packets received on a secure channel";
               }
               leaf badtag-packets {
                 type uint64;
                 description "Macsec bad tag packets received on a secure channel";
               }
               leaf unknown-sci-packets {
                 type uint64;
                 description "Macsec unknown sci packets received on a secure channel";
               }
               leaf no-sci-packets {
                 type uint64;
                 description "Macsec no sci packets received on a secure channel";
               }
               leaf control-pass-packets {
                 type uint64;
                 description "Macsec allowed control packets received on a secure channel";
               }
               leaf control-fail-packets {
                 type uint64;
                 description "Macsec dropped control packets received on a secure channel";
               }
               leaf uncontrol-pass-packets {
                 type uint64;
                 description "Macsec allowed uncontrol packets received on a secure channel";
               }
               leaf uncontrol-fail-packets {
                 type uint64;
                 description "Macsec dropped uncontrol packets received on a secure channel";
               }
             }
             list secure-channel-received-extended {
               leaf hit-dropped-packets {
                 type uint64;
                 description "Macsec hit dropped packets received on a security channel";
               }
               leaf invalid-packets {
                 type uint64;
                 description "Macsec invalid packets accepted on a security channel";
               }
               leaf late-packets {
                 type uint64;
                 description "Macsec late packets dropped on a security channel";
               }
               leaf delayed-packets {
                 type uint64;
                 description "Macsec delayed packets accepted on a security channel";
               }
               leaf unchecked-packets {
                 type uint64;
                 description "Macsec unchecked packets accepted on a security channel";
               }
               leaf notvalid-packets {
                 type uint64;
                 description "Macsec not valid packets dropped on a security channel";
               }
               leaf notusing-sa-packets {
                 type uint64;
                 description "Macsec not using sa packets received on a security channel";
               }
               leaf unused-sa-packets {
                 type uint64;
                 description "Macsec unused sa packets received on a security channel";
               }
               leaf untagged-hit-packets {
                 type uint64;
                 description "Macsec untagged hit packets received on a secure channel";
               }
             }
           }
         }
         container multilink-bundle-status {
           leaf rx-sequence-number {
             type string;
             description "Received sequence number";
           }
           leaf tx-sequence-number {
             type string;
             description "Transmitted sequence number";
           }
           leaf packet-drops {
             type int32;
             description "Number of packets dropped";
           }
           leaf packet-drop-bytes {
             type int32;
             description "Number of bytes in dropped packets";
           }
           leaf fragment-drops {
             type int32;
             description "Number of fragments dropped";
           }
           leaf fragment-drop-bytes {
             type int32;
             description "Number of bytes in dropped fragments";
           }
           leaf mrru-exceeded {
             type int32;
             description "Number of assembled packets that exceeded MRRU";
           }
           leaf processing-errors {
             type int32;
             description "Number of errors encountered in assembling packets";
           }
           leaf fragment-timeout {
             type int32;
             description "Fragments timed out during assembly";
           }
           leaf sequence-number-missing {
             type int32;
             description "Gap detected in sequence numbers";
           }
           leaf out-of-order-sequence-number {
             type int32;
             description "Fragments with an out-of-order sequence number";
           }
           leaf out-of-range-sequence-number {
             type int32;
             description "Fragments with an out-of-range sequence number";
           }
           leaf packet-buffer-overflow {
             type int32;
             description "Number of times the packet data buffer overflowed";
           }
           leaf fragment-buffer-overflow {
             type int32;
             description "Number of times the fragment data buffer overflowed";
           }
         }
         container multilink-bundle-class {
           leaf multilink-class-id {
             type int32;
             description "Multilink class ID";
           }
           leaf rx-sequence-number {
             type string;
             description "Received sequence number";
           }
           leaf tx-sequence-number {
             type string;
             description "Transmitted sequence number";
           }
           leaf packet-drops {
             type int32;
             description "Number of packets dropped";
           }
           leaf packet-drop-bytes {
             type int32;
             description "Number of bytes in dropped packets";
           }
           leaf fragment-drops {
             type int32;
             description "Number of fragments dropped";
           }
           leaf fragment-drop-bytes {
             type int32;
             description "Number of bytes in dropped fragments";
           }
           leaf mrru-exceeded {
             type int32;
             description "Number of assembled packets that exceeded MRRU";
           }
           leaf processing-errors {
             type int32;
             description "Number of errors encountered in assembling packets";
           }
           leaf fragment-timeout {
             type int32;
             description "Fragments timed out during assembly";
           }
           leaf sequence-number-missing {
             type int32;
             description "Gap detected in sequence numbers";
           }
           leaf out-of-order-sequence-number {
             type int32;
             description "Fragments with an out-of-order sequence number";
           }
           leaf out-of-range-sequence-number {
             type int32;
             description "Fragments with an out-of-range sequence number";
           }
           leaf packet-buffer-overflow {
             type int32;
             description "Number of times the packet data buffer overflowed";
           }
           leaf fragment-buffer-overflow {
             type int32;
             description "Number of times the fragment data buffer overflowed";
           }
           leaf multilink-class-drop-timeout {
             type int32;
             description "Drop timeout for multilink class (milliseconds)";
           }
         }
         container lag-traffic-statistics {
           container lag-bundle {
             leaf input-packets {
               type int32;
             }
             leaf input-pps {
               type int32;
             }
             leaf input-bytes {
               type int32;
             }
             leaf input-bps {
               type int32;
             }
             leaf output-packets {
               type int32;
             }
             leaf output-pps {
               type int32;
             }
             leaf output-bytes {
               type int32;
             }
             leaf output-bps {
               type int32;
             }
           }
           container lag-adaptive-statistics {
             leaf adaptive-adjusts {
               type int32;
             }
             leaf adaptive-scans {
               type int32;
             }
             leaf adaptive-updates {
               type int32;
             }
           }
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           container aggregate-member-info {
             leaf aggregate-member-count {
               type uint32;
             }
           }
           list lag-link {
             leaf name {
               type string;
               description "Name of this item";
             }
             leaf down {
               type empty;
               description "Link is down";
             }
             leaf input-packets {
               type int32;
             }
             leaf input-pps {
               type int32;
             }
             leaf input-bytes {
               type int32;
             }
             leaf input-bps {
               type int32;
             }
             leaf output-packets {
               type int32;
             }
             leaf output-pps {
               type int32;
             }
             leaf output-bytes {
               type int32;
             }
             leaf output-bps {
               type int32;
             }
           }
           list lag-bfd-view {
             leaf name {
               type string;
               description "Name of this item";
             }
             leaf link-usability {
               type string;
             }
           }
           list lag-targeting-summary {
             leaf targeting-intf-name {
               type string;
             }
             leaf targeting-intf-type {
               type string;
             }
             leaf targeting-intf-link-state {
               type string;
             }
           }
           list lag-marker {
             leaf name {
               type string;
               description "Name of this item";
             }
             leaf marker-rx-packets {
               type string;
             }
             leaf marker-response-tx-packets {
               type string;
             }
             leaf unknown-rx-packets {
               type string;
               description "Number of unknown type packets received";
             }
             leaf illegal-rx-packets {
               type string;
               description "Number of ill formed packets received";
             }
           }
           list lag-lacp-statistics {
             leaf name {
               type string;
               description "Name of this item";
             }
             leaf lacp-rx-packets {
               type string;
               description "Number of LACP packets received";
             }
             leaf lacp-tx-packets {
               type string;
               description "Number of LACP packets transmitted";
             }
             leaf unknown-rx-packets {
               type string;
               description "Number of unknown type packets received";
             }
             leaf illegal-rx-packets {
               type string;
               description "Number of ill formed packets received";
             }
           }
           list if-distribution-list-information {
             leaf list-type {
               type string;
             }
             leaf list-status {
               type string;
             }
             list if-list {
               leaf if-child-name {
                 type string;
               }
               leaf if-status {
                 type string;
               }
             }
           }
           list lag-link-protection-subgrp {
             leaf name {
               type string;
               description "Name of this item";
             }
             leaf lag-link-protection-subgrp-name {
               type string;
             }
             leaf lag-link-protection-subgrp-state {
               type string;
             }
           }
           list lag-lacp-info {
             leaf name {
               type string;
               description "Name of this item";
             }
             leaf lacp-role {
               type string;
               description "Whether it is an actor or partner";
             }
             leaf lacp-sys-priority {
               type string;
               description "System priority";
             }
             leaf lacp-system-id {
               type string;
               description "LACP system identifier";
             }
             leaf lacp-port-priority {
               type string;
               description "Priority of the port";
             }
             leaf lacp-port-number {
               type string;
               description "Port number";
             }
             leaf lacp-port-key {
               type string;
               description "Operational key of the port";
             }
           }
           list lag-lacp-state {
             leaf name {
               type string;
               description "Name of this item";
             }
             leaf lacp-role {
               type string;
               description "Whether it is an actor or partner";
             }
             leaf lacp-expired {
               type string;
               description "State of the receive lacp machine is EXPIRED?";
             }
             leaf lacp-defaulted {
               type string;
               description "State of the receive lacp machine is DEFAULTED?";
             }
             leaf lacp-distributing {
               type string;
               description "State of the mux lacp machine is DISTRIBUTING?";
             }
             leaf lacp-collecting {
               type string;
               description "State of the mux lacp machine is COLLECTING?";
             }
             leaf lacp-synchronization {
               type string;
               description "Actor view of partner information is in sync";
             }
             leaf lacp-aggregation {
               type string;
               description "Actor view of partner information is in sync";
             }
             leaf lacp-timeout {
               type string;
               description "Configured as either fast or slow periodic";
             }
             leaf lacp-activity {
               type string;
               description "Configured as either active or passive";
             }
           }
           list lag-lacp-protocol {
             leaf name {
               type string;
               description "Name of this item";
             }
             leaf lacp-receive-state {
               type string;
               description "State of the receive lacp machine";
             }
             leaf lacp-transmit-state {
               type string;
               description "State of the transmit lacp machine";
             }
             leaf lacp-mux-state {
               type string;
               description "State of the mux lacp machine";
             }
           }
           list lag-lacp-bfd {
             leaf name {
               type string;
               description "Name of this item";
             }
             leaf lacp-bfd-state {
               type string;
               description "State of the BFD session";
             }
           }
           list lacp-hold-up-information {
             leaf name {
               type string;
               description "Name of this item";
             }
             leaf status {
               type string;
             }
             leaf restart-count {
               type int32;
             }
             leaf time-to-expire {
               type int32;
             }
             leaf start-time {
               type string;
             }
           }
         }
         container layer2-input-policer-statistics {
           leaf policer-low-bytes {
             type int32;
             description "Number of loss priority low bytes";
           }
           leaf policer-low-frames {
             type int32;
             description "Number of loss priority low frames";
           }
           leaf policer-low-rate {
             type int32;
             description "Rate of loss priority low pkts";
           }
           leaf policer-medium-high-bytes {
             type int32;
             description "Number of loss priority medium high bytes";
           }
           leaf policer-medium-high-frames {
             type int32;
             description "Number of loss priority medium high frames";
           }
           leaf policer-medium-high-rate {
             type int32;
             description "Rate of loss priority medium high rate";
           }
           leaf policer-high-bytes {
             type int32;
             description "Number of loss priority high bytes";
           }
           leaf policer-high-frames {
             type int32;
             description "Number of loss priority high frames";
           }
           leaf policer-high-rate {
             type int32;
             description "Rate of loss priority high rate";
           }
           leaf policer-dropped-bytes {
             type int32;
             description "Number of dropped bytes";
           }
           leaf policer-dropped-frames {
             type int32;
             description "Number of dropped frames";
           }
           leaf policer-dropped-rate {
             type int32;
             description "Number of dropped rate";
           }
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container layer2-output-policer-statistics {
           leaf policer-low-bytes {
             type int32;
             description "Number of loss priority low bytes";
           }
           leaf policer-low-frames {
             type int32;
             description "Number of loss priority low frames";
           }
           leaf policer-low-rate {
             type int32;
             description "Rate of loss priority low pkts";
           }
           leaf policer-medium-high-bytes {
             type int32;
             description "Number of loss priority medium high bytes";
           }
           leaf policer-medium-high-frames {
             type int32;
             description "Number of loss priority medium high frames";
           }
           leaf policer-medium-high-rate {
             type int32;
             description "Rate of loss priority medium high rate";
           }
           leaf policer-high-bytes {
             type int32;
             description "Number of loss priority high bytes";
           }
           leaf policer-high-frames {
             type int32;
             description "Number of loss priority high frames";
           }
           leaf policer-high-rate {
             type int32;
             description "Rate of loss priority high rate";
           }
           leaf policer-dropped-bytes {
             type int32;
             description "Number of dropped bytes";
           }
           leaf policer-dropped-frames {
             type int32;
             description "Number of dropped frames";
           }
           leaf policer-dropped-rate {
             type int32;
             description "Number of dropped rate";
           }
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container atm-input-policer-statistics {
           leaf atm-policer-traffic-count-cells {
             type int32;
             description "Stats for counted ATM Cells";
           }
           leaf atm-policer-traffic-discard-cells {
             type int32;
             description "Stats for discarded ATM Cells";
           }
           leaf atm-policer-traffic-discard-tag-cells {
             type int32;
             description "Stats for discard-tag ATM Cells";
           }
         }
         container mac-policer-information {
           leaf mac-address {
             type jt:mac-addr;
           }
           leaf mac-entry-type {
             type string;
           }
           leaf receive-bytes {
             type int32;
           }
           leaf transmit-bytes {
             type int32;
           }
           leaf receive-frames {
             type int32;
           }
           leaf transmit-frames {
             type int32;
           }
           container ether-policer-list {
             list ether-policer-record {
               leaf policer-type {
                 type string;
               }
               leaf out-of-spec-frames {
                 type int32;
               }
               leaf out-of-spec-bytes {
                 type int32;
               }
             }
           }
         }
         container ppp-parameters {
           leaf lcp-restart-timer {
             type int32;
             description "LCP restart timer (milliseconds)";
           }
           leaf ncp-restart-timer {
             type int32;
             description "NCP restart timer (milliseconds)";
           }
           leaf termination-requests {
             type string;
             description "Whether PPP termination requests are sent";
           }
           leaf loopback-clear-timer {
             type int32;
             description "PPP loopback clear timer (seconds)";
           }
         }
       }
       container controller {
         leaf name {
           type string;
           description "Name of this item";
         }
         leaf admin-status {
           type string;
           description "Desired state of the interface";
         }
         leaf oper-status {
           type string;
           description "Current operational state of the interface";
         }
       }
       container interface-set {
         leaf name {
           type string;
           description "Name of this item";
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container interface-set-queue-information {
           container queue-counters {
             leaf queue-counters-error-message {
               type string;
               description "Queue statistics not available for this interface";
             }
             list queue {
               leaf queue-number {
                 type int32;
                 description "Queue number";
               }
               leaf queue-counters-queued-packets {
                 type uint64;
                 description "Queued packet count";
               }
               leaf queue-counters-trans-packets {
                 type uint64;
                 description "Total number of transmitted packets";
               }
               leaf queue-counters-total-drop-packets {
                 type uint64;
                 description "Number of total packets dropped at the queue";
               }
               leaf forwarding-class-name {
                 type string;
                 description "Forwarding class name associated with queue";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
           }
           container ingress-queue-counters {
             list queue {
               leaf queue-number {
                 type int32;
                 description "Queue number";
               }
               leaf forwarding-class-name {
                 type string;
                 description "Forwarding class name associated with queue";
               }
               leaf queue-counters-queued-packets {
                 type uint64;
                 description "Queued packet count";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets {
                 type uint64;
                 description "Total number of transmitted packets";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets {
                 type uint64;
                 description "Number of total packets dropped at the queue";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container queue-num-forwarding-class-name-map {
               leaf queue-number {
                 type int32;
                 description "Queue number";
               }
               leaf forwarding-class-name {
                 type string;
                 description "Forwarding class name associated with queue";
               }
             }
           }
         }
         leaf interface-set-index {
           type uint64;
           description "Class-of-service logical interface index";
         }
         leaf snmp-index {
           type int32;
           description "SNMP ifIndex for this interface";
         }
         list interface-set-member-list {
           leaf interface-set-member {
             type string;
           }
         }
         container aci-vlan-iflset-information {
           leaf agent-circuit-id {
             type string;
             description "Agent Circuit ID";
           }
           leaf agent-remote-id {
             type string;
             description "Agent Remote ID";
           }
         }
         container line-identity-iflset-information {
           leaf agent-circuit-id {
             type string;
             description "Agent Circuit ID";
           }
           leaf agent-remote-id {
             type string;
             description "Agent Remote ID";
           }
         }
         container pppoe-uifl-iflset-information {
           leaf dynamic-profile {
             type string;
             description "Dynamic Profile name";
           }
           leaf max-sessions {
             type int32;
             description "Maximum number of PPPoE sessions";
           }
           leaf max-sessions-vsa-ignore {
             type string;
             description "Ignore max-sessions VSA";
           }
         }
         list lag-targeting-summary {
           leaf targeting-intf-name {
             type string;
           }
           leaf targeting-intf-type {
             type string;
           }
           leaf targeting-intf-link-state {
             type string;
           }
         }
       }
     }
     container interface-filter-information {
       list physical-interface {
         leaf name {
           type string;
           description "Name of this item";
         }
         leaf admin-status {
           type string;
           description "Desired state of the interface";
         }
         leaf oper-status {
           type string;
           description "Current operational state of the interface";
         }
         leaf esi-source-bmac {
           type jt:mac-addr;
           description "Ethernet segment source B-MAC for this interface";
         }
         leaf sonet-payload-pointer-curptr {
           type string;
           description "Value of the SONET/SDH payload pointer, derived from the H1 and H2 overhead bytes";
         }
         leaf sonet-payload-pointer-ptrinc-count {
           type string;
           description "Number of times the value of the SONET/SDH payload pointer had positive justification";
         }
         leaf sonet-payload-pointer-ptrdec-count {
           type string;
           description "Number of times the value of the SONET/SDH payload pointer had negative justification";
         }
         leaf sonet-payload-pointer-newptr-ndf-count {
           type string;
           description "Number of times a new payload pointer was created with the New Data Found flag set";
         }
         leaf link-partner-status {
           type string;
           description "Auto-negotiation status of link partner";
         }
         container optics-properties {
           leaf wavelength {
             type string;
             description "Wavelength of optics in nanometers";
           }
           leaf frequency {
             type string;
             description "Frequency of optics in terahertz";
           }
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container voq-counters {
           leaf voq-counters-error-message {
             type string;
             description "VOQ statistics not available for this interface";
           }
           container voq {
             container fpc {
               leaf fpc-no {
                 type int32;
                 description "FPC number";
               }
               container pfe {
                 leaf-list pfe-no {
                   type int32;
                   description "PFE number";
                 }
                 leaf voq-counters-tail-drop-packets {
                   type int32;
                   description "Tail DROP packet count";
                 }
                 leaf voq-counters-tail-drop-packets-rate {
                   type int32;
                   description "Rate at which tail packets are dropped";
                 }
                 leaf voq-counters-tail-drop-bytes {
                   type int32;
                   description "Tail DROP bytes count";
                 }
                 leaf voq-counters-tail-drop-bytes-rate {
                   type int32;
                   description "Rate at which tail bytes are dropped";
                 }
                 leaf voq-counters-drop-packets {
                   type int32;
                   description "DROP packet count";
                 }
                 leaf voq-counters-drop-packets-rate {
                   type int32;
                   description "Rate at which packets are dropped";
                 }
                 leaf voq-counters-drop-bytes {
                   type int32;
                   description "DROP bytes count";
                 }
                 leaf voq-counters-drop-bytes-rate {
                   type int32;
                   description "Rate at which bytes are dropped";
                 }
               }
             }
             leaf queue-number {
               type int32;
               description "Queue number";
             }
             leaf forwarding-class-name {
               type string;
               description "Forwarding class name associated with queue";
             }
           }
         }
         container smart-sfp-av-titan-statistics {
           leaf smart-sfp-av-titan-error-message {
             type string;
             description "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           container smart-sfp-av-titan-defect-list {
             leaf sfp-tdm-defects {
               type string;
             }
             leaf sfp-system-defects {
               type string;
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container optics-bit-rate {
           leaf bit-rate {
             type string;
             description " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container active-alarms {
         }
         container active-defects {
         }
         container media-state-information {
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description "Optics laser status";
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         container ethernet-pcs-statistics {
           leaf bit-error-seconds {
             type int32;
             description "Bit error duration";
           }
           leaf errored-blocks-seconds {
             type int32;
             description "Errored blocks duration";
           }
         }
         container ethernet-fec-mode {
           leaf enabled_fec_mode {
             type string;
             description "Enabled FEC mode: <NONE/FEC74/FEC91/FEC108>";
           }
         }
         container ethernet-fec-statistics {
           leaf fec_ccw_count {
             type int32;
             description "FEC Corrected Error Count";
           }
           leaf fec_nccw_count {
             type int32;
             description "FEC Uncorrected Error Count";
           }
           leaf fec_ccw_error_rate {
             type int32;
             description "FEC Corrected Error Rate (errors/sec)";
           }
           leaf fec_nccw_error_rate {
             type int32;
             description "FEC Uncorrected Error Rate (errors/sec)";
           }
         }
         container ctle {
           leaf ctle_value {
             type int32;
             description "Ctle value";
           }
         }
         container pre-emphasis {
           leaf pre_emphasis_value {
             type int32;
             description "Pre-emphasis value";
           }
         }
         container differential-amplitude {
           leaf differential_amplitude_value {
             type int32;
             description "Differential-amplitude value";
           }
         }
         container ethernet-mac-statistics {
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container ethernet-prbs-mode {
           leaf prbs-mode {
             type string;
             description "PRBS Mode: <Enabled/Disabled>";
           }
         }
         container ethernet-prbs-statistics {
           leaf prbs-lane {
             type int32;
             description "PRBS Lane";
           }
           leaf prbs-state {
             type string;
             description "PRBS State";
           }
           leaf prbs-error-count {
             type int32;
             description "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           leaf fibrechannel-port-flow-control-mode {
             type string;
           }
           list fibrechannel-port-flow-control-credits {
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
         }
         container mac-database {
         }
         container dsl-information {
           container dsl-statistics {
             leaf interleaved-rx-cells {
               type int32;
               description "Interleaved receiver cells";
             }
             leaf fast-rx-cells {
               type int32;
               description "Fast receiver cells";
             }
             leaf interleaved-tx-cells {
               type int32;
               description "Interleaved transmitter cells";
             }
             leaf fast-tx-cells {
               type int32;
               description "Fast transmitter cells";
             }
           }
         }
         container vdsl-information {
         }
         container shdsl-information {
         }
         container efm-information {
           container efm-line-statistics {
             container active-alarms-efm {
             }
             container active-defects-efm {
             }
             container media-information {
               leaf media-type {
                 type string;
                 description "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description "Circuit Emulation counter information";
                 }
                 leaf ce-counter-packets {
                   type int32;
                   description "Circuit Emulation number of packets";
                 }
                 leaf ce-counter-bytes {
                   type int32;
                   description "Circuit Emulation number of bytes";
                 }
                 leaf ce-counter-count {
                   type int32;
                   description "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description "Number of feet";
               }
             }
             container shdsl-information {
             }
           }
         }
         container atm-information {
           container plcp-defects {
           }
           container atm-defects {
           }
         }
         container serial-information {
           leaf dce-loopback-override {
             type string;
           }
           container eia530-control-signal {
           }
         }
         container virtual-path-information {
           leaf cdvt {
             type int32;
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             leaf output-drops-bytes {
               type int32;
             }
           }
         }
         container cds1-information {
           list interface-tx-queue {
             leaf output-drops-bytes {
               type int32;
             }
           }
         }
         container nxds0-information {
           list interface-tx-queue {
             leaf output-drops-bytes {
               type int32;
             }
           }
         }
         list logical-interface {
           leaf name {
             type string;
             description "Name of this item";
           }
           leaf admin-status {
             type string;
             description "Desired state of the interface";
           }
           leaf oper-status {
             type string;
             description "Current operational state of the interface";
           }
           leaf vrfname {
             type string;
             description "Routing instance name";
           }
           leaf zonename {
             type string;
             description "Zone name";
           }
           leaf subunit {
             type int32;
             description "Subunit for this interface";
           }
           leaf dialer-time-to-disconnect {
             type string;
             description "Time for dialer to disconnect due to idle timeout";
           }
           leaf lcp-state {
             type string;
             description "State of the Line Control Protocol";
           }
           leaf chap-state {
             type string;
             description "State of the Challenge Handshake Authentication Protocol";
           }
           leaf pap-state {
             type string;
             description "State of the Password Authentication Protocol";
           }
           container pppoe-information {
             list pppoe-interface {
               leaf state {
                 type string;
                 description "State";
               }
               leaf session-id {
                 type string;
                 description "Session ID";
               }
               leaf ac-name-session {
                 type string;
                 description "Session AC name";
               }
               leaf remote-mac {
                 type string;
                 description "Remote MAC address";
               }
               leaf ac-name-config {
                 type string;
                 description "Configured AC name";
               }
               leaf service-name {
                 type string;
                 description "Service name";
               }
               leaf auto-reconnect {
                 type string;
                 description "Autoreconnect timeout";
               }
               leaf idle-timeout {
                 type string;
                 description "Idle timeout";
               }
               leaf underlying-interface-name {
                 type string;
                 description "Underlying interface name";
               }
               leaf underlying-interface-index {
                 type string;
                 description "Underlying interface index";
               }
               leaf padg-credits {
                 type int32;
                 description "PADG transmit credits";
               }
               leaf pppoe-credit-scale-factor {
                 type string;
                 description "Scaling factor";
               }
               leaf ignore-eol-tag {
                 type string;
                 description "Ignore End-of-List TAG";
               }
               leaf ppp-max-payload-tag {
                 type int32;
                 description "PPP-Max-Payload TAG";
               }
               leaf interface-name {
                 type string;
                 description "Class-of-service interface name";
               }
               leaf interface-index {
                 type uint32;
                 description "Class-of-service interface index";
               }
               leaf aci-iflset-name {
                 type string;
                 description "ACI Interface Set name";
               }
               leaf aci-iflset-index {
                 type string;
                 description "ACI Interface Set index";
               }
               leaf ifl-type {
                 type string;
                 description "Type";
               }
               leaf session-uptime {
                 type string;
                 description "Duration for which the session has been up";
               }
               leaf dynamic-profile {
                 type string;
                 description "Dynamic Profile name";
               }
               leaf pppoe-credits {
                 type string;
                 description "Forwarding credit balances";
               }
               leaf dynamic-interface-bandwidth {
                 type string;
                 description "Dynamic interface bandwidth";
               }
               leaf agent-circuit-id {
                 type string;
                 description "Agent Circuit ID";
               }
               leaf agent-remote-id {
                 type string;
                 description "Agent Remote ID";
               }
               leaf padm-motm {
                 type string;
                 description "PADM Message of the Moment tag";
               }
               leaf padm-hurl {
                 type string;
                 description "PADM HTTP URL tag";
               }
             }
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           container aci-vlan-information {
             leaf dynamic-profile {
               type string;
               description "Dynamic Profile name";
             }
           }
           container line-identity-information {
             leaf dynamic-profile {
               type string;
               description "Dynamic Profile name";
             }
             leaf circuit-id {
               type string;
               description "Aci vlan attribute";
             }
             leaf remote-id {
               type string;
               description "Aci vlan attribute";
             }
             leaf accept-no-ids {
               type string;
               description "Aci vlan attribute";
             }
           }
           container demux-information {
             container demux-interface {
               leaf demux-underlying-interface-name {
                 type string;
                 description "Underlying interface name";
               }
               leaf demux-underlying-interface-index {
                 type string;
                 description "Underlying interface index";
               }
               leaf demux-inet-prefix-type {
                 type string;
                 description "Prefix type";
               }
               leaf demux-inet-prefix-count {
                 type string;
                 description "IPv4 Prefix count";
               }
               leaf demux-inet-prefix {
                 type string;
                 description "IPv4 Prefix";
               }
               leaf demux-inet6-prefix-type {
                 type string;
                 description "Prefix type";
               }
               leaf demux-inet6-prefix-count {
                 type string;
                 description "IPv6 Prefix count";
               }
               leaf demux-inet6-prefix {
                 type string;
                 description "IPv6 Prefix";
               }
             }
           }
           container dual-ad-icl-color-information {
             container dual-ad-icl-color-info {
               leaf dual-ad-icl-color-type {
                 type uint32;
                 description "Dual-AD ICL Color Type";
               }
               leaf dual-ad-icl-color {
                 type uint32;
                 description "Dual-AD ICL Color";
               }
             }
           }
           container dialer-information {
             leaf dialer-time-to-disconnect {
               type string;
               description "Time for dialer to disconnect due to idle timeout";
             }
             container dialer-interface {
               leaf dialer-interface-name {
                 type string;
                 description "Interface name";
               }
               leaf dialer-interface-state {
                 type string;
                 description "Dialer interface state";
               }
               leaf pool-id {
                 type string;
                 description "Pool identifier";
               }
               leaf primary-interface {
                 type string;
                 description "Primary interface";
               }
               leaf activation-delay {
                 type string;
                 description "Activation delay";
               }
               leaf deactivation-delay {
                 type string;
                 description "Deactivation delay";
               }
               leaf activation-delay-elapsed {
                 type string;
                 description "Activation delay elapsed";
               }
               leaf deactivation-delay-elapsed {
                 type string;
                 description "Deactivation delay elapsed";
               }
               leaf call-idle-timeout {
                 type string;
                 description "Call idle timeout";
               }
               leaf initial-route-check {
                 type string;
                 description "Initial route check delay";
               }
               leaf redial-delay {
                 type string;
                 description "Delay before dialer dials out again (seconds)";
               }
               leaf callback-wait-period {
                 type string;
                 description "Delay before dialer attempts callback (seconds)";
               }
               leaf callback-wait-period-elapsed {
                 type string;
                 description "Number of seconds in callback wait period that have elapsed";
               }
               leaf load-threshold {
                 type string;
                 description "Load threshold that determines when interfaces are added to bundle";
               }
               leaf load-interval {
                 type string;
                 description "Interval over which average load is calculated";
               }
               container dialer-interface-flags {
                 leaf backup {
                   type empty;
                   description "Dialer backup";
                 }
                 leaf multilink {
                   type empty;
                   description "Dialer multilink";
                 }
                 leaf watchlist {
                   type empty;
                   description "Dialer watchlist";
                 }
                 leaf interesting-detected {
                   type empty;
                   description "Interesting packet detected";
                 }
               }
             }
           }
           container shared-interface-information {
             container shared-interface-logical-interface {
               leaf peer-interface-name {
                 type string;
                 description "Peer interface name";
               }
               leaf interface-shared-with {
                 type string;
                 description "Logical interface owner";
               }
               leaf rx-fe {
                 type string;
                 description "Rx tunnel token forwarding element";
               }
               leaf rx-nhid {
                 type string;
                 description "Rx tunnel token next hop index";
               }
               leaf tx-fe {
                 type string;
                 description "Tx tunnel token forwarding element";
               }
               leaf tx-nhid {
                 type string;
                 description "Tx tunnel token next hop index";
               }
             }
           }
           container mac-database {
           }
           container queue-counters {
             leaf queue-counters-error-message {
               type string;
               description "Queue statistics not available for this interface";
             }
             list queue {
               leaf queue-number {
                 type int32;
                 description "Queue number";
               }
               leaf queue-counters-queued-packets {
                 type uint64;
                 description "Queued packet count";
               }
               leaf queue-counters-trans-packets {
                 type uint64;
                 description "Total number of transmitted packets";
               }
               leaf queue-counters-total-drop-packets {
                 type uint64;
                 description "Number of total packets dropped at the queue";
               }
               leaf forwarding-class-name {
                 type string;
                 description "Forwarding class name associated with queue";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
           }
           container ingress-queue-counters {
             list queue {
               leaf queue-number {
                 type int32;
                 description "Queue number";
               }
               leaf forwarding-class-name {
                 type string;
                 description "Forwarding class name associated with queue";
               }
               leaf queue-counters-queued-packets {
                 type uint64;
                 description "Queued packet count";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets {
                 type uint64;
                 description "Total number of transmitted packets";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets {
                 type uint64;
                 description "Number of total packets dropped at the queue";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container queue-num-forwarding-class-name-map {
               leaf queue-number {
                 type int32;
                 description "Queue number";
               }
               leaf forwarding-class-name {
                 type string;
                 description "Forwarding class name associated with queue";
               }
             }
           }
           container forwarding-class-counters {
             leaf forwarding-class-counters-error-message {
               type string;
               description "Forwarding-class statistics not available for this interface";
             }
             container ipv4-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container multilink-bundle-options {
             leaf filler-packet-interval {
               type int32;
             }
           }
           container multilink-traffic-statistics {
             container bundle {
             }
             container class {
             }
             container multilink-detail-statistics {
               container bundle-detail {
               }
               container class-detail {
               }
             }
             container crtp {
               container crtp-sessions {
                 leaf input-frames {
                   type int32;
                 }
                 leaf output-frames {
                   type int32;
                 }
               }
               list crtp-statistics {
                 leaf name {
                   type string;
                   description "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             leaf multicast-statistics-header {
               type empty;
             }
             container ipv4-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             leaf input-bps {
               type int32;
             }
             leaf input-pps {
               type int32;
             }
             leaf input-drop-bps {
               type int32;
               description "Drop rate at ingress in bits per second ";
             }
             leaf input-drop-pps {
               type int32;
               description "Drop rate at ingress in packets per second ";
             }
             leaf input-bytes {
               type int32;
             }
             leaf input-packets {
               type int32;
             }
             leaf input-drop-bytes {
               type int32;
               description "Drop statistics at ingress in bytes";
             }
             leaf input-drop-packets {
               type int32;
               description "Drop statistics at ingress in packets";
             }
           }
           container transit-traffic-statistics {
           }
           container keepalive-statistics {
             leaf keepalive-lmi-descriptor {
               type string;
             }
             leaf keepalive-input-count {
               type int32;
             }
             leaf keepalive-input-time {
               type string;
             }
             leaf keepalive-output-count {
               type int32;
             }
             leaf keepalive-output-time {
               type string;
             }
           }
           container virtual-circuit-information {
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-cos-information {
               leaf vc-cos-mode {
                 type string;
                 description "Virtual circuit CoS scheduling mode";
               }
               list atm-cos-queue {
                 container atm-cos-queue-parameters {
                   leaf cos-forwarding-class-name {
                     type string;
                     description "Forwarding class name associated with queue";
                   }
                   leaf cos-queue-number {
                     type int32;
                     description "Queue number";
                   }
                   leaf scheduling-priority {
                     type string;
                     description "Scheduling priority";
                   }
                   leaf transmit-weight-cells {
                     type int32;
                     description "Weight to apply to scheduling as number of cells";
                   }
                   leaf transmit-weight-percent {
                     type int32;
                     description "Weight to apply to scheduling as fill percentage";
                   }
                   leaf epd-threshold {
                     type int32;
                     description "Early packet drop threshold";
                   }
                   leaf epd-threshold-plp0 {
                     type int32;
                     description "Early packet drop threshold for PLP 0";
                   }
                   leaf epd-threshold-plp1 {
                     type int32;
                     description "Early packet drop threshold for PLP 1";
                   }
                   container linear-red-drop-profile {
                     leaf queue-depth {
                       type uint32;
                       description "Instantaneous queue depth";
                     }
                     leaf low-red {
                       type int32;
                       description "Fill level percentage when linear RED is applied for low PLP";
                     }
                     leaf high-red {
                       type int32;
                       description "Fill level percentage when linear RED is applied for high PLP";
                     }
                     leaf max-low-red {
                       type int32;
                       description "Fill level percentage with 100% packet drop for low PLP";
                     }
                     leaf max-high-red {
                       type int32;
                       description "Fill level percentage with 100% packet drop for high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
           }
           list filter-information {
             leaf filter-family {
               type string;
               description "Protocol family of the filter";
             }
             leaf-list filter-input {
               type string;
               description "Name of the input filter";
             }
             leaf-list filter-output {
               type string;
               description "Name of the output filter";
             }
           }
           list address-family {
             leaf local-bias-information {
               type string;
             }
             leaf ft-iff-dest-port {
               type uint32;
               description "Destination UDP port to be used for this family";
             }
             container pppoe-underlying-information {
               list pppoe-underlying-interface {
                 leaf dynamic-profile {
                   type string;
                   description "Dynamic Profile name";
                 }
                 leaf service-name-table {
                   type string;
                   description "Name of Service Name Table";
                 }
                 leaf max-sessions {
                   type int32;
                   description "Maximum number of PPPoE sessions";
                 }
                 leaf max-sessions-vsa-ignore {
                   type string;
                   description "Ignore max-sessions VSA";
                 }
                 leaf duplicate-protection {
                   type string;
                   description "Duplicate protection mode";
                 }
                 leaf short-cycle-protection {
                   type string;
                   description "Short cycle protection mode";
                 }
                 leaf direct-connect {
                   type string;
                   description "Direct connect mode";
                 }
                 leaf ac-name {
                   type string;
                   description "Access Concentrator name";
                 }
                 leaf underlying-interface-name {
                   type string;
                   description "Underlying interface name";
                 }
                 leaf underlying-interface-index {
                   type string;
                   description "Underlying interface index";
                 }
                 leaf encapsulation-type-identifier {
                   type string;
                   description "Encapsulation type identifier";
                 }
                 leaf state {
                   type string;
                   description "State";
                 }
                 leaf active-sessions {
                   type int32;
                   description "Number of active PPPoE sessions";
                 }
                 leaf aci-autosensing {
                   type string;
                   description "ACI VLAN Autosensing mode";
                 }
                 leaf line-identity-autosensing {
                   type string;
                   description "Line Identity Autosensing mode";
                 }
               }
             }
             list interface-address {
             }
             container destination-class-statistics {
             }
             container source-class-statistics {
             }
           }
           list bridge-iff-properties {
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container media-information {
             leaf media-type {
               type string;
               description "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description "Circuit Emulation counter information";
               }
               leaf ce-counter-packets {
                 type int32;
                 description "Circuit Emulation number of packets";
               }
               leaf ce-counter-bytes {
                 type int32;
                 description "Circuit Emulation number of bytes";
               }
               leaf ce-counter-count {
                 type int32;
                 description "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description "Number of feet";
             }
           }
           list macsec-statistics {
             leaf interface-name {
               type string;
               description "Class-of-service interface name";
             }
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
             leaf ok-packets {
               type uint64;
               description "Macsec packets accepted";
             }
             leaf decrypted-bytes {
               type uint64;
               description "Macsec received bytes decrypted";
             }
             leaf decrypted-packets {
               type uint64;
               description "Macsec received packets decrypted";
             }
             leaf validated-packets {
               type uint64;
               description "Macsec received packets validated";
             }
             leaf validated-bytes {
               type uint64;
               description "Macsec received bytes validated";
             }
             leaf untagged-packets {
               type uint64;
               description "Macsec untagged packets";
             }
             leaf toolong-packets {
               type uint64;
               description "Macsec too long packets transmitted on a secure channel";
             }
             leaf control-packets {
               type uint64;
               description "Macsec control packets received on a secure channel";
             }
             leaf tagged-miss-packets {
               type uint64;
               description "Macsec tagged miss packets received on a secure channel";
             }
             leaf untagged-hit-packets {
               type uint64;
               description "Macsec untagged hit packets received on a secure channel";
             }
             leaf notag-packets {
               type uint64;
               description "Macsec no tag packets received on a secure channel";
             }
             leaf badtag-packets {
               type uint64;
               description "Macsec bad tag packets received on a secure channel";
             }
             leaf unknown-sci-packets {
               type uint64;
               description "Macsec unknown sci packets received on a secure channel";
             }
             leaf no-sci-packets {
               type uint64;
               description "Macsec no sci packets received on a secure channel";
             }
             leaf control-pass-packets {
               type uint64;
               description "Macsec allowed control packets received on a secure channel";
             }
             leaf uncontrol-pass-packets {
               type uint64;
               description "Macsec allowed uncontrol packets received on a secure channel";
             }
             leaf control-fail-packets {
               type uint64;
               description "Macsec dropped control packets received on a secure channel";
             }
             leaf uncontrol-fail-packets {
               type uint64;
               description "Macsec dropped uncontrol packets received on a secure channel";
             }
             leaf hit-dropped-packets {
               type uint64;
               description "Macsec hit dropped packets received on a security channel";
             }
             leaf notusing-sa-packets {
               type uint64;
               description "Macsec not using sa packets received on a security channel";
             }
             leaf unused-sa-packets {
               type uint64;
               description "Macsec unused sa packets received on a security channel";
             }
             leaf late-packets {
               type uint64;
               description "Macsec late packets dropped on a security channel";
             }
             leaf delayed-packets {
               type uint64;
               description "Macsec delayed packets accepted on a security channel";
             }
             leaf unchecked-packets {
               type uint64;
               description "Macsec unchecked packets accepted on a security channel";
             }
             leaf notvalid-packets {
               type uint64;
               description "Macsec not valid packets dropped on a security channel";
             }
             leaf invalid-packets {
               type uint64;
               description "Macsec invalid packets accepted on a security channel";
             }
             list secure-channel-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-association-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-channel-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list secure-association-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list macsec-error-information {
               list secure-channel-sent-errors {
                 leaf untagged-packets {
                   type uint64;
                   description "Macsec untagged packets";
                 }
                 leaf toolong-packets {
                   type uint64;
                   description "Macsec too long packets transmitted on a secure channel";
                 }
               }
               list secure-channel-received-errors {
                 leaf control-packets {
                   type uint64;
                   description "Macsec control packets received on a secure channel";
                 }
                 leaf tagged-miss-packets {
                   type uint64;
                   description "Macsec tagged miss packets received on a secure channel";
                 }
                 leaf untagged-hit-packets {
                   type uint64;
                   description "Macsec untagged hit packets received on a secure channel";
                 }
                 leaf untagged-packets {
                   type uint64;
                   description "Macsec untagged packets";
                 }
                 leaf notag-packets {
                   type uint64;
                   description "Macsec no tag packets received on a secure channel";
                 }
                 leaf badtag-packets {
                   type uint64;
                   description "Macsec bad tag packets received on a secure channel";
                 }
                 leaf unknown-sci-packets {
                   type uint64;
                   description "Macsec unknown sci packets received on a secure channel";
                 }
                 leaf no-sci-packets {
                   type uint64;
                   description "Macsec no sci packets received on a secure channel";
                 }
                 leaf control-pass-packets {
                   type uint64;
                   description "Macsec allowed control packets received on a secure channel";
                 }
                 leaf control-fail-packets {
                   type uint64;
                   description "Macsec dropped control packets received on a secure channel";
                 }
                 leaf uncontrol-pass-packets {
                   type uint64;
                   description "Macsec allowed uncontrol packets received on a secure channel";
                 }
                 leaf uncontrol-fail-packets {
                   type uint64;
                   description "Macsec dropped uncontrol packets received on a secure channel";
                 }
               }
               list secure-channel-received-extended {
                 leaf hit-dropped-packets {
                   type uint64;
                   description "Macsec hit dropped packets received on a security channel";
                 }
                 leaf invalid-packets {
                   type uint64;
                   description "Macsec invalid packets accepted on a security channel";
                 }
                 leaf late-packets {
                   type uint64;
                   description "Macsec late packets dropped on a security channel";
                 }
                 leaf delayed-packets {
                   type uint64;
                   description "Macsec delayed packets accepted on a security channel";
                 }
                 leaf unchecked-packets {
                   type uint64;
                   description "Macsec unchecked packets accepted on a security channel";
                 }
                 leaf notvalid-packets {
                   type uint64;
                   description "Macsec not valid packets dropped on a security channel";
                 }
                 leaf notusing-sa-packets {
                   type uint64;
                   description "Macsec not using sa packets received on a security channel";
                 }
                 leaf unused-sa-packets {
                   type uint64;
                   description "Macsec unused sa packets received on a security channel";
                 }
                 leaf untagged-hit-packets {
                   type uint64;
                   description "Macsec untagged hit packets received on a secure channel";
                 }
               }
             }
           }
           container lag-traffic-statistics {
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             list if-distribution-list-information {
             }
           }
           container layer2-input-policer-statistics {
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container layer2-output-policer-statistics {
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container mac-policer-information {
             container ether-policer-list {
             }
           }
         }
         container active-alarms-otn {
         }
         container active-defects-otn {
         }
         container active-alarms-optics {
         }
         container active-defects-optics {
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
         }
         container links {
           list link-entry {
             leaf sonet-payload-pointer-curptr {
               type string;
               description "Value of the SONET/SDH payload pointer, derived from the H1 and H2 overhead bytes";
             }
             leaf sonet-payload-pointer-ptrinc-count {
               type string;
               description "Number of times the value of the SONET/SDH payload pointer had positive justification";
             }
             leaf sonet-payload-pointer-ptrdec-count {
               type string;
               description "Number of times the value of the SONET/SDH payload pointer had negative justification";
             }
             leaf sonet-payload-pointer-newptr-ndf-count {
               type string;
               description "Number of times a new payload pointer was created with the New Data Found flag set";
             }
             leaf sonet-rx-overhead {
               type string;
             }
             leaf sonet-tx-overhead {
               type string;
             }
             leaf sonet-rx-path-trace {
               type string;
               description "Received SONET path trace";
             }
             leaf sonet-tx-path-trace {
               type string;
               description "Transmitted SONET path trace";
             }
             container active-alarms {
             }
             container active-defects {
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               leaf optic-diagnostics-not-available {
                 type string;
                 description "Optical diagnostics not supported by this transceiver";
               }
               leaf laser-bias-current-not-available {
                 type string;
                 description "Laser bias current measurement not available";
               }
               leaf soa-bias-current-not-available {
                 type string;
                 description "SOA bias current measurement not available";
               }
               leaf laser-tx-power-not-available {
                 type string;
                 description "Laser output power measurement not available";
               }
               leaf module-temperature-not-available {
                 type string;
                 description "Module temperature measurement not available";
               }
               leaf tx-module-temperature-not-available {
                 type string;
                 description "Tx module temperature measurement not available";
               }
               leaf rx-module-temperature-not-available {
                 type string;
                 description "Rx module temperature measurement not available";
               }
               leaf laser-rx-power-not-available {
                 type string;
                 description "Laser receiver optical power measurement not available";
               }
               leaf laser-tx-power-high-alarm-threshold-not-available {
                 type string;
                 description "Laser output power high alarm threshold not available";
               }
               leaf laser-tx-power-low-alarm-threshold-not-available {
                 type string;
                 description "Laser output power low alarm threshold not available";
               }
               leaf laser-tx-power-high-warning-threshold-not-available {
                 type string;
                 description "Laser output power high warning threshold not available";
               }
               leaf laser-tx-power-low-warning-threshold-not-available {
                 type string;
                 description "Laser output power low warning threshold not available";
               }
               leaf laser-bias-current {
                 type string;
                 description "Laser bias current (milliamperes)";
               }
               leaf soa-bias-current {
                 type string;
                 description "SOA bias current (milliamperes)";
               }
               leaf laser-output-power {
                 type string;
                 description "Laser output power (milliwatts)";
               }
               leaf laser-output-power-dbm {
                 type string;
                 description "Laser output power (dBm)";
               }
               leaf module-temperature {
                 type string;
                 description "Module temperature";
               }
               leaf tx-module-temperature {
                 type string;
                 description "Tx module temperature";
               }
               leaf rx-module-temperature {
                 type string;
                 description "Rx module temperature";
               }
               leaf module-voltage {
                 type string;
                 description "Module voltage";
               }
               leaf corrected-error-ratio {
                 type string;
                 description "Corrected error ratio";
               }
               leaf uncorrected-words-ratio {
                 type string;
                 description "Uncorrected words ratio";
               }
               leaf tx-module-voltage {
                 type string;
                 description "Tx module voltage";
               }
               leaf rx-module-voltage {
                 type string;
                 description "Rx module voltage";
               }
               leaf rx-signal-avg-optical-power {
                 type string;
                 description "Receiver signal average power (milliwatts)";
               }
               leaf rx-signal-avg-optical-power-dbm {
                 type string;
                 description "Receiver signal average power (dBm)";
               }
               leaf laser-rx-optical-power {
                 type string;
                 description "Laser receiver optical power (milliwatts)";
               }
               leaf laser-rx-optical-power-dbm {
                 type string;
                 description "Laser receiver optical power (dBm)";
               }
               leaf wavelength-channel {
                 type string;
                 description "Wavelength channel number set";
               }
               leaf wavelength-setpoint {
                 type string;
                 description "Wavelength point set";
               }
               leaf tx-dither {
                 type string;
                 description "Tx dither status";
               }
               leaf frequency-error {
                 type string;
                 description "Frequency error value";
               }
               leaf wavelength-error {
                 type string;
                 description "Wavelength error value";
               }
               leaf laser-bias-current-high-alarm {
                 type string;
                 description "Laser bias current high alarm";
               }
               leaf laser-bias-current-low-alarm {
                 type string;
                 description "Laser bias current low alarm";
               }
               leaf laser-bias-current-high-warn {
                 type string;
                 description "Laser bias current high warning";
               }
               leaf laser-bias-current-low-warn {
                 type string;
                 description "Laser bias current low warning";
               }
               leaf soa-bias-current-high-alarm {
                 type string;
                 description "SOA bias current high alarm";
               }
               leaf soa-bias-current-low-alarm {
                 type string;
                 description "SOA bias current low alarm";
               }
               leaf soa-bias-current-high-warn {
                 type string;
                 description "SOA bias current high warning";
               }
               leaf soa-bias-current-low-warn {
                 type string;
                 description "SOA bias current low warning";
               }
               leaf laser-tx-power-high-alarm {
                 type string;
                 description "Laser output power high alarm";
               }
               leaf laser-tx-power-low-alarm {
                 type string;
                 description "Laser output power low alarm";
               }
               leaf laser-tx-power-high-warn {
                 type string;
                 description "Laser output power high warning";
               }
               leaf laser-tx-power-low-warn {
                 type string;
                 description "Laser output power low warning";
               }
               leaf tx-power-high-alarm {
                 type string;
                 description "Tx power high alarm";
               }
               leaf tx-power-low-alarm {
                 type string;
                 description "Tx power low alarm";
               }
               leaf tx-power-high-warn {
                 type string;
                 description "Tx power high warning";
               }
               leaf tx-power-low-warn {
                 type string;
                 description "Tx power low warning";
               }
               leaf module-temperature-high-alarm {
                 type string;
                 description "Module temperature high alarm";
               }
               leaf module-temperature-low-alarm {
                 type string;
                 description "Module temperature low alarm";
               }
               leaf module-temperature-high-warn {
                 type string;
                 description "Module temperature high warning";
               }
               leaf module-temperature-low-warn {
                 type string;
                 description "Module temperature low warning";
               }
               leaf tx-module-temperature-high-alarm {
                 type string;
                 description "Tx module temperature high alarm";
               }
               leaf tx-module-temperature-low-alarm {
                 type string;
                 description "Tx module temperature low alarm";
               }
               leaf rx-module-temperature-high-alarm {
                 type string;
                 description "Rx module temperature high alarm";
               }
               leaf rx-module-temperature-low-alarm {
                 type string;
                 description "Rx module temperature low alarm";
               }
               leaf module-voltage-high-alarm {
                 type string;
                 description "Module voltage high alarm";
               }
               leaf module-voltage-low-alarm {
                 type string;
                 description "Module voltage low alarm";
               }
               leaf module-voltage-high-warn {
                 type string;
                 description "Module voltage high warning";
               }
               leaf module-voltage-low-warn {
                 type string;
                 description "Module voltage low warning";
               }
               leaf tx-module-voltage-high-alarm {
                 type string;
                 description "Tx module voltage high alarm";
               }
               leaf tx-module-voltage-low-alarm {
                 type string;
                 description "Tx module voltage low alarm";
               }
               leaf rx-module-voltage-high-alarm {
                 type string;
                 description "Rx module voltage high alarm";
               }
               leaf rx-module-voltage-low-alarm {
                 type string;
                 description "Rx module voltage low alarm";
               }
               leaf laser-rx-power-high-alarm {
                 type string;
                 description "Laser receiver power high alarm";
               }
               leaf laser-rx-power-low-alarm {
                 type string;
                 description "Laser receiver power low alarm";
               }
               leaf laser-rx-power-high-warn {
                 type string;
                 description "Laser receiver power high warning";
               }
               leaf laser-rx-power-low-warn {
                 type string;
                 description "Laser receiver power low warning";
               }
               leaf rx-power-high-alarm {
                 type string;
                 description "Receiver power high alarm";
               }
               leaf rx-power-low-alarm {
                 type string;
                 description "Receiver power low alarm";
               }
               leaf rx-power-high-warn {
                 type string;
                 description "Receiver power high warning";
               }
               leaf rx-power-low-warn {
                 type string;
                 description "Receiver power low warning";
               }
               leaf laser-end-of-life-alarm {
                 type string;
                 description "Laser end-of-life alarm";
               }
               leaf laser-wavelength-alarm {
                 type string;
                 description "Laser wavelength alarm";
               }
               leaf laser-bias-current-alarm {
                 type string;
                 description "Laser bias current alarm";
               }
               leaf module-temperature-alarm {
                 type string;
                 description "Module temperature alarm";
               }
               leaf laser-power-alarm {
                 type string;
                 description "Laser power alarm";
               }
               leaf modulator-temperature-alarm {
                 type string;
                 description "Modulator temperature alarm";
               }
               leaf modulator-bias-alarm {
                 type string;
                 description "Modulator bias alarm";
               }
               leaf module-not-ready-alarm {
                 type string;
                 description "Module not ready alarm";
               }
               leaf module-power-down-alarm {
                 type string;
                 description "Module power down alarm";
               }
               leaf module-not-init-done-alarm {
                 type string;
                 description "Module initialization not done alarm";
               }
               leaf module-not-high-power-on-alarm {
                 type string;
                 description "Module not high powered on alarm";
               }
               leaf module-fault-alarm {
                 type string;
                 description "Module in fault state alarm";
               }
               leaf pld-flash-init-fault-alarm {
                 type string;
                 description "PLD or Flash initialization fault alarm";
               }
               leaf power-supply-fault-alarm {
                 type string;
                 description "Power supply fault alarm";
               }
               leaf checksum-fault-alarm {
                 type string;
                 description "Checksum fault alarm";
               }
               leaf apd-supply-fault-alarm {
                 type string;
                 description "APD supply fault alarm";
               }
               leaf tec-fault-alarm {
                 type string;
                 description "TEC fault alarm";
               }
               leaf wavelength-unlocked-alarm {
                 type string;
                 description "Wavelength unlocked alarm";
               }
               leaf tx-tune-alarm {
                 type string;
                 description "Tx tune alarm";
               }
               leaf tx-mux-fifo-error-alarm {
                 type string;
                 description "Tx multiplexer fifo error alarm";
               }
               leaf tx-loss-of-pll-alarm {
                 type string;
                 description "Tx loss of PLL alarm";
               }
               leaf tx-data-not-ready-alarm {
                 type string;
                 description "Tx data not ready alarm";
               }
               leaf tx-not-ready-alarm {
                 type string;
                 description "Tx not ready alarm";
               }
               leaf tx-laser-fault-alarm {
                 type string;
                 description "Tx laser fault alarm";
               }
               leaf tx-laser-disabled-alarm {
                 type string;
                 description "Tx laser disabled alarm";
               }
               leaf tx-loss-of-signal-functionality-alarm {
                 type string;
                 description "Tx loss of signal functionality alarm";
               }
               leaf tx-cdr-loss-of-lock-alarm {
                 type string;
                 description "Tx CDR loss of lock alarm";
               }
               leaf rx-loss-avg-opt-power-alarm {
                 type string;
                 description "Receiver loss of average optical power alarm";
               }
               leaf rx-loss-ac-power-alarm {
                 type string;
                 description "Receiver loss of AC power alarm";
               }
               leaf rx-loss-of-pll-alarm {
                 type string;
                 description "Receiver loss of PLL alarm";
               }
               leaf rx-not-ready-alarm {
                 type string;
                 description "Receiver not ready alarm";
               }
               leaf rx-loss-of-signal-alarm {
                 type string;
                 description "Receiver loss of signal alarm";
               }
               leaf rx-cdr-loss-of-lock-alarm {
                 type string;
                 description "Receiver CDR loss of lock alarm";
               }
               leaf laser-bias-current-high-alarm-threshold {
                 type string;
                 description "Laser bias current high alarm threshold (milliamperes)";
               }
               leaf laser-bias-current-low-alarm-threshold {
                 type string;
                 description "Laser bias current low alarm threshold (milliamperes)";
               }
               leaf laser-bias-current-high-warn-threshold {
                 type string;
                 description "Laser bias current high warning threshold (milliamperes)";
               }
               leaf laser-bias-current-low-warn-threshold {
                 type string;
                 description "Laser bias current low warning threshold (milliamperes)";
               }
               leaf soa-bias-current-high-alarm-threshold {
                 type string;
                 description "SOA bias current high alarm threshold (milliamperes)";
               }
               leaf soa-bias-current-low-alarm-threshold {
                 type string;
                 description "SOA bias current low alarm threshold (milliamperes)";
               }
               leaf soa-bias-current-high-warn-threshold {
                 type string;
                 description "SOA bias current high warning threshold (milliamperes)";
               }
               leaf soa-bias-current-low-warn-threshold {
                 type string;
                 description "SOA bias current low warning threshold (milliamperes)";
               }
               leaf laser-tx-power-high-alarm-threshold {
                 type string;
                 description "Laser transmitter power high alarm threshold (milliwatts)";
               }
               leaf laser-tx-power-high-alarm-threshold-dbm {
                 type string;
                 description "Laser transmitter power high alarm threshold (dBm)";
               }
               leaf laser-tx-power-low-alarm-threshold {
                 type string;
                 description "Laser transmitter power low alarm threshold (milliwatts)";
               }
               leaf laser-tx-power-low-alarm-threshold-dbm {
                 type string;
                 description "Laser transmitter power low alarm threshold (dBm)";
               }
               leaf laser-tx-power-high-warn-threshold {
                 type string;
                 description "Laser transmitter power high warning threshold (milliwatts)";
               }
               leaf laser-tx-power-high-warn-threshold-dbm {
                 type string;
                 description "Laser transmitter power high warning threshold (dBm)";
               }
               leaf laser-tx-power-low-warn-threshold {
                 type string;
                 description "Laser transmitter power low warning threshold (milliwatts)";
               }
               leaf laser-tx-power-low-warn-threshold-dbm {
                 type string;
                 description "Laser transmitter power low warning threshold (dBm)";
               }
               leaf module-temperature-high-alarm-threshold {
                 type string;
                 description "Module temperature high alarm threshold";
               }
               leaf module-temperature-low-alarm-threshold {
                 type string;
                 description "Module temperature low alarm threshold";
               }
               leaf module-temperature-high-warn-threshold {
                 type string;
                 description "Module temperature high warning threshold";
               }
               leaf module-temperature-low-warn-threshold {
                 type string;
                 description "Module temperature low warning threshold";
               }
               leaf laser-temperature-high-alarm-threshold {
                 type string;
                 description "Laser temperature high alarm threshold";
               }
               leaf laser-temperature-low-alarm-threshold {
                 type string;
                 description "Laser temperature low alarm threshold";
               }
               leaf laser-temperature-high-warn-threshold {
                 type string;
                 description "Laser temperature high warning threshold";
               }
               leaf laser-temperature-low-warn-threshold {
                 type string;
                 description "Laser temperature low warning threshold";
               }
               leaf module-voltage-high-alarm-threshold {
                 type string;
                 description "Module voltage high alarm threshold (volts)";
               }
               leaf module-voltage-low-alarm-threshold {
                 type string;
                 description "Module voltage low alarm threshold (volts)";
               }
               leaf module-voltage-high-warn-threshold {
                 type string;
                 description "Module voltage high warning threshold (volts)";
               }
               leaf module-voltage-low-warn-threshold {
                 type string;
                 description "Module voltage low warning threshold (volts)";
               }
               leaf laser-rx-power-high-alarm-threshold {
                 type string;
                 description "Laser receiver power high alarm (milliwatts)";
               }
               leaf laser-rx-power-high-alarm-threshold-dbm {
                 type string;
                 description "Laser receiver power high alarm (dBm)";
               }
               leaf laser-rx-power-low-alarm-threshold {
                 type string;
                 description "Laser receiver power low alarm (milliwatts)";
               }
               leaf laser-rx-power-low-alarm-threshold-dbm {
                 type string;
                 description "Laser receiver power low alarm (dBm)";
               }
               leaf laser-rx-power-high-warn-threshold {
                 type string;
                 description "Laser receiver power high warning (milliwatts)";
               }
               leaf laser-rx-power-high-warn-threshold-dbm {
                 type string;
                 description "Laser receiver power high warning (dBm)";
               }
               leaf laser-rx-power-low-warn-threshold {
                 type string;
                 description "Laser receiver power low warning (milliwatts)";
               }
               leaf laser-rx-power-low-warn-threshold-dbm {
                 type string;
                 description "Laser receiver power low warning (dBm)";
               }
               leaf rx-power-high-alarm-threshold {
                 type string;
                 description "Receiver power high alarm (milliwatts)";
               }
               leaf rx-power-high-alarm-threshold-dbm {
                 type string;
                 description "Receiver power high alarm (dBm)";
               }
               leaf rx-power-low-alarm-threshold {
                 type string;
                 description "Receiver power low alarm (milliwatts)";
               }
               leaf rx-power-low-alarm-threshold-dbm {
                 type string;
                 description "Receiver power low alarm (dBm)";
               }
               leaf rx-power-high-warning-threshold {
                 type string;
                 description "Receiver power high warning (milliwatts)";
               }
               leaf rx-power-high-warning-threshold-dbm {
                 type string;
                 description "Receiver power high warning (dBm)";
               }
               leaf rx-power-low-warning-threshold {
                 type string;
                 description "Receiver power low warning (milliwatts)";
               }
               leaf rx-power-low-warning-threshold-dbm {
                 type string;
                 description "Receiver power low warning (dBm)";
               }
               leaf los-alarm-threshold {
                 type string;
                 description "LOS alarm threshold (milliwatts)";
               }
               leaf los-alarm-threshold-dbm {
                 type string;
                 description "LOS alarm threshold (dBm)";
               }
               leaf los-warning-threshold {
                 type string;
                 description "LOS warning threshold (milliwatts)";
               }
               leaf los-warning-threshold-dbm {
                 type string;
                 description "LOS warning threshold (dBm)";
               }
               leaf dsp-module-state {
                 type string;
                 description "DSP module state";
               }
               leaf output-power {
                 type string;
                 description "Output power (milliwatts)";
               }
               leaf output-power-dbm {
                 type string;
                 description "Output power (dBm)";
               }
               leaf input-power {
                 type string;
                 description "Input power (milliwatts)";
               }
               leaf input-power-dbm {
                 type string;
                 description "Input power (dBm)";
               }
               leaf per-wave-rx-optical-power {
                 type string;
                 description "Per-wavelength receiver optical power (milliwatts)";
               }
               leaf per-wave-rx-optical-power-dbm {
                 type string;
                 description "Per-wavelength receiver optical power (dBm)";
               }
               leaf lane-laser-frequency-error {
                 type string;
                 description "Lane laser frequency error (MHz)";
               }
               leaf tec-current {
                 type string;
                 description "Tec current";
               }
               leaf residual-isi {
                 type string;
                 description "Residual ISI";
               }
               container optics-diagnostics-ot {
                 leaf module-temp-fault {
                   type string;
                   description "Module temperature fault";
                 }
                 leaf specific-hw-fault {
                   type string;
                   description "Specific HW fault";
                 }
                 leaf internal-power-fault {
                   type string;
                   description "Internal power fault";
                 }
                 leaf post-therm-fault {
                   type string;
                   description "Power thermal fault";
                 }
                 leaf post-fault {
                   type string;
                   description "Post fault";
                 }
                 leaf command-error {
                   type string;
                   description "Command error";
                 }
                 leaf rx-pll-lock {
                   type string;
                   description "RX PLL lock";
                 }
                 leaf network-lane-los {
                   type string;
                   description "Network Lane LOS";
                 }
                 leaf network-lane-lof {
                   type string;
                   description "Network Lane LOF";
                 }
                 leaf network-lane-oof {
                   type string;
                   description "Network Lane OOF";
                 }
                 leaf network-lane-lom {
                   type string;
                   description "Network Lane LOM";
                 }
                 leaf network-lane-oom {
                   type string;
                   description "Network Lane OOM";
                 }
                 leaf network-lane-otu-bdi {
                   type string;
                   description "Network Lane OTU BDI";
                 }
                 leaf lane-rx-fifo-error {
                   type string;
                   description "Lane RX FIFO error";
                 }
                 leaf tx-reference-clock-fault {
                   type string;
                   description "TX reference clock fault";
                 }
                 leaf rx-modem-sync-fault {
                   type string;
                   description "Rx modem sync fault";
                 }
                 leaf rx-modem-loss-of-lock {
                   type string;
                   description "RX modem loss of lock";
                 }
                 leaf rx-loss-of-alignment {
                   type string;
                   description "RX loss of alignment";
                 }
                 leaf rx-out-of-alignment {
                   type string;
                   description "RX out of alignment";
                 }
                 leaf rx-timing-fault {
                   type string;
                   description "Rx timing fault";
                 }
                 leaf link-msg-data-available {
                   type string;
                   description "Link msg data available";
                 }
                 leaf modulator-bias-control-loop-fail {
                   type string;
                   description "Modulator Bias Control Loop Fail";
                 }
                 leaf itla-fault {
                   type string;
                   description "ITLA fault";
                 }
                 leaf dac-calib-fault {
                   type string;
                   description "DAC calib fault";
                 }
                 leaf adc-calib-fault {
                   type string;
                   description "ADC calib fault";
                 }
                 leaf prom-fault {
                   type string;
                   description "PROM fault";
                 }
                 leaf tx-mod-bias-voa-ctrl-loop-high-alarm {
                   type string;
                   description "TX mod bias VOA ctrl loop high alarm";
                 }
                 leaf tx-mod-bias-voa-ctrl-loop-low-alarm {
                   type string;
                   description "TX mod bias VOA ctrl loop low alarm";
                 }
                 leaf rx-phase-control-loop-high-alarm {
                   type string;
                   description "RX phase control loop high alarm";
                 }
                 leaf rx-phase-control-loop-low-alarm {
                   type string;
                   description "RX phase control loop low alarm";
                 }
                 leaf rx-phase-control-loop-high-warning {
                   type string;
                   description "RX phase control loop high warning";
                 }
                 leaf rx-phase-control-loop-low-warning {
                   type string;
                   description "RX phase control loop low warning";
                 }
                 leaf oa-pump-bias-current-high-alarm {
                   type string;
                   description "OA pump bias current high alarm";
                 }
                 leaf oa-pump-bias-current-low-alarm {
                   type string;
                   description "OA pump bias current low alarm";
                 }
                 leaf oa-pump-bias-current-high-warning {
                   type string;
                   description "OA pump bias current high warning";
                 }
                 leaf oa-pump-bias-current-low-warning {
                   type string;
                   description "OA pump bias current low warning";
                 }
                 leaf tx-jitter-pll-lol-input-nw-lane {
                   type string;
                   description "Tx jitter PLL LOL i/p nw lane";
                 }
                 leaf tx-out-of-alignment {
                   type string;
                   description "TX out of alignment";
                 }
                 leaf tx-cmu-lock-fault {
                   type string;
                   description "Tx CMU lock fault";
                 }
                 leaf adc-signal-below-threshold {
                   type string;
                   description "ADC signal below threshold";
                 }
                 leaf tx-output-power-adjustment-fault {
                   type string;
                   description "Tx output power adjustment fault";
                 }
                 leaf tx-output-mod-converge-fault {
                   type string;
                   description "TX output mod converge fault";
                 }
                 leaf tx-laser-ready-fault {
                   type string;
                   description "Tx laser ready fault";
                 }
                 leaf tx-laser-ready-off-fault {
                   type string;
                   description "Tx laser ready off fault";
                 }
                 leaf tx-asic-ready-fault {
                   type string;
                   description "Tx asic ready fault";
                 }
                 leaf tx-initialization-fault {
                   type string;
                   description "Tx initialization fault";
                 }
                 leaf rx-demodulator-lock-fault {
                   type string;
                   description "Rx demodulator lock fault";
                 }
                 leaf rx-dispersion-lock-fault {
                   type string;
                   description "Rx dispersion lock fault";
                 }
                 leaf rx-adc-output-fault {
                   type string;
                   description "Rx ADC output fault";
                 }
                 leaf rx-optical-input-fault {
                   type string;
                   description "Rx optical input fault";
                 }
                 leaf rx-asic-ready-fault {
                   type string;
                   description "Rx asic ready fault";
                 }
                 leaf rx-initialization-fault {
                   type string;
                   description "Rx initialization fault";
                 }
                 leaf tx-mod-bias-high-alarm {
                   type string;
                   description "TX modulator bias high alarm";
                 }
                 leaf tx-mod-bias-low-alarm {
                   type string;
                   description "TX modulator bias low alarm";
                 }
                 leaf tx-mod-bias-high-warning {
                   type string;
                   description "TX modulator bias high warning";
                 }
                 leaf tx-mod-bias-low-warning {
                   type string;
                   description "TX modulator bias low warning";
                 }
                 leaf rx-pwr-high-alarm {
                   type string;
                   description "RX power high alarm";
                 }
                 leaf rx-pwr-low-alarm {
                   type string;
                   description "RX power low alarm";
                 }
                 leaf rx-pwr-high-warn {
                   type string;
                   description "RX power high warning";
                 }
                 leaf rx-pwr-low-warn {
                   type string;
                   description "RX power low warning";
                 }
                 leaf tx-laser-power-high-alarm {
                   type string;
                   description "TX laser power high alarm";
                 }
                 leaf tx-laser-power-low-alarm {
                   type string;
                   description "TX laser power low alarm";
                 }
                 leaf tx-laser-power-high-warn {
                   type string;
                   description "TX laser power high warning";
                 }
                 leaf tx-laser-power-low-warn {
                   type string;
                   description "TX laser power low warning";
                 }
                 leaf tx-bias-high-alarm {
                   type string;
                   description "TX laser current high alarm";
                 }
                 leaf tx-bias-low-alarm {
                   type string;
                   description "TX laser current low alarm";
                 }
                 leaf tx-bias-high-warn {
                   type string;
                   description "TX laser current high warning";
                 }
                 leaf tx-bias-low-warn {
                   type string;
                   description "TX laser current low warning";
                 }
                 leaf tx-laser-temp-high-alarm {
                   type string;
                   description "TX laser temperature high alarm";
                 }
                 leaf tx-laser-temp-low-alarm {
                   type string;
                   description "TX laser temperature low alarm";
                 }
                 leaf tx-laser-temp-high-warn {
                   type string;
                   description "TX laser temperature high warning";
                 }
                 leaf tx-laser-temp-low-warn {
                   type string;
                   description "TX laser temperature low warning";
                 }
               }
             }
             list optics-diagnostics-vendor-extension {
               leaf optics-vendor-part-number {
                 type string;
                 description "Optics component vendor part number";
               }
               leaf optics-vendor-material-number {
                 type string;
                 description "Optic component vendor material number";
               }
             }
           }
         }
         container peer-configuration-status {
           leaf peer-nonmatching-dlci {
             type int32;
             description "DCE end DLCIs that does not match the DTE";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description "Drop statistics due to stp state at ingress in bytes";
           }
           leaf stp-output-bytes-dropped {
             type int32;
             description "Drop statistics due to stp state at egress in bytes";
           }
           leaf stp-input-packets-dropped {
             type int32;
             description "Drop statistics due to stp state at ingress in packets";
           }
           leaf stp-output-packets-dropped {
             type int32;
             description "Drop statistics due to stp state at egress in packets";
           }
         }
         container af-fe-info {
         }
         container af-fe-q-pkts {
         }
         container af-fe-q-bytes {
         }
         container chassis-queue-counters {
           container interface-chassis-cos-summary {
             leaf intf-cos-chassis-num-queues-supported {
               type int32;
               description "Number of Packet Forwarding Engine chassis queues the interface supports";
             }
             leaf intf-cos-chassis-num-queues-in-use {
               type int32;
               description "Number of Packet Forwarding Engine chassis queues in use on the interface";
             }
           }
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-group-information {
         }
         container ima-link-information {
         }
         container ethernet-mac-pfc-statistics {
           leaf mac-pfc-dot1p {
             type int32;
           }
           leaf input-mac-pfc-frames {
             type int32;
           }
           leaf output-mac-pfc-frames {
             type int32;
           }
         }
         container cos-information {
           list cos-stream-information {
           }
           container cos-forwarding-class-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-forwarding-class-map-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-classifier-information {
             list classifier {
               leaf classifier-name {
                 type string;
                 description "Class-of-service classifier name";
               }
               leaf code-point-type {
                 type string;
                 description "Class-of-service code point type";
               }
               leaf table-index {
                 type uint32;
                 description "Table index";
               }
               container classifier-map {
                 list classifier-map-item {
                   leaf code-point {
                     type string;
                     description "Class-of-service code point alias name or bits";
                   }
                   leaf fc-name {
                     type string;
                     description "Class-of-service forwarding class name";
                   }
                   leaf loss-priority {
                     type string;
                     description "Class-of-service loss priority";
                   }
                   leaf cntag-present {
                     type string;
                     description "Class-of-service cntag present";
                   }
                 }
               }
             }
           }
           container cos-loss-priority-map-information {
             list loss-priority-map {
               leaf loss-priority-map-name {
                 type string;
                 description "Name of class-of-service loss priority map";
               }
               leaf code-point-type {
                 type string;
                 description "Class-of-service code point type";
               }
               leaf table-index {
                 type uint32;
                 description "Table index";
               }
               list loss-priority-map-table {
                 list loss-priority-map-item {
                   leaf code-point {
                     type string;
                     description "Class-of-service code point alias name or bits";
                   }
                   leaf loss-priority {
                     type string;
                     description "Class-of-service loss priority";
                   }
                 }
                 list loss-priority-map-table-entry {
                   leaf table-index {
                     type uint32;
                     description "Table index";
                   }
                   leaf code-point {
                     type string;
                     description "Class-of-service code point alias name or bits";
                   }
                   leaf loss-priority {
                     type string;
                     description "Class-of-service loss priority";
                   }
                 }
               }
             }
           }
           container cos-drop-profile-information {
             list drop-profile {
               leaf profile-name {
                 type string;
                 description "Class-of-service drop profile name";
               }
               leaf profile-type {
                 type string;
                 description "Class-of-service drop profile type";
               }
               leaf table-index {
                 type uint32;
                 description "Table index";
               }
               container profile-map {
                 container profile-map-item {
                   leaf fill-level {
                     type uint32;
                     description "Class-of-service drop profile fill level value";
                   }
                   leaf probability {
                     type uint32;
                     description "Class-of-service drop profile probability value";
                   }
                 }
               }
             }
           }
           container cos-mpls-ecn-map-information {
             list cos-mpls-ecn-map-info {
               leaf ecn-capable-exp {
                 type int32;
                 description "ECN capable exp";
               }
               leaf congestion-experienced-exp {
                 type int32;
                 description "Congestion Expereienced exp";
               }
             }
           }
           container cos-monitoring-profile-information {
             list monitoring-profile {
               leaf monitoring-profile-name {
                 type string;
                 description "Class-of-service monitoring profile name";
               }
               container export-filters {
                 container export-filter {
                   leaf filter-name {
                     type string;
                     description "Class-of-service monitoring profile filter name";
                   }
                   leaf monitoring-queue-number {
                     type uint32;
                     description "Class-of-service monitoring profile filter queue value";
                   }
                   leaf peak-queue-length-value {
                     type uint32;
                     description "Class-of-service monitoring profile peak queue length value";
                   }
                 }
               }
             }
           }
           container cos-rewrite-information {
             list rewrite {
               leaf rewrite-name {
                 type string;
                 description "Class-of-service rewrite rule name";
               }
               leaf code-point-type {
                 type string;
                 description "Class-of-service code point type";
               }
               leaf table-index {
                 type uint32;
                 description "Table index";
               }
               container rewrite-map {
                 list rewrite-map-item {
                   leaf fc-name {
                     type string;
                     description "Class-of-service forwarding class name";
                   }
                   leaf loss-priority {
                     type string;
                     description "Class-of-service loss priority";
                   }
                   leaf code-point {
                     type string;
                     description "Class-of-service code point alias name or bits";
                   }
                 }
               }
             }
           }
           container cos-loss-priority-rewrite-information {
             list loss-priority-rewrite {
               leaf loss-priority-rewrite-name {
                 type string;
                 description "Name of class-of-service loss priority rewrite";
               }
               leaf code-point-type {
                 type string;
                 description "Class-of-service code point type";
               }
               leaf table-index {
                 type uint32;
                 description "Table index";
               }
               list loss-priority-rewrite-table {
                 list loss-priority-rewrite-item {
                   leaf loss-priority {
                     type string;
                     description "Class-of-service loss priority";
                   }
                   leaf code-point {
                     type string;
                     description "Class-of-service code point alias name or bits";
                   }
                 }
                 list loss-priority-rewrite-table-entry {
                   leaf table-index {
                     type uint32;
                     description "Table index";
                   }
                   leaf loss-priority {
                     type string;
                     description "Class-of-service loss priority";
                   }
                   leaf code-point {
                     type string;
                     description "Class-of-service code point alias name or bits";
                   }
                 }
               }
             }
           }
           container cos-code-point-map-information {
             list code-point-map {
               leaf code-point-type {
                 type string;
                 description "Class-of-service code point type";
               }
               container alias-map {
                 list alias-map-item {
                   leaf code-point-alias {
                     type string;
                     description "Class-of-service code point alias name";
                   }
                   leaf code-point-bits {
                     type string;
                     description "Class-of-service code point bit sequence";
                   }
                 }
               }
             }
           }
           container cos-fragmentation-map-information {
             list fragmentation-map {
               leaf fragmentation-map-name {
                 type string;
                 description "Class-of-service fragmentation map name";
               }
               leaf fragmentation-map-index {
                 type uint32;
                 description "Index number for Class-of-service fragmentation map";
               }
               list fragment-map {
                 leaf fc-name {
                   type string;
                   description "Class-of-service forwarding class name";
                 }
                 leaf no-fragmentation {
                   type empty;
                   description "Do not fragment packets of this class";
                 }
                 leaf fragment-threshold {
                   type string;
                   description "Fragmentation threshold";
                 }
                 leaf fragment-multilink-class {
                   type int32;
                   description "Identifier for multilink class";
                 }
               }
             }
           }
           container cos-translation-table-map-information {
             list translation-table {
               leaf translation-table-name {
                 type string;
                 description "Class-of-service translation table name";
               }
               leaf translation-table-type {
                 type string;
                 description "Class-of-service translation table type";
               }
               leaf table-index {
                 type uint32;
                 description "Table index";
               }
               container translation-table-map {
                 container translation-table-map-item {
                   leaf from-code-point {
                     type string;
                     description "Class-of-service code point alias name or bits";
                   }
                   leaf to-code-point {
                     type string;
                     description "Class-of-service code point alias name or bits";
                   }
                 }
               }
               list translation-table-entry {
                 leaf table-index {
                   type uint32;
                   description "Table index";
                 }
                 leaf from-code-point {
                   type string;
                   description "Class-of-service code point alias name or bits";
                 }
                 leaf to-code-point {
                   type string;
                   description "Class-of-service code point alias name or bits";
                 }
               }
             }
           }
           container cos-multi-destination-information {
             container sm-md-map {
               leaf scheduler-map-name {
                 type string;
                 description "Class-of-service scheduler map name";
               }
               leaf scheduler-map-index {
                 type uint64;
                 description "Class-of-service scheduler map index";
               }
             }
             container fc-md-map {
               leaf fc-name {
                 type string;
                 description "Class-of-service forwarding class name";
               }
               leaf fc-queue-number {
                 type uint32;
                 description "Class-of-service forwarding class queue number";
               }
             }
             container cls-md-map {
               leaf multidest-classifier-name {
                 type string;
                 description "Multi destination classifier name";
               }
               leaf multidest-classifier-type {
                 type string;
                 description "Multi destination classifier type";
               }
               leaf multidest-classifier-index {
                 type uint32;
                 description "Multi destination classifier id";
               }
             }
           }
           container cos-forwarding-class-set-information {
             list forwarding-class-set {
               list forwarding-class-set-entry {
                 leaf forwarding-class-set-name {
                   type string;
                   description "Class-of-service forwarding class set name";
                 }
                 leaf forwarding-class-set-type {
                   type string;
                   description "Identifier for Class-of-service forwarding class set type";
                 }
                 leaf forwarding-class-set-index {
                   type uint32;
                   description "Identifier for Class-of-service forwarding class set";
                 }
                 container fc-map {
                   list fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-rqueue-number {
                       type uint32;
                       description "Class-of-service forwarding class restricted queue number";
                     }
                     leaf fc-priority {
                       type string;
                       description "Class-of-service forwarding class queue priority";
                     }
                     leaf fc-policing-priority {
                       type string;
                       description "Class-of-service forwarding class policing priority";
                     }
                     leaf fc-spu-priority {
                       type string;
                       description "Class-of-service forwarding class spu priority";
                     }
                     leaf fc-no-loss {
                       type string;
                       description "Class-of-service forwarding class no-loss";
                     }
                     leaf fc-pfc-priority {
                       type uint32;
                       description "Class-of-service forwarding class pfc-priority";
                     }
                     leaf fc-multicast {
                       type string;
                       description "Class-of-service forwarding class multicast";
                     }
                   }
                 }
               }
             }
           }
           container cos-policy-map-information {
             list policy-map {
               leaf policy-map-name {
                 type string;
                 description "Class-of-service Policy-map name";
               }
               leaf table-index {
                 type uint32;
                 description "Table index";
               }
               leaf policy-map-user-attribute {
                 type uint32;
                 description "User-defined attribute";
               }
               container policy-map-cp-entries {
                 leaf code-point-type {
                   type string;
                   description "Class-of-service code point type";
                 }
                 leaf code-point {
                   type string;
                   description "Class-of-service code point alias name or bits";
                 }
                 leaf code-point-option {
                   type string;
                   description "Class-of-service code point option flag";
                 }
               }
             }
           }
           container cos-client-info {
             list cos-client {
               leaf cos-client-info-internal-id {
                 type uint32;
                 description "Junos client internal identifier";
               }
               leaf cos-client-info-requests {
                 type uint32;
                 description "Number of requests from Junos client";
               }
               leaf cos-client-info-responses {
                 type uint32;
                 description "Number of responses to Junos client";
               }
               leaf cos-client-info-failures {
                 type uint32;
                 description "Number of failures while handling Junos client requests";
               }
               leaf cos-client-info-identifier {
                 type string;
                 description "Junos client identifier";
               }
               leaf cos-client-name {
                 type string;
                 description "Junos client name";
               }
               leaf cos-client-state {
                 type string;
                 description "Junos client state information";
               }
               leaf cos-client-internal-name {
                 type string;
                 description "Junos client internal name";
               }
               leaf cos-client-stats {
                 type string;
                 description "Junos client statistics";
               }
               leaf cos-client-failure-stats {
                 type string;
                 description "Junos client failure/error statistics";
               }
               leaf cos-client-validate-failures {
                 type uint32;
                 description "Junos client request validation failures";
               }
               leaf cos-client-ownership-failures {
                 type uint32;
                 description "Junos client ownership validation failures";
               }
               leaf cos-client-info-name {
                 type string;
                 description "CoS client name";
               }
               leaf cos-client-internal-id {
                 type uint32;
                 description "Junos client internal identifier";
               }
               leaf cos-client-requests {
                 type uint64;
                 description "Number of requests from Junos client";
               }
               leaf cos-client-responses {
                 type uint64;
                 description "Number of responses to Junos client";
               }
               leaf cos-client-failures {
                 type uint64;
                 description "Number of failures while handling Junos client requests";
               }
               leaf cos-client-identifier {
                 type string;
                 description "Junos client identifier";
               }
               leaf cos-client-status {
                 type string;
                 description "Junos client status";
               }
               leaf cos-client-connected-time {
                 type string;
                 description "Junos client time of connect";
               }
               leaf cos-client-reconnected-time {
                 type string;
                 description "Junos client time of reconnect";
               }
               leaf cos-client-disconnected-time {
                 type string;
                 description "Junos client time of disconnect";
               }
               leaf cos-client-message-type {
                 type string;
                 description "Junos client message type";
               }
               leaf cos-client-operation-type {
                 type string;
                 description "Junos client operation type";
               }
               leaf-list cos-bind-point-type {
                 type string;
                 description "Class-of-service bind point type";
               }
               leaf-list cos-bind-point-owner-type {
                 type string;
                 description "Class-of-service bind point owner type";
               }
               leaf-list cos-bind-point-owner-internal-id {
                 type uint32;
                 description "Junos client internal identifier";
               }
               leaf-list cos-bind-point-name {
                 type string;
                 description "Class-of-service bind point name";
               }
               leaf cos-bind-point-feature {
                 type string;
                 description "Class-of-service bind point feature name";
               }
               leaf cos-bind-point-feature-object-name {
                 type string;
                 description "Class-of-service bind point feature object name";
               }
             }
           }
           container cos-host-outbound-info {
             list cos-host-outbound-traffic-info {
               leaf cos-host-outbound-traffic-protocol-name {
                 type string;
                 description "CoS host outbound traffic protocol name";
               }
               leaf cos-host-outbound-traffic-dscp {
                 type string;
                 description "CoS host outbound traffic dscp";
               }
               leaf cos-host-outbound-traffic-dot1p {
                 type string;
                 description "CoS host outbound traffic ieee 802.1p";
               }
               leaf cos-host-outbound-traffic-fc-id {
                 type string;
                 description "CoS host outbound traffic forwarding class id";
               }
               leaf cos-host-outbound-traffic-queue-id {
                 type string;
                 description "CoS host outbound traffic queue id";
               }
               leaf cos-host-outbound-traffic-restrict-queue-id {
                 type string;
                 description "CoS host outbound traffic restrict queue id";
               }
               leaf cos-host-outbound-traffic-override-firewall {
                 type string;
                 description "CoS host outbound traffic override firwall action";
               }
               leaf cos-host-outbound-traffic-rw-dot1p {
                 type string;
                 description "CoS host outbound traffic - use ieee 802.1p rewrite rules";
               }
             }
           }
           container cos-drop-congestion-notification-information {
             list cos-drop-congestion-notification-info {
               leaf cos-dcn-fc-name {
                 type string;
                 description "Cos DCN forwarding class";
               }
               leaf cos-dcn-udp-port {
                 type int32;
                 description "Cos DCN udp port number";
               }
             }
           }
           container cos-dedicated-buffer-profile-information {
             list dedicated-buffer-profile {
               leaf dedicated-buffer-profile-name {
                 type string;
                 description "Class-of-service dedicated buffer profile name";
               }
               leaf dedicated-buffer-profile-index {
                 type int32;
                 description "Class-of-service dedicated buffer profile index";
               }
               leaf ingress-buffer-size {
                 type string;
                 description "Ingress per port dedicated buffer in cells";
               }
               leaf egress-buffer-size {
                 type string;
                 description "Egress per port dedicated buffer in cells";
               }
             }
           }
           container cos-dynamic-threshold-profile-information {
             list dynamic-threshold-profile {
               leaf dynamic-threshold-profile-name {
                 type string;
                 description "Class-of-service dynamic threshold profile name";
               }
               leaf dynamic-threshold-profile-index {
                 type uint64;
                 description "Class-of-service dynamic threshold profile index";
               }
               list dynamic-threshold-profile-entry {
                 leaf dynamic-threshold-profile-priority-group {
                   type string;
                   description "Class-of-service dynamic threshold profile priority group";
                 }
                 leaf dynamic-threshold-profile-threshold-value {
                   type uint32;
                   description "Class-of-service dynamic threshold profile threshold value";
                 }
               }
             }
           }
           container cos-decn-profile-information {
             list decn-profile {
               leaf decn-profile-name {
                 type string;
                 description "Class-of-service decn profile name";
               }
               leaf decn-profile-index {
                 type uint64;
                 description "Class-of-service decn profile index";
               }
               list decn-profile-queue {
                 leaf dynamic-explicit-congestion-notification-queue {
                   type uint32;
                   description "Class-of-service DECN queue";
                 }
                 leaf dynamic-explicit-congestion-notification-offset {
                   type uint32;
                   description "Class-of-service DECN offset";
                 }
                 leaf dynamic-explicit-congestion-notification-floor {
                   type uint32;
                   description "Class-of-service DECN floor";
                 }
               }
             }
           }
           container cos-scheduler-map-information {
             list scheduler-map {
               leaf scheduler-map-name {
                 type string;
                 description "Class-of-service scheduler map name";
               }
               leaf scheduler-map-index {
                 type uint64;
                 description "Class-of-service scheduler map index";
               }
               leaf user-plane-name {
                 type string;
                 description "Class-of-service user-plane name for XDA";
               }
               list scheduler {
                 leaf scheduler-name {
                   type string;
                   description "Class-of-service scheduler name";
                 }
                 leaf fc-name {
                   type string;
                   description "Class-of-service forwarding class name";
                 }
                 leaf scheduler-index {
                   type uint64;
                   description "Class of service scheduler index";
                 }
                 leaf scheduler-tx-rate {
                   type string;
                   description "Class-of-service scheduler transmit rate";
                 }
                 leaf scheduler-tx-limit {
                   type string;
                   description "Class-of-service scheduler transmit limit";
                 }
                 leaf scheduler-buffer-size {
                   type string;
                   description "Class-of-service scheduler buffer size";
                 }
                 leaf scheduler-buffer-multicast-share {
                   type uint32;
                   description "Class-of-service scheduler multicast buffer share";
                 }
                 leaf scheduler-buffer-limit {
                   type string;
                   description "Class-of-service scheduler buffer limit";
                 }
                 leaf scheduler-buffer-rate {
                   type string;
                   description "Class-of-service scheduler buffer rate";
                 }
                 leaf scheduler-shared-buffer-maximum-percentage {
                   type uint32;
                   description "Shared Buffer maximum percentage";
                 }
                 leaf scheduler-shared-buffer-multicast-maximum-percentage {
                   type uint32;
                   description "Shared Buffer multicast maximum percentage";
                 }
                 leaf scheduler-buffer-dynamic-threshold {
                   type uint32;
                   description "Queue shared-buffer dynamic threshold";
                 }
                 leaf scheduler-priority {
                   type string;
                   description "Class-of-service scheduler priority";
                 }
                 leaf scheduler-shaping-rate {
                   type string;
                   description "Class-of-service scheduler shaping rate";
                 }
                 leaf scheduler-shaping-rate-burst {
                   type string;
                   description "Class-of-service scheduler shaping rate burst";
                 }
                 leaf scheduler-adjust-minimum {
                   type int32;
                   description "Class-of-service scheduler adjustment minimum rate";
                 }
                 leaf scheduler-adjust-percent {
                   type int32;
                   description "Class-of-service scheduler percent adjustment for a queue";
                 }
                 leaf scheduler-excess-priority {
                   type string;
                   description "Class-of-service scheduler excess priority";
                 }
                 leaf scheduler-excess-rate {
                   type string;
                   description "Class-of-service scheduler excess rate";
                 }
                 leaf scheduler-explicit-congestion-notification {
                   type string;
                   description "Class-of-service ECN status of queue";
                 }
                 leaf scheduler-ecn-rtlog-rate-limit {
                   type uint32;
                   description "Class-of-service ECN Security Log Rate Limit";
                 }
                 leaf scheduler-ecn-no-pfc-assist {
                   type string;
                   description "Class-of-service ECN no pfc assist";
                 }
                 leaf scheduler-queue-monitoring {
                   type string;
                   description "Class-of-service queue depth monitoring of queue";
                 }
                 leaf scheduler-drop-profile-ln-index {
                   type uint32;
                   description "Class-of-service scheduler drop profile index low, non-TCP";
                 }
                 leaf scheduler-drop-profile-ln {
                   type string;
                   description "Class-of-service scheduler drop profile low, non-TCP";
                 }
                 leaf scheduler-drop-profile-lt-index {
                   type uint32;
                   description "Class-of-service scheduler drop profile index low, TCP";
                 }
                 leaf scheduler-drop-profile-lt {
                   type string;
                   description "Class-of-service scheduler drop profile low, TCP";
                 }
                 leaf scheduler-drop-profile-hn-index {
                   type uint32;
                   description "Class-of-service scheduler drop profile index high, non-TCP";
                 }
                 leaf scheduler-drop-profile-hn {
                   type string;
                   description "Class-of-service scheduler drop profile high, non-TCP";
                 }
                 leaf scheduler-drop-profile-ht-index {
                   type uint32;
                   description "Class-of-service scheduler drop profile index high, TCP";
                 }
                 leaf scheduler-drop-profile-ht {
                   type string;
                   description "Class-of-service scheduler drop profile high, TCP";
                 }
                 leaf scheduler-drop-profile-la-index {
                   type uint32;
                   description "Class-of-service scheduler drop profile index low";
                 }
                 leaf scheduler-drop-profile-la {
                   type string;
                   description "Class-of-service scheduler drop profile low";
                 }
                 leaf scheduler-drop-profile-ma-index {
                   type uint32;
                   description "Class-of-service scheduler drop profile index medium";
                 }
                 leaf scheduler-drop-profile-ma {
                   type string;
                   description "Class-of-service scheduler drop profile medium";
                 }
                 leaf scheduler-drop-profile-mla-index {
                   type uint32;
                   description "Class-of-service scheduler drop profile index medium-low";
                 }
                 leaf scheduler-drop-profile-mla {
                   type string;
                   description "Class-of-service scheduler drop profile medium-low";
                 }
                 leaf scheduler-drop-profile-mha-index {
                   type uint32;
                   description "Class-of-service scheduler drop profile index medium-high";
                 }
                 leaf scheduler-drop-profile-mha {
                   type string;
                   description "Class-of-service scheduler drop profile medium-high";
                 }
                 leaf scheduler-drop-profile-ha-index {
                   type uint32;
                   description "Class-of-service scheduler drop profile index high";
                 }
                 leaf scheduler-drop-profile-ha {
                   type string;
                   description "Class-of-service scheduler drop profile high";
                 }
               }
             }
           }
           container cos-traffic-control-profile-information {
             list traffic-control-profile {
               leaf traffic-control-profile-name {
                 type string;
                 description "Class-of-service traffic control profile name";
               }
               leaf traffic-control-profile-index {
                 type uint64;
                 description "Index number for Class-of-service traffic control profile";
               }
               leaf user-plane-name {
                 type string;
                 description "Class-of-service user-plane name for XDA";
               }
               leaf scheduler-map-name {
                 type string;
                 description "Class-of-service scheduler map name";
               }
               leaf atm-service {
                 type string;
                 description "Class-of-service traffic control profile atm service";
               }
               leaf shaping-rate {
                 type uint64;
                 description "Class-of-service shaping rate";
               }
               leaf shaping-rate-burst {
                 type uint32;
                 description "Class-of-service shaping rate burst, in bytes";
               }
               leaf low-granularity {
                 type uint32;
                 description "Class-of-service low-granularity mode support";
               }
               leaf queue-mode-4q {
                 type uint32;
                 description "Class-of-service tcp-voq-mode(4Q) mode support";
               }
               leaf shaping-rate-priority-strict-high {
                 type uint64;
                 description "Class-of-service shaping rate for priority strict high";
               }
               leaf shaping-rate-priority-strict-high-burst {
                 type uint32;
                 description "Class-of-service shaping rate burst for priority strict-high";
               }
               leaf shaping-rate-priority-high {
                 type uint64;
                 description "Class-of-service shaping rate for priority high";
               }
               leaf shaping-rate-priority-high-burst {
                 type uint32;
                 description "Class-of-service shaping rate for priority high burst";
               }
               leaf shaping-rate-priority-medium {
                 type uint64;
                 description "Class-of-service shaping rate for priority medium";
               }
               leaf shaping-rate-priority-medium-burst {
                 type uint32;
                 description "Class-of-service shaping rate for priority medium burst";
               }
               leaf shaping-rate-priority-medium-low {
                 type uint64;
                 description "Class-of-service shaping rate for priority medium-low";
               }
               leaf shaping-rate-priority-medium-low-burst {
                 type uint32;
                 description "Class-of-service shaping rate burst for priority medium-low";
               }
               leaf shaping-rate-priority-low {
                 type uint64;
                 description "Class-of-service shaping rate for priority low";
               }
               leaf shaping-rate-priority-low-burst {
                 type uint32;
                 description "Class-of-service shaping rate for priority low burst";
               }
               leaf shaping-rate-excess-high {
                 type uint64;
                 description "Class-of-service shaping rate for excess high";
               }
               leaf shaping-rate-excess-high-burst {
                 type uint32;
                 description "Class-of-service shaping rate for excess high burst";
               }
               leaf shaping-rate-excess-medium-high {
                 type uint64;
                 description "Class-of-service shaping rate for excess medium-high";
               }
               leaf shaping-rate-excess-medium-high-burst {
                 type uint32;
                 description "Class-of-service shaping rate burst for excess medium-high";
               }
               leaf shaping-rate-excess-medium-low {
                 type uint64;
                 description "Class-of-service shaping rate for excess medium-low";
               }
               leaf shaping-rate-excess-medium-low-burst {
                 type uint32;
                 description "Class-of-service shaping rate burst for excess medium-low";
               }
               leaf shaping-rate-excess-low {
                 type uint64;
                 description "Class-of-service shaping rate for excess low";
               }
               leaf shaping-rate-excess-low-burst {
                 type uint32;
                 description "Class-of-service shaping rate for excess low burst";
               }
               leaf guaranteed-rate {
                 type uint64;
                 description "Class-of-service guaranteed rate";
               }
               leaf guaranteed-rate-burst {
                 type uint32;
                 description "Class-of-service guaranteed rate burst, in bytes";
               }
               leaf delay-buffer-rate {
                 type uint64;
                 description "Class-of-service delay buffer rate";
               }
               leaf excess-rate {
                 type uint32;
                 description "Class-of-service excess rate";
               }
               leaf excess-rate-high {
                 type uint32;
                 description "Class-of-service excess rate for excess-high priority traffic";
               }
               leaf excess-rate-medium-high {
                 type uint32;
                 description "Class-of-service excess rate for excess-medium-high priority traffic";
               }
               leaf excess-rate-medium-low {
                 type uint32;
                 description "Class-of-service excess rate for excess-medium-low priority traffic";
               }
               leaf excess-rate-low {
                 type uint32;
                 description "Class-of-service excess rate for excess-low priority traffic";
               }
               leaf adjust-minimum {
                 type uint64;
                 description "Class-of-service adjustment minimum rate";
               }
               leaf overhead-bytes {
                 type int32;
                 description "Class-of-service Overhead bytes";
               }
               leaf frame-mode-bytes {
                 type int32;
                 description "Class-of-service overhead bytes when in frame-mode";
               }
               leaf cell-mode-bytes {
                 type int32;
                 description "Class-of-service overhead bytes when in cell-mode";
               }
               leaf overhead-accounting-mode {
                 type string;
                 description "Class-of-service Overhead Accounting Mode";
               }
               list traffic-control-profile-instance {
                 leaf traffic-control-profile-instance-name {
                   type string;
                   description "Class-of-service traffic control profile instance";
                 }
                 leaf traffic-control-profile-instance-index {
                   type uint32;
                   description "Index number for Class-of-service traffic control profile instance";
                 }
                 leaf instance-reference-count {
                   type uint32;
                   description "Instance reference count";
                 }
               }
             }
           }
           container cos-routing-instance-information {
             list routing-instance-map {
               leaf routing-instance-name {
                 type string;
                 description "Name of class-of-service routing instance";
               }
               list i-logical-map {
                 leaf i-logical-name {
                   type string;
                   description "Class-of-service logical interface name";
                 }
                 leaf i-logical-index {
                   type uint32;
                   description "Class-of-service logical interface index";
                 }
                 leaf monitoring-profile-map-name {
                   type string;
                   description "Monitoring Profile Name";
                 }
                 list cos-objects {
                   leaf cos-object-type {
                     type string;
                     description "Class-of-service object type";
                   }
                   leaf cos-object-name {
                     type string;
                     description "Class-of-service object name";
                   }
                   leaf cos-object-subtype {
                     type string;
                     description "Class-of-service object subtype";
                   }
                   leaf cos-object-index {
                     type uint64;
                     description "Class-of-service object index";
                   }
                 }
               }
             }
           }
           container cos-fabric-scheduler-map-information {
             container fabric-scheduler-map {
               list fabric-scheduler {
                 leaf fabric-scheduler-name {
                   type string;
                   description "Class-of-service scheduler name";
                 }
                 leaf fabric-scheduler-index {
                   type uint32;
                   description "Class of service scheduler index";
                 }
                 leaf fabric-scheduler-drop-profile-ln-index {
                   type uint32;
                   description "Class-of-service scheduler drop profile index low, non-TCP";
                 }
                 leaf fabric-scheduler-drop-profile-ln {
                   type string;
                   description "Class-of-service scheduler drop profile low, non-TCP";
                 }
                 leaf fabric-scheduler-drop-profile-lt-index {
                   type uint32;
                   description "Class-of-service scheduler drop profile index low, TCP";
                 }
                 leaf fabric-scheduler-drop-profile-lt {
                   type string;
                   description "Class-of-service scheduler drop profile low, TCP";
                 }
                 leaf fabric-scheduler-drop-profile-hn-index {
                   type uint32;
                   description "Class-of-service scheduler drop profile index high, non-TCP";
                 }
                 leaf fabric-scheduler-drop-profile-hn {
                   type string;
                   description "Class-of-service scheduler drop profile high, non-TCP";
                 }
                 leaf fabric-scheduler-drop-profile-ht-index {
                   type uint32;
                   description "Class-of-service scheduler drop profile index high, TCP";
                 }
                 leaf fabric-scheduler-drop-profile-ht {
                   type string;
                   description "Class-of-service scheduler drop profile high, TCP";
                 }
                 leaf fabric-scheduler-priority {
                   type string;
                 }
               }
             }
           }
           container cos-tcm-information {
             list tcm {
               leaf tcm-name {
                 type string;
                 description "Class-of-service traffic-class-map name";
               }
               leaf tcm-type {
                 type string;
                 description "Class-of-service traffic-class-map type";
               }
               leaf table-index {
                 type uint32;
                 description "Table index";
               }
               container tcm-map {
                 list tcm-map-item {
                   leaf code-point {
                     type string;
                     description "Class-of-service code point alias name or bits";
                   }
                   leaf tc-name {
                     type string;
                     description "Class-of-service traffic-class-map traffic-class name";
                   }
                 }
               }
             }
           }
         }
         container physical-interface-cos-information {
         }
         container precl-statistics {
           container precl-information {
           }
         }
         container mlfr-uni-nni-traffic-statistics {
           container bundle {
           }
         }
       }
       list logical-interface {
         leaf name {
           type string;
           description "Name of this item";
         }
         leaf admin-status {
           type string;
           description "Desired state of the interface";
         }
         leaf oper-status {
           type string;
           description "Current operational state of the interface";
         }
         leaf vrfname {
           type string;
           description "Routing instance name";
         }
         leaf zonename {
           type string;
           description "Zone name";
         }
         leaf subunit {
           type int32;
           description "Subunit for this interface";
         }
         leaf dialer-time-to-disconnect {
           type string;
           description "Time for dialer to disconnect due to idle timeout";
         }
         leaf lcp-state {
           type string;
           description "State of the Line Control Protocol";
         }
         leaf chap-state {
           type string;
           description "State of the Challenge Handshake Authentication Protocol";
         }
         leaf pap-state {
           type string;
           description "State of the Password Authentication Protocol";
         }
         container pppoe-information {
           list pppoe-interface {
             leaf state {
               type string;
               description "State";
             }
             leaf session-id {
               type string;
               description "Session ID";
             }
             leaf ac-name-session {
               type string;
               description "Session AC name";
             }
             leaf remote-mac {
               type string;
               description "Remote MAC address";
             }
             leaf ac-name-config {
               type string;
               description "Configured AC name";
             }
             leaf service-name {
               type string;
               description "Service name";
             }
             leaf auto-reconnect {
               type string;
               description "Autoreconnect timeout";
             }
             leaf idle-timeout {
               type string;
               description "Idle timeout";
             }
             leaf underlying-interface-name {
               type string;
               description "Underlying interface name";
             }
             leaf underlying-interface-index {
               type string;
               description "Underlying interface index";
             }
             leaf padg-credits {
               type int32;
               description "PADG transmit credits";
             }
             leaf pppoe-credit-scale-factor {
               type string;
               description "Scaling factor";
             }
             leaf ignore-eol-tag {
               type string;
               description "Ignore End-of-List TAG";
             }
             leaf ppp-max-payload-tag {
               type int32;
               description "PPP-Max-Payload TAG";
             }
             leaf interface-name {
               type string;
               description "Class-of-service interface name";
             }
             leaf interface-index {
               type uint32;
               description "Class-of-service interface index";
             }
             leaf aci-iflset-name {
               type string;
               description "ACI Interface Set name";
             }
             leaf aci-iflset-index {
               type string;
               description "ACI Interface Set index";
             }
             leaf ifl-type {
               type string;
               description "Type";
             }
             leaf session-uptime {
               type string;
               description "Duration for which the session has been up";
             }
             leaf dynamic-profile {
               type string;
               description "Dynamic Profile name";
             }
             leaf pppoe-credits {
               type string;
               description "Forwarding credit balances";
             }
             leaf dynamic-interface-bandwidth {
               type string;
               description "Dynamic interface bandwidth";
             }
             leaf agent-circuit-id {
               type string;
               description "Agent Circuit ID";
             }
             leaf agent-remote-id {
               type string;
               description "Agent Remote ID";
             }
             leaf padm-motm {
               type string;
               description "PADM Message of the Moment tag";
             }
             leaf padm-hurl {
               type string;
               description "PADM HTTP URL tag";
             }
           }
         }
         container pppoe-underlying-information {
           list pppoe-underlying-interface {
             leaf dynamic-profile {
               type string;
               description "Dynamic Profile name";
             }
             leaf service-name-table {
               type string;
               description "Name of Service Name Table";
             }
             leaf max-sessions {
               type int32;
               description "Maximum number of PPPoE sessions";
             }
             leaf max-sessions-vsa-ignore {
               type string;
               description "Ignore max-sessions VSA";
             }
             leaf duplicate-protection {
               type string;
               description "Duplicate protection mode";
             }
             leaf short-cycle-protection {
               type string;
               description "Short cycle protection mode";
             }
             leaf direct-connect {
               type string;
               description "Direct connect mode";
             }
             leaf ac-name {
               type string;
               description "Access Concentrator name";
             }
             leaf underlying-interface-name {
               type string;
               description "Underlying interface name";
             }
             leaf underlying-interface-index {
               type string;
               description "Underlying interface index";
             }
             leaf encapsulation-type-identifier {
               type string;
               description "Encapsulation type identifier";
             }
             leaf state {
               type string;
               description "State";
             }
             leaf active-sessions {
               type int32;
               description "Number of active PPPoE sessions";
             }
             leaf aci-autosensing {
               type string;
               description "ACI VLAN Autosensing mode";
             }
             leaf line-identity-autosensing {
               type string;
               description "Line Identity Autosensing mode";
             }
           }
         }
         container aci-vlan-information {
           leaf dynamic-profile {
             type string;
             description "Dynamic Profile name";
           }
         }
         container line-identity-information {
           leaf dynamic-profile {
             type string;
             description "Dynamic Profile name";
           }
           leaf circuit-id {
             type string;
             description "Aci vlan attribute";
           }
           leaf remote-id {
             type string;
             description "Aci vlan attribute";
           }
           leaf accept-no-ids {
             type string;
             description "Aci vlan attribute";
           }
         }
         container demux-information {
           container demux-interface {
             leaf demux-underlying-interface-name {
               type string;
               description "Underlying interface name";
             }
             leaf demux-underlying-interface-index {
               type string;
               description "Underlying interface index";
             }
             leaf demux-inet-prefix-type {
               type string;
               description "Prefix type";
             }
             leaf demux-inet-prefix-count {
               type string;
               description "IPv4 Prefix count";
             }
             leaf demux-inet-prefix {
               type string;
               description "IPv4 Prefix";
             }
             leaf demux-inet6-prefix-type {
               type string;
               description "Prefix type";
             }
             leaf demux-inet6-prefix-count {
               type string;
               description "IPv6 Prefix count";
             }
             leaf demux-inet6-prefix {
               type string;
               description "IPv6 Prefix";
             }
           }
         }
         container dual-ad-icl-color-information {
           container dual-ad-icl-color-info {
             leaf dual-ad-icl-color-type {
               type uint32;
               description "Dual-AD ICL Color Type";
             }
             leaf dual-ad-icl-color {
               type uint32;
               description "Dual-AD ICL Color";
             }
           }
         }
         container dialer-information {
           leaf dialer-time-to-disconnect {
             type string;
             description "Time for dialer to disconnect due to idle timeout";
           }
           container dialer-interface {
             leaf dialer-interface-name {
               type string;
               description "Interface name";
             }
             leaf dialer-interface-state {
               type string;
               description "Dialer interface state";
             }
             leaf pool-id {
               type string;
               description "Pool identifier";
             }
             leaf primary-interface {
               type string;
               description "Primary interface";
             }
             leaf activation-delay {
               type string;
               description "Activation delay";
             }
             leaf deactivation-delay {
               type string;
               description "Deactivation delay";
             }
             leaf activation-delay-elapsed {
               type string;
               description "Activation delay elapsed";
             }
             leaf deactivation-delay-elapsed {
               type string;
               description "Deactivation delay elapsed";
             }
             leaf call-idle-timeout {
               type string;
               description "Call idle timeout";
             }
             leaf initial-route-check {
               type string;
               description "Initial route check delay";
             }
             leaf redial-delay {
               type string;
               description "Delay before dialer dials out again (seconds)";
             }
             leaf callback-wait-period {
               type string;
               description "Delay before dialer attempts callback (seconds)";
             }
             leaf callback-wait-period-elapsed {
               type string;
               description "Number of seconds in callback wait period that have elapsed";
             }
             leaf load-threshold {
               type string;
               description "Load threshold that determines when interfaces are added to bundle";
             }
             leaf load-interval {
               type string;
               description "Interval over which average load is calculated";
             }
             container dialer-interface-flags {
               leaf backup {
                 type empty;
                 description "Dialer backup";
               }
               leaf multilink {
                 type empty;
                 description "Dialer multilink";
               }
               leaf watchlist {
                 type empty;
                 description "Dialer watchlist";
               }
               leaf interesting-detected {
                 type empty;
                 description "Interesting packet detected";
               }
             }
           }
         }
         container shared-interface-information {
           container shared-interface-logical-interface {
             leaf peer-interface-name {
               type string;
               description "Peer interface name";
             }
             leaf interface-shared-with {
               type string;
               description "Logical interface owner";
             }
             leaf rx-fe {
               type string;
               description "Rx tunnel token forwarding element";
             }
             leaf rx-nhid {
               type string;
               description "Rx tunnel token next hop index";
             }
             leaf tx-fe {
               type string;
               description "Tx tunnel token forwarding element";
             }
             leaf tx-nhid {
               type string;
               description "Tx tunnel token next hop index";
             }
           }
         }
         container mac-database {
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
           }
           container multilink-detail-statistics {
             container bundle-detail {
             }
             container class-detail {
             }
           }
           container crtp {
             container crtp-sessions {
               leaf input-frames {
                 type int32;
               }
               leaf output-frames {
                 type int32;
               }
             }
             list crtp-statistics {
               leaf name {
                 type string;
                 description "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container transit-traffic-statistics {
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-cos-information {
             leaf vc-cos-mode {
               type string;
               description "Virtual circuit CoS scheduling mode";
             }
             list atm-cos-queue {
               container atm-cos-queue-parameters {
                 leaf cos-forwarding-class-name {
                   type string;
                   description "Forwarding class name associated with queue";
                 }
                 leaf cos-queue-number {
                   type int32;
                   description "Queue number";
                 }
                 leaf scheduling-priority {
                   type string;
                   description "Scheduling priority";
                 }
                 leaf transmit-weight-cells {
                   type int32;
                   description "Weight to apply to scheduling as number of cells";
                 }
                 leaf transmit-weight-percent {
                   type int32;
                   description "Weight to apply to scheduling as fill percentage";
                 }
                 leaf epd-threshold {
                   type int32;
                   description "Early packet drop threshold";
                 }
                 leaf epd-threshold-plp0 {
                   type int32;
                   description "Early packet drop threshold for PLP 0";
                 }
                 leaf epd-threshold-plp1 {
                   type int32;
                   description "Early packet drop threshold for PLP 1";
                 }
                 container linear-red-drop-profile {
                   leaf queue-depth {
                     type uint32;
                     description "Instantaneous queue depth";
                   }
                   leaf low-red {
                     type int32;
                     description "Fill level percentage when linear RED is applied for low PLP";
                   }
                   leaf high-red {
                     type int32;
                     description "Fill level percentage when linear RED is applied for high PLP";
                   }
                   leaf max-low-red {
                     type int32;
                     description "Fill level percentage with 100% packet drop for low PLP";
                   }
                   leaf max-high-red {
                     type int32;
                     description "Fill level percentage with 100% packet drop for high PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         list filter-information {
           leaf filter-family {
             type string;
             description "Protocol family of the filter";
           }
           leaf-list filter-input {
             type string;
             description "Name of the input filter";
           }
           leaf-list filter-output {
             type string;
             description "Name of the output filter";
           }
         }
         list address-family {
           leaf local-bias-information {
             type string;
           }
           leaf ft-iff-dest-port {
             type uint32;
             description "Destination UDP port to be used for this family";
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           list interface-address {
           }
           container destination-class-statistics {
           }
           container source-class-statistics {
           }
         }
         list bridge-iff-properties {
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         list macsec-statistics {
           leaf interface-name {
             type string;
             description "Class-of-service interface name";
           }
           leaf encrypted-packets {
             type uint64;
             description "Macsec encrypted packets sent";
           }
           leaf encrypted-bytes {
             type uint64;
             description "Macsec encrypted bytes sent";
           }
           leaf protected-packets {
             type uint64;
             description "Macsec packets sent with only integrity protection";
           }
           leaf protected-bytes {
             type uint64;
             description "Macsec bytes sent with only integrity protection";
           }
           leaf ok-packets {
             type uint64;
             description "Macsec packets accepted";
           }
           leaf decrypted-bytes {
             type uint64;
             description "Macsec received bytes decrypted";
           }
           leaf decrypted-packets {
             type uint64;
             description "Macsec received packets decrypted";
           }
           leaf validated-packets {
             type uint64;
             description "Macsec received packets validated";
           }
           leaf validated-bytes {
             type uint64;
             description "Macsec received bytes validated";
           }
           leaf untagged-packets {
             type uint64;
             description "Macsec untagged packets";
           }
           leaf toolong-packets {
             type uint64;
             description "Macsec too long packets transmitted on a secure channel";
           }
           leaf control-packets {
             type uint64;
             description "Macsec control packets received on a secure channel";
           }
           leaf tagged-miss-packets {
             type uint64;
             description "Macsec tagged miss packets received on a secure channel";
           }
           leaf untagged-hit-packets {
             type uint64;
             description "Macsec untagged hit packets received on a secure channel";
           }
           leaf notag-packets {
             type uint64;
             description "Macsec no tag packets received on a secure channel";
           }
           leaf badtag-packets {
             type uint64;
             description "Macsec bad tag packets received on a secure channel";
           }
           leaf unknown-sci-packets {
             type uint64;
             description "Macsec unknown sci packets received on a secure channel";
           }
           leaf no-sci-packets {
             type uint64;
             description "Macsec no sci packets received on a secure channel";
           }
           leaf control-pass-packets {
             type uint64;
             description "Macsec allowed control packets received on a secure channel";
           }
           leaf uncontrol-pass-packets {
             type uint64;
             description "Macsec allowed uncontrol packets received on a secure channel";
           }
           leaf control-fail-packets {
             type uint64;
             description "Macsec dropped control packets received on a secure channel";
           }
           leaf uncontrol-fail-packets {
             type uint64;
             description "Macsec dropped uncontrol packets received on a secure channel";
           }
           leaf hit-dropped-packets {
             type uint64;
             description "Macsec hit dropped packets received on a security channel";
           }
           leaf notusing-sa-packets {
             type uint64;
             description "Macsec not using sa packets received on a security channel";
           }
           leaf unused-sa-packets {
             type uint64;
             description "Macsec unused sa packets received on a security channel";
           }
           leaf late-packets {
             type uint64;
             description "Macsec late packets dropped on a security channel";
           }
           leaf delayed-packets {
             type uint64;
             description "Macsec delayed packets accepted on a security channel";
           }
           leaf unchecked-packets {
             type uint64;
             description "Macsec unchecked packets accepted on a security channel";
           }
           leaf notvalid-packets {
             type uint64;
             description "Macsec not valid packets dropped on a security channel";
           }
           leaf invalid-packets {
             type uint64;
             description "Macsec invalid packets accepted on a security channel";
           }
           list secure-channel-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-association-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-channel-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list secure-association-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list macsec-error-information {
             list secure-channel-sent-errors {
               leaf untagged-packets {
                 type uint64;
                 description "Macsec untagged packets";
               }
               leaf toolong-packets {
                 type uint64;
                 description "Macsec too long packets transmitted on a secure channel";
               }
             }
             list secure-channel-received-errors {
               leaf control-packets {
                 type uint64;
                 description "Macsec control packets received on a secure channel";
               }
               leaf tagged-miss-packets {
                 type uint64;
                 description "Macsec tagged miss packets received on a secure channel";
               }
               leaf untagged-hit-packets {
                 type uint64;
                 description "Macsec untagged hit packets received on a secure channel";
               }
               leaf untagged-packets {
                 type uint64;
                 description "Macsec untagged packets";
               }
               leaf notag-packets {
                 type uint64;
                 description "Macsec no tag packets received on a secure channel";
               }
               leaf badtag-packets {
                 type uint64;
                 description "Macsec bad tag packets received on a secure channel";
               }
               leaf unknown-sci-packets {
                 type uint64;
                 description "Macsec unknown sci packets received on a secure channel";
               }
               leaf no-sci-packets {
                 type uint64;
                 description "Macsec no sci packets received on a secure channel";
               }
               leaf control-pass-packets {
                 type uint64;
                 description "Macsec allowed control packets received on a secure channel";
               }
               leaf control-fail-packets {
                 type uint64;
                 description "Macsec dropped control packets received on a secure channel";
               }
               leaf uncontrol-pass-packets {
                 type uint64;
                 description "Macsec allowed uncontrol packets received on a secure channel";
               }
               leaf uncontrol-fail-packets {
                 type uint64;
                 description "Macsec dropped uncontrol packets received on a secure channel";
               }
             }
             list secure-channel-received-extended {
               leaf hit-dropped-packets {
                 type uint64;
                 description "Macsec hit dropped packets received on a security channel";
               }
               leaf invalid-packets {
                 type uint64;
                 description "Macsec invalid packets accepted on a security channel";
               }
               leaf late-packets {
                 type uint64;
                 description "Macsec late packets dropped on a security channel";
               }
               leaf delayed-packets {
                 type uint64;
                 description "Macsec delayed packets accepted on a security channel";
               }
               leaf unchecked-packets {
                 type uint64;
                 description "Macsec unchecked packets accepted on a security channel";
               }
               leaf notvalid-packets {
                 type uint64;
                 description "Macsec not valid packets dropped on a security channel";
               }
               leaf notusing-sa-packets {
                 type uint64;
                 description "Macsec not using sa packets received on a security channel";
               }
               leaf unused-sa-packets {
                 type uint64;
                 description "Macsec unused sa packets received on a security channel";
               }
               leaf untagged-hit-packets {
                 type uint64;
                 description "Macsec untagged hit packets received on a secure channel";
               }
             }
           }
         }
         container lag-traffic-statistics {
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           list if-distribution-list-information {
           }
         }
         container layer2-input-policer-statistics {
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container layer2-output-policer-statistics {
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container mac-policer-information {
           container ether-policer-list {
           }
         }
       }
     }
     container interface-policer-information {
       list physical-interface {
         leaf name {
           type string;
           description "Name of this item";
         }
         leaf admin-status {
           type string;
           description "Desired state of the interface";
         }
         leaf oper-status {
           type string;
           description "Current operational state of the interface";
         }
         leaf esi-source-bmac {
           type jt:mac-addr;
           description "Ethernet segment source B-MAC for this interface";
         }
         leaf sonet-payload-pointer-curptr {
           type string;
           description "Value of the SONET/SDH payload pointer, derived from the H1 and H2 overhead bytes";
         }
         leaf sonet-payload-pointer-ptrinc-count {
           type string;
           description "Number of times the value of the SONET/SDH payload pointer had positive justification";
         }
         leaf sonet-payload-pointer-ptrdec-count {
           type string;
           description "Number of times the value of the SONET/SDH payload pointer had negative justification";
         }
         leaf sonet-payload-pointer-newptr-ndf-count {
           type string;
           description "Number of times a new payload pointer was created with the New Data Found flag set";
         }
         leaf link-partner-status {
           type string;
           description "Auto-negotiation status of link partner";
         }
         container optics-properties {
           leaf wavelength {
             type string;
             description "Wavelength of optics in nanometers";
           }
           leaf frequency {
             type string;
             description "Frequency of optics in terahertz";
           }
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container voq-counters {
           leaf voq-counters-error-message {
             type string;
             description "VOQ statistics not available for this interface";
           }
           container voq {
             container fpc {
               leaf fpc-no {
                 type int32;
                 description "FPC number";
               }
               container pfe {
                 leaf-list pfe-no {
                   type int32;
                   description "PFE number";
                 }
                 leaf voq-counters-tail-drop-packets {
                   type int32;
                   description "Tail DROP packet count";
                 }
                 leaf voq-counters-tail-drop-packets-rate {
                   type int32;
                   description "Rate at which tail packets are dropped";
                 }
                 leaf voq-counters-tail-drop-bytes {
                   type int32;
                   description "Tail DROP bytes count";
                 }
                 leaf voq-counters-tail-drop-bytes-rate {
                   type int32;
                   description "Rate at which tail bytes are dropped";
                 }
                 leaf voq-counters-drop-packets {
                   type int32;
                   description "DROP packet count";
                 }
                 leaf voq-counters-drop-packets-rate {
                   type int32;
                   description "Rate at which packets are dropped";
                 }
                 leaf voq-counters-drop-bytes {
                   type int32;
                   description "DROP bytes count";
                 }
                 leaf voq-counters-drop-bytes-rate {
                   type int32;
                   description "Rate at which bytes are dropped";
                 }
               }
             }
             leaf queue-number {
               type int32;
               description "Queue number";
             }
             leaf forwarding-class-name {
               type string;
               description "Forwarding class name associated with queue";
             }
           }
         }
         container smart-sfp-av-titan-statistics {
           leaf smart-sfp-av-titan-error-message {
             type string;
             description "AV Smart SFP un-available";
           }
           container smart-sfp-av-titan-eth-port-statistics {
             leaf rx-crct-frames {
               type uint32;
             }
             leaf rx-crct-bytes {
               type uint32;
             }
             leaf rx-fragments {
               type uint32;
             }
             leaf rx-crct-unicast-frames {
               type uint32;
             }
             leaf rx-crct-multicast-frames {
               type uint32;
             }
             leaf rx-crct-broadcast-frames {
               type uint32;
             }
             leaf rx-err-fcs-frames {
               type uint32;
             }
             leaf rx-len-err-frames {
               type uint32;
             }
             leaf rx-undersize-frames {
               type uint32;
             }
             leaf rx-oversize-frames {
               type uint32;
             }
             leaf rx-inv-vlan-mismatch-frames {
               type uint32;
             }
             leaf rx-discarded-frames {
               type uint32;
             }
             leaf rx-dropped-q-overflow-frames {
               type uint32;
             }
             leaf tx-frames {
               type uint32;
             }
             leaf tx-bytes {
               type uint32;
             }
             leaf tx-unicast-frames {
               type uint32;
             }
             leaf tx-multicast-frames {
               type uint32;
             }
             leaf tx-broadcast-frames {
               type uint32;
             }
           }
           container smart-sfp-av-titan-iwf-statistics {
             leaf rx-packets {
               type uint32;
             }
             leaf tx-packets {
               type uint32;
             }
             leaf malformed-packets {
               type uint32;
             }
             leaf reordered-packets {
               type uint32;
             }
             leaf misordered-dropped-packets {
               type uint32;
             }
             leaf missing-packets {
               type uint32;
             }
             leaf played-out-packets {
               type uint32;
             }
             leaf jb-overrun {
               type uint32;
             }
             leaf jb-underrun {
               type uint32;
             }
           }
           container smart-sfp-av-titan-ds3-statistics {
             leaf rx-bpvexzerrors {
               type uint32;
             }
             leaf rx-cvperrors {
               type uint32;
             }
             leaf b3-errors {
               type uint32;
             }
           }
           container smart-sfp-av-titan-stm-statistics {
             leaf rx-b1-errors {
               type uint32;
             }
             leaf tx-b1-errors {
               type uint32;
             }
           }
         }
         container smart-sfp-av-titan-defects {
           container smart-sfp-av-titan-defect-list {
             leaf sfp-tdm-defects {
               type string;
             }
             leaf sfp-system-defects {
               type string;
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container optics-bit-rate {
           leaf bit-rate {
             type string;
             description " Optics Bit Rate";
           }
         }
         container optics-fec-statistics {
           leaf fec-corrected-errors {
             type int32;
           }
           leaf fec-valid-time {
             type int32;
           }
           leaf fec-corrected-error-ratio {
             type int32;
           }
           leaf fec-uncorrected-words {
             type int32;
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container active-alarms {
         }
         container active-defects {
         }
         container media-state-information {
         }
         container sonet-errors {
           list media-alarm {
             leaf media-alarm-name {
               type string;
             }
             leaf media-alarm-count {
               type int32;
             }
           }
         }
         container sonet-physical-information {
           list media-alarm {
             leaf media-alarm-name {
               type string;
             }
             leaf media-alarm-seconds {
               type int32;
             }
             leaf media-alarm-count {
               type int32;
             }
             leaf media-alarm-state {
               type string;
             }
           }
         }
         container sonet-section-information {
           list media-alarm {
             leaf media-alarm-name {
               type string;
             }
             leaf media-alarm-seconds {
               type int32;
             }
             leaf media-alarm-count {
               type int32;
             }
             leaf media-alarm-state {
               type string;
             }
           }
         }
         container sonet-line-information {
           list media-alarm {
             leaf media-alarm-name {
               type string;
             }
             leaf media-alarm-seconds {
               type int32;
             }
             leaf media-alarm-count {
               type int32;
             }
             leaf media-alarm-state {
               type string;
             }
           }
         }
         container sonet-path-information {
           list media-alarm {
             leaf media-alarm-name {
               type string;
             }
             leaf media-alarm-seconds {
               type int32;
             }
             leaf media-alarm-count {
               type int32;
             }
             leaf media-alarm-state {
               type string;
             }
           }
         }
         container sonet-vt-information {
           list media-alarm {
             leaf media-alarm-name {
               type string;
             }
             leaf media-alarm-seconds {
               type int32;
             }
             leaf media-alarm-count {
               type int32;
             }
             leaf media-alarm-state {
               type string;
             }
           }
         }
         container otn-errors {
           list media-alarm {
             leaf media-alarm-name {
               type string;
             }
             leaf media-alarm-count {
               type int32;
             }
           }
         }
         container otn-fec-statistics {
           leaf fec-corrected-errors {
             type int32;
           }
           leaf fec-valid-time {
             type int32;
           }
           leaf fec-corrected-error-ratio {
             type int32;
           }
           leaf fec-uncorrected-words {
             type int32;
           }
         }
         container otn-fec-alarms {
           list media-alarm {
             leaf media-alarm-name {
               type string;
             }
             leaf media-alarm-seconds {
               type int32;
             }
             leaf media-alarm-count {
               type int32;
             }
             leaf media-alarm-state {
               type string;
             }
           }
         }
         container otn-fec-mode {
           leaf fec-mode {
             type string;
             description "Optics FEC mode";
           }
         }
         container otn-otn-mode {
           leaf otn-mode {
             type string;
           }
         }
         container otn-otn-rate {
           leaf otn-rate {
             type string;
           }
         }
         container otn-otn-loopback {
           leaf otn-loopback {
             type string;
           }
         }
         container otn-local-loopback {
           leaf local-loopback {
             type string;
           }
         }
         container otn-payload-prbs {
           leaf payload-prbs {
             type string;
           }
         }
         container otn-laser-enable {
           leaf laser-enable {
             type string;
             description "Optics laser status";
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         container ethernet-pcs-statistics {
           leaf bit-error-seconds {
             type int32;
             description "Bit error duration";
           }
           leaf errored-blocks-seconds {
             type int32;
             description "Errored blocks duration";
           }
         }
         container ethernet-fec-mode {
           leaf enabled_fec_mode {
             type string;
             description "Enabled FEC mode: <NONE/FEC74/FEC91/FEC108>";
           }
         }
         container ethernet-fec-statistics {
           leaf fec_ccw_count {
             type int32;
             description "FEC Corrected Error Count";
           }
           leaf fec_nccw_count {
             type int32;
             description "FEC Uncorrected Error Count";
           }
           leaf fec_ccw_error_rate {
             type int32;
             description "FEC Corrected Error Rate (errors/sec)";
           }
           leaf fec_nccw_error_rate {
             type int32;
             description "FEC Uncorrected Error Rate (errors/sec)";
           }
         }
         container ctle {
           leaf ctle_value {
             type int32;
             description "Ctle value";
           }
         }
         container pre-emphasis {
           leaf pre_emphasis_value {
             type int32;
             description "Pre-emphasis value";
           }
         }
         container differential-amplitude {
           leaf differential_amplitude_value {
             type int32;
             description "Differential-amplitude value";
           }
         }
         container ethernet-mac-statistics {
           leaf input-bytes {
             type int32;
           }
           leaf input-packets {
             type int32;
           }
           leaf output-bytes {
             type int32;
           }
           leaf output-packets {
             type int32;
           }
           leaf input-undersized-frames {
             type int32;
           }
           leaf input-unicasts {
             type int32;
           }
           leaf output-unicasts {
             type int32;
           }
           leaf input-broadcasts {
             type int32;
           }
           leaf output-broadcasts {
             type int32;
           }
           leaf input-multicasts {
             type int32;
           }
           leaf output-multicasts {
             type int32;
           }
           leaf input-crc-errors {
             type int32;
           }
           leaf output-crc-errors {
             type int32;
           }
           leaf input-fifo-errors {
             type int32;
           }
           leaf output-fifo-errors {
             type int32;
           }
           leaf input-dma-errors {
             type int32;
           }
           leaf output-dma-errors {
             type int32;
           }
           leaf input-mac-control-frames {
             type int32;
           }
           leaf output-mac-control-frames {
             type int32;
           }
           leaf input-mac-pause-frames {
             type int32;
           }
           leaf output-mac-pause-frames {
             type int32;
           }
           leaf input-oversized-frames {
             type int32;
           }
           leaf input-jabber-frames {
             type int32;
           }
           leaf input-fragment-frames {
             type int32;
           }
           leaf input-vlan-tagged-frames {
             type int32;
           }
           leaf input-code-violations {
             type int32;
           }
           leaf input-total-errors {
             type int32;
           }
           leaf output-total-errors {
             type int32;
           }
           leaf input-policer-frame-drops {
             type int32;
           }
           leaf input-policer-byte-drops {
             type int32;
           }
         }
         container ethernet-prbs-mode {
           leaf prbs-mode {
             type string;
             description "PRBS Mode: <Enabled/Disabled>";
           }
         }
         container ethernet-prbs-statistics {
           leaf prbs-lane {
             type int32;
             description "PRBS Lane";
           }
           leaf prbs-state {
             type string;
             description "PRBS State";
           }
           leaf prbs-error-count {
             type int32;
             description "PRBS Error Count";
           }
         }
         container smart-sfp-configurable-type {
           leaf smart-sfp-tdm-management {
             type string;
           }
         }
         container smart-sfp-type {
           leaf smart-sfp-module-type {
             type string;
           }
           leaf smart-sfp-present {
             type string;
           }
         }
         container smart-sfp-config {
           leaf tdm-loopback {
             type string;
           }
           leaf dmac-check-enable {
             type string;
           }
           leaf encap-ecid {
             type int32;
           }
           leaf decap-ecid {
             type int32;
           }
           leaf vlan-id-1 {
             type int32;
           }
           leaf vlan-id-2 {
             type int32;
           }
           leaf mode {
             type string;
           }
           leaf chan-dmac {
             type jt:mac-addr;
           }
         }
         container smart-sfp-oc3-statistics {
           leaf fcs-error-count {
             type uint32;
           }
           leaf sec-sefs {
             type uint32;
           }
           leaf sec-es {
             type uint32;
           }
           leaf sec-es-min15 {
             type uint32;
           }
           leaf sec-ses {
             type uint32;
           }
           leaf sec-ses-min15 {
             type uint32;
           }
           leaf sec-cv {
             type uint32;
           }
           leaf sec-cv-min15 {
             type uint32;
           }
           leaf line-es {
             type uint32;
           }
           leaf line-es-min15 {
             type uint32;
           }
           leaf line-ses {
             type uint32;
           }
           leaf line-ses-min15 {
             type uint32;
           }
           leaf line-cv {
             type uint32;
           }
           leaf line-cv-min15 {
             type uint32;
           }
           leaf line-uas {
             type uint32;
           }
           leaf line-uas-min15 {
             type uint32;
           }
           leaf path-es {
             type uint32;
           }
           leaf path-es-min15 {
             type uint32;
           }
           leaf path-ses {
             type uint32;
           }
           leaf path-ses-min15 {
             type uint32;
           }
           leaf path-cv {
             type uint32;
           }
           leaf path-cv-min15 {
             type uint32;
           }
           leaf path-uas {
             type uint32;
           }
           leaf path-uas-min15 {
             type uint32;
           }
         }
         container smart-sfp-e1t1-statistics {
           leaf e1t1-es {
             type uint32;
           }
           leaf e1t1-es-min15 {
             type uint32;
           }
           leaf e1t1-ses {
             type uint32;
           }
           leaf e1t1-ses-min15 {
             type uint32;
           }
           leaf e1t1-uas {
             type uint32;
           }
           leaf e1t1-uas-min15 {
             type uint32;
           }
           leaf e1t1-bes {
             type uint32;
           }
           leaf e1t1-bes-min15 {
             type uint32;
           }
           leaf e1t1-les {
             type uint32;
           }
           leaf e1t1-les-min15 {
             type uint32;
           }
           leaf e1t1-pes {
             type uint32;
           }
           leaf e1t1-pes-min15 {
             type uint32;
           }
           leaf e1t1-psess {
             type uint32;
           }
           leaf e1t1-psess-min15 {
             type uint32;
           }
           leaf e1t1-ces {
             type uint32;
           }
           leaf e1t1-ces-min15 {
             type uint32;
           }
           leaf e1t1-cses {
             type uint32;
           }
           leaf e1t1-cses-min15 {
             type uint32;
           }
           leaf e1t1-sefs {
             type uint32;
           }
           leaf e1t1-sefs-min15 {
             type uint32;
           }
         }
         container smart-sfp-e3t3-statistics {
           leaf e3t3-les {
             type uint32;
           }
           leaf e3t3-les-min15 {
             type uint32;
           }
           leaf e3t3-pes {
             type uint32;
           }
           leaf e3t3-pes-min15 {
             type uint32;
           }
           leaf e3t3-psess {
             type uint32;
           }
           leaf e3t3-psess-min15 {
             type uint32;
           }
           leaf e3t3-ces {
             type uint32;
           }
           leaf e3t3-ces-min15 {
             type uint32;
           }
           leaf e3t3-cses {
             type uint32;
           }
           leaf e3t3-cses-min15 {
             type uint32;
           }
           leaf e3t3-sefs {
             type uint32;
           }
           leaf e3t3-sefs-min15 {
             type uint32;
           }
           leaf e3t3-uas {
             type uint32;
           }
           leaf e3t3-uas-min15 {
             type uint32;
           }
         }
         container fibrechannel-port-flow-control {
           leaf fibrechannel-port-flow-control-mode {
             type string;
           }
           list fibrechannel-port-flow-control-credits {
             leaf fibrechannel-port-flow-control-credits-subject {
               type string;
             }
             leaf fibrechannel-port-flow-control-credits-assigned {
               type uint64;
             }
             leaf fibrechannel-port-flow-control-credits-available {
               type uint64;
             }
           }
         }
         container fibrechannel-mac-statistics {
           container fibrechannel-mac-statistics-generic {
             leaf link-failures {
               type uint64;
             }
             leaf loss-of-sync {
               type uint64;
             }
             leaf loss-of-signal {
               type uint64;
             }
             leaf sw-link-resets {
               type uint64;
             }
             leaf buffer-to-buffer-credit-recovery-lost-frames {
               type uint64;
             }
             leaf buffer-to-buffer-credit-recovery-lost-rrdys {
               type uint64;
             }
           }
           container fibrechannel-mac-statistics-received {
             leaf rx-class-2-frames {
               type uint64;
             }
             leaf rx-class-2-octets {
               type uint64;
             }
             leaf rx-class-3-frames {
               type uint64;
             }
             leaf rx-class-3-octets {
               type uint64;
             }
             leaf rx-class-f-frames {
               type uint64;
             }
             leaf rx-class-f-octets {
               type uint64;
             }
             leaf class-2-discards {
               type uint64;
             }
             leaf class-3-discards {
               type uint64;
             }
             leaf class-f-discards {
               type uint64;
             }
             leaf rx-frames-too-long {
               type uint64;
             }
             leaf rx-frames-too-short {
               type uint64;
             }
             leaf rx-missing-eof {
               type uint64;
             }
             leaf rx-invalid-crcs {
               type uint64;
             }
             leaf rx-link-resets {
               type uint64;
             }
             leaf rx-link-reset-responses {
               type uint64;
             }
             leaf rx-offlines {
               type uint64;
             }
             leaf rx-not-operationals {
               type uint64;
             }
             leaf rx-invalid-tx-words {
               type uint64;
             }
             leaf rx-encoding-disparity-errors {
               type uint64;
             }
             leaf rx-delimiter-errors {
               type uint64;
             }
             leaf rx-input-buffers-full {
               type uint64;
             }
             leaf rx-invalid-ordered-sets {
               type uint64;
             }
             leaf rx-prim-seq-protocol-errors {
               type uint64;
             }
             leaf rx-other-errors {
               type uint64;
             }
           }
           container fibrechannel-mac-statistics-transmitted {
             leaf tx-class-2-frames {
               type uint64;
             }
             leaf tx-class-2-octets {
               type uint64;
             }
             leaf tx-class-3-frames {
               type uint64;
             }
             leaf tx-class-3-octets {
               type uint64;
             }
             leaf tx-class-f-frames {
               type uint64;
             }
             leaf tx-class-f-octets {
               type uint64;
             }
             leaf tx-link-resets {
               type uint64;
             }
             leaf tx-link-reset-responses {
               type uint64;
             }
             leaf tx-offlines {
               type uint64;
             }
             leaf tx-not-operationals {
               type uint64;
             }
             leaf tx-bb-credit-zeroes {
               type uint64;
             }
             leaf tx-other-errors {
               type uint64;
             }
           }
         }
         container ethernet-filter-statistics {
           leaf input-reject-count {
             type int32;
           }
           leaf output-packet-pad-count {
             type int32;
           }
           leaf output-packet-error-count {
             type int32;
           }
           leaf input-packets {
             type int32;
           }
           leaf input-reject-destination-address-count {
             type int32;
           }
           leaf input-reject-source-address-count {
             type int32;
           }
           leaf output-packets {
             type int32;
           }
           leaf cam-destination-filter-count {
             type int32;
           }
           leaf cam-source-filter-count {
             type int32;
           }
         }
         container ethernet-autonegotiation {
         }
         container mac-database {
         }
         container dsl-information {
           container dsl-statistics {
             leaf interleaved-rx-cells {
               type int32;
               description "Interleaved receiver cells";
             }
             leaf fast-rx-cells {
               type int32;
               description "Fast receiver cells";
             }
             leaf interleaved-tx-cells {
               type int32;
               description "Interleaved transmitter cells";
             }
             leaf fast-tx-cells {
               type int32;
               description "Fast transmitter cells";
             }
           }
         }
         container vdsl-information {
         }
         container shdsl-information {
         }
         container efm-information {
           container efm-line-statistics {
             container active-alarms-efm {
             }
             container active-defects-efm {
             }
             container media-information {
               leaf media-type {
                 type string;
                 description "Type of media this information is for";
               }
               list media-alarm {
                 leaf media-alarm-name {
                   type string;
                 }
                 leaf media-alarm-count {
                   type int32;
                 }
                 leaf media-alarm-seconds {
                   type int32;
                 }
                 leaf media-alarm-state {
                   type string;
                 }
                 leaf ce-counter-name {
                   type string;
                   description "Circuit Emulation counter information";
                 }
                 leaf ce-counter-packets {
                   type int32;
                   description "Circuit Emulation number of packets";
                 }
                 leaf ce-counter-bytes {
                   type int32;
                   description "Circuit Emulation number of bytes";
                 }
                 leaf ce-counter-count {
                   type int32;
                   description "Circuit Emulation number of event occurrences";
                 }
               }
               leaf ds1-timeslots {
                 type string;
               }
               leaf ds1-line-encoding {
                 type string;
               }
               leaf ds1-byte-encoding {
                 type string;
               }
               leaf ds1-data-inversion {
                 type string;
               }
               leaf idle-cycle-flag {
                 type string;
               }
               leaf start-end-flag {
                 type string;
               }
               leaf ds0-byte-encoding {
                 type string;
               }
               leaf ds0-data-inversion {
                 type string;
               }
               leaf e3-data-inversion {
                 type string;
               }
               leaf ds1-buildout {
                 type string;
                 description "Number of feet";
               }
             }
             container shdsl-information {
             }
           }
         }
         container atm-information {
           container plcp-defects {
           }
           container atm-defects {
           }
         }
         container serial-information {
           leaf dce-loopback-override {
             type string;
           }
           container eia530-control-signal {
           }
         }
         container virtual-path-information {
           leaf cdvt {
             type int32;
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
         }
         container ct3-information {
           list interface-tx-queue {
             leaf output-drops-bytes {
               type int32;
             }
           }
         }
         container cds1-information {
           list interface-tx-queue {
             leaf output-drops-bytes {
               type int32;
             }
           }
         }
         container nxds0-information {
           list interface-tx-queue {
             leaf output-drops-bytes {
               type int32;
             }
           }
         }
         list logical-interface {
           leaf name {
             type string;
             description "Name of this item";
           }
           leaf admin-status {
             type string;
             description "Desired state of the interface";
           }
           leaf oper-status {
             type string;
             description "Current operational state of the interface";
           }
           leaf vrfname {
             type string;
             description "Routing instance name";
           }
           leaf zonename {
             type string;
             description "Zone name";
           }
           leaf subunit {
             type int32;
             description "Subunit for this interface";
           }
           leaf dialer-time-to-disconnect {
             type string;
             description "Time for dialer to disconnect due to idle timeout";
           }
           leaf lcp-state {
             type string;
             description "State of the Line Control Protocol";
           }
           leaf chap-state {
             type string;
             description "State of the Challenge Handshake Authentication Protocol";
           }
           leaf pap-state {
             type string;
             description "State of the Password Authentication Protocol";
           }
           container layer2-input-policer-information {
             leaf layer2-input-policer {
               type string;
               description "Name of the Layer 2 input policer";
             }
           }
           container layer2-output-policer-information {
             leaf layer2-output-policer {
               type string;
               description "Name of the Layer 2 output policer";
             }
           }
           container pppoe-information {
             list pppoe-interface {
               leaf state {
                 type string;
                 description "State";
               }
               leaf session-id {
                 type string;
                 description "Session ID";
               }
               leaf ac-name-session {
                 type string;
                 description "Session AC name";
               }
               leaf remote-mac {
                 type string;
                 description "Remote MAC address";
               }
               leaf ac-name-config {
                 type string;
                 description "Configured AC name";
               }
               leaf service-name {
                 type string;
                 description "Service name";
               }
               leaf auto-reconnect {
                 type string;
                 description "Autoreconnect timeout";
               }
               leaf idle-timeout {
                 type string;
                 description "Idle timeout";
               }
               leaf underlying-interface-name {
                 type string;
                 description "Underlying interface name";
               }
               leaf underlying-interface-index {
                 type string;
                 description "Underlying interface index";
               }
               leaf padg-credits {
                 type int32;
                 description "PADG transmit credits";
               }
               leaf pppoe-credit-scale-factor {
                 type string;
                 description "Scaling factor";
               }
               leaf ignore-eol-tag {
                 type string;
                 description "Ignore End-of-List TAG";
               }
               leaf ppp-max-payload-tag {
                 type int32;
                 description "PPP-Max-Payload TAG";
               }
               leaf interface-name {
                 type string;
                 description "Class-of-service interface name";
               }
               leaf interface-index {
                 type uint32;
                 description "Class-of-service interface index";
               }
               leaf aci-iflset-name {
                 type string;
                 description "ACI Interface Set name";
               }
               leaf aci-iflset-index {
                 type string;
                 description "ACI Interface Set index";
               }
               leaf ifl-type {
                 type string;
                 description "Type";
               }
               leaf session-uptime {
                 type string;
                 description "Duration for which the session has been up";
               }
               leaf dynamic-profile {
                 type string;
                 description "Dynamic Profile name";
               }
               leaf pppoe-credits {
                 type string;
                 description "Forwarding credit balances";
               }
               leaf dynamic-interface-bandwidth {
                 type string;
                 description "Dynamic interface bandwidth";
               }
               leaf agent-circuit-id {
                 type string;
                 description "Agent Circuit ID";
               }
               leaf agent-remote-id {
                 type string;
                 description "Agent Remote ID";
               }
               leaf padm-motm {
                 type string;
                 description "PADM Message of the Moment tag";
               }
               leaf padm-hurl {
                 type string;
                 description "PADM HTTP URL tag";
               }
             }
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           container aci-vlan-information {
             leaf dynamic-profile {
               type string;
               description "Dynamic Profile name";
             }
           }
           container line-identity-information {
             leaf dynamic-profile {
               type string;
               description "Dynamic Profile name";
             }
             leaf circuit-id {
               type string;
               description "Aci vlan attribute";
             }
             leaf remote-id {
               type string;
               description "Aci vlan attribute";
             }
             leaf accept-no-ids {
               type string;
               description "Aci vlan attribute";
             }
           }
           container demux-information {
             container demux-interface {
               leaf demux-underlying-interface-name {
                 type string;
                 description "Underlying interface name";
               }
               leaf demux-underlying-interface-index {
                 type string;
                 description "Underlying interface index";
               }
               leaf demux-inet-prefix-type {
                 type string;
                 description "Prefix type";
               }
               leaf demux-inet-prefix-count {
                 type string;
                 description "IPv4 Prefix count";
               }
               leaf demux-inet-prefix {
                 type string;
                 description "IPv4 Prefix";
               }
               leaf demux-inet6-prefix-type {
                 type string;
                 description "Prefix type";
               }
               leaf demux-inet6-prefix-count {
                 type string;
                 description "IPv6 Prefix count";
               }
               leaf demux-inet6-prefix {
                 type string;
                 description "IPv6 Prefix";
               }
             }
           }
           container dual-ad-icl-color-information {
             container dual-ad-icl-color-info {
               leaf dual-ad-icl-color-type {
                 type uint32;
                 description "Dual-AD ICL Color Type";
               }
               leaf dual-ad-icl-color {
                 type uint32;
                 description "Dual-AD ICL Color";
               }
             }
           }
           container dialer-information {
             leaf dialer-time-to-disconnect {
               type string;
               description "Time for dialer to disconnect due to idle timeout";
             }
             container dialer-interface {
               leaf dialer-interface-name {
                 type string;
                 description "Interface name";
               }
               leaf dialer-interface-state {
                 type string;
                 description "Dialer interface state";
               }
               leaf pool-id {
                 type string;
                 description "Pool identifier";
               }
               leaf primary-interface {
                 type string;
                 description "Primary interface";
               }
               leaf activation-delay {
                 type string;
                 description "Activation delay";
               }
               leaf deactivation-delay {
                 type string;
                 description "Deactivation delay";
               }
               leaf activation-delay-elapsed {
                 type string;
                 description "Activation delay elapsed";
               }
               leaf deactivation-delay-elapsed {
                 type string;
                 description "Deactivation delay elapsed";
               }
               leaf call-idle-timeout {
                 type string;
                 description "Call idle timeout";
               }
               leaf initial-route-check {
                 type string;
                 description "Initial route check delay";
               }
               leaf redial-delay {
                 type string;
                 description "Delay before dialer dials out again (seconds)";
               }
               leaf callback-wait-period {
                 type string;
                 description "Delay before dialer attempts callback (seconds)";
               }
               leaf callback-wait-period-elapsed {
                 type string;
                 description "Number of seconds in callback wait period that have elapsed";
               }
               leaf load-threshold {
                 type string;
                 description "Load threshold that determines when interfaces are added to bundle";
               }
               leaf load-interval {
                 type string;
                 description "Interval over which average load is calculated";
               }
               container dialer-interface-flags {
                 leaf backup {
                   type empty;
                   description "Dialer backup";
                 }
                 leaf multilink {
                   type empty;
                   description "Dialer multilink";
                 }
                 leaf watchlist {
                   type empty;
                   description "Dialer watchlist";
                 }
                 leaf interesting-detected {
                   type empty;
                   description "Interesting packet detected";
                 }
               }
             }
           }
           container shared-interface-information {
             container shared-interface-logical-interface {
               leaf peer-interface-name {
                 type string;
                 description "Peer interface name";
               }
               leaf interface-shared-with {
                 type string;
                 description "Logical interface owner";
               }
               leaf rx-fe {
                 type string;
                 description "Rx tunnel token forwarding element";
               }
               leaf rx-nhid {
                 type string;
                 description "Rx tunnel token next hop index";
               }
               leaf tx-fe {
                 type string;
                 description "Tx tunnel token forwarding element";
               }
               leaf tx-nhid {
                 type string;
                 description "Tx tunnel token next hop index";
               }
             }
           }
           container mac-database {
           }
           container queue-counters {
             leaf queue-counters-error-message {
               type string;
               description "Queue statistics not available for this interface";
             }
             list queue {
               leaf queue-number {
                 type int32;
                 description "Queue number";
               }
               leaf queue-counters-queued-packets {
                 type uint64;
                 description "Queued packet count";
               }
               leaf queue-counters-trans-packets {
                 type uint64;
                 description "Total number of transmitted packets";
               }
               leaf queue-counters-total-drop-packets {
                 type uint64;
                 description "Number of total packets dropped at the queue";
               }
               leaf forwarding-class-name {
                 type string;
                 description "Forwarding class name associated with queue";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
           }
           container ingress-queue-counters {
             list queue {
               leaf queue-number {
                 type int32;
                 description "Queue number";
               }
               leaf forwarding-class-name {
                 type string;
                 description "Forwarding class name associated with queue";
               }
               leaf queue-counters-queued-packets {
                 type uint64;
                 description "Queued packet count";
               }
               leaf queue-counters-queued-packets-rate {
                 type uint64;
                 description "Rate at which packets are queued";
               }
               leaf queue-counters-queued-bytes {
                 type uint64;
                 description "Queued bytes count";
               }
               leaf queue-counters-queued-bytes-rate {
                 type uint64;
                 description "Rate at which bytes are queued";
               }
               leaf queue-counters-queued-packets-na {
                 type string;
                 description "Queued packets not available";
               }
               leaf queue-counters-queued-bytes-na {
                 type string;
                 description "Queued bytes not available";
               }
               leaf queue-counters-trans-packets {
                 type uint64;
                 description "Total number of transmitted packets";
               }
               leaf queue-counters-trans-packets-rate {
                 type uint64;
                 description "Rate at which packets are transmitted";
               }
               leaf queue-counters-trans-bytes {
                 type uint64;
                 description "Total number of transmitted bytes";
               }
               leaf queue-counters-trans-bytes-rate {
                 type uint64;
                 description "Rate at which bytes are transmitted";
               }
               leaf queue-counters-tail-drop-packets-na {
                 type string;
                 description "Number of packets dropped due to tail drop not available";
               }
               leaf queue-counters-tail-drop-packets {
                 type uint64;
                 description "Number of packets dropped at the tail of the queue";
               }
               leaf queue-counters-tail-drop-packets-rate {
                 type uint64;
                 description "Rate at which packets are dropped at tail of queue";
               }
               leaf queue-counters-tail-drop-bytes {
                 type uint64;
                 description "Number of packets dropped at tail drop of the queue";
               }
               leaf queue-counters-tail-drop-bytes-rate {
                 type uint64;
                 description "Number of packets dropped at tail drop of the queue";
               }
               leaf queue-counters-rate-limit-drop-packets-na {
                 type string;
                 description "Number of packets dropped due to rate-limit drop not available";
               }
               leaf queue-counters-rate-limit-drop-packets {
                 type uint64;
                 description "Number of packets dropped by rate-limit for the queue";
               }
               leaf queue-counters-rate-limit-drop-packets-rate {
                 type uint64;
                 description "Rate at which packets are dropped by rate-limit for the queue";
               }
               leaf queue-counters-rate-limit-drop-bytes-na {
                 type string;
                 description "Number of bytes dropped due to tail drop not available";
               }
               leaf queue-counters-rate-limit-drop-bytes {
                 type uint64;
                 description "Number of bytes dropped at the tail of the queue";
               }
               leaf queue-counters-rate-limit-drop-bytes-rate {
                 type uint64;
                 description "Rate at which bytes are dropped at the tail of the queue";
               }
               leaf queue-counters-red-packets-na {
                 type string;
                 description "Number of packets dropped due to RED not available";
               }
               leaf queue-counters-red-packets {
                 type uint64;
                 description "Number of packets dropped due to RED";
               }
               leaf queue-counters-red-packets-rate {
                 type uint64;
                 description "Rate at which packets are dropped due to RED";
               }
               leaf queue-counters-red-packets-ln {
                 type uint64;
                 description "Number of RED dropped low-loss, non-TCP packets";
               }
               leaf queue-counters-red-packets-rate-ln {
                 type uint64;
                 description "RED drop rate for low-loss, non-TCP packets";
               }
               leaf queue-counters-red-packets-lt {
                 type uint64;
                 description "Number of RED dropped of low-loss, TCP packets";
               }
               leaf queue-counters-red-packets-rate-lt {
                 type uint64;
                 description "RED drop rate for low-loss, TCP packets";
               }
               leaf queue-counters-red-packets-hn {
                 type uint64;
                 description "Number of RED dropped high-loss, non-TCP packets";
               }
               leaf queue-counters-red-packets-rate-hn {
                 type uint64;
                 description "RED drop rate for high-loss, non-TCP packets";
               }
               leaf queue-counters-red-packets-ht {
                 type uint64;
                 description "Number of RED dropped high-loss, TCP packets";
               }
               leaf queue-counters-red-packets-rate-ht {
                 type uint64;
                 description "RED drop rate for high-loss, TCP packets";
               }
               leaf queue-counters-red-packets-low {
                 type uint64;
                 description "Number of RED dropped low-loss packets";
               }
               leaf queue-counters-red-packets-rate-low {
                 type uint64;
                 description "RED drop rate for low-loss packets";
               }
               leaf queue-counters-red-packets-medium-low {
                 type uint64;
                 description "Number of RED dropped medium-low-loss packets";
               }
               leaf queue-counters-red-packets-rate-medium-low {
                 type uint64;
                 description "RED drop rate for medium-low-loss packets";
               }
               leaf queue-counters-red-packets-medium-high {
                 type uint64;
                 description "Number of RED dropped medium-high-loss packets";
               }
               leaf queue-counters-red-packets-rate-medium-high {
                 type uint64;
                 description "RED drop rate for medium-high-loss packets";
               }
               leaf queue-counters-red-packets-medium {
                 type uint64;
                 description "Number of RED dropped medium-loss packets";
               }
               leaf queue-counters-red-packets-rate-medium {
                 type uint64;
                 description "RED drop rate for medium-loss packets";
               }
               leaf queue-counters-red-packets-high {
                 type uint64;
                 description "Number of RED dropped high-loss packets";
               }
               leaf queue-counters-red-packets-rate-high {
                 type uint64;
                 description "RED drop rate for high-loss packets";
               }
               leaf queue-counters-red-bytes-na {
                 type string;
                 description "Number of bytes dropped due to RED not available";
               }
               leaf queue-counters-red-bytes {
                 type uint64;
                 description "Number of bytes dropped due to RED";
               }
               leaf queue-counters-red-bytes-rate {
                 type uint64;
                 description "Rate at which bytes are dropped due to RED";
               }
               leaf queue-counters-red-bytes-ln {
                 type uint64;
                 description "Number of RED dropped low-loss, non-TCP bytes";
               }
               leaf queue-counters-red-bytes-rate-ln {
                 type uint64;
                 description "RED drop rate for low-loss, non-TCP bytes";
               }
               leaf queue-counters-red-bytes-lt {
                 type uint64;
                 description "Number of RED dropped low-loss, TCP bytes";
               }
               leaf queue-counters-red-bytes-rate-lt {
                 type uint64;
                 description "RED drop rate for low-loss, TCP bytes";
               }
               leaf queue-counters-red-bytes-hn {
                 type uint64;
                 description "Number of RED dropped high-loss, non-TCP bytes";
               }
               leaf queue-counters-red-bytes-rate-hn {
                 type uint64;
                 description "RED drop rate for high-loss, non-TCP bytes";
               }
               leaf queue-counters-red-bytes-ht {
                 type uint64;
                 description "Number of RED dropped high-loss, TCP bytes";
               }
               leaf queue-counters-red-bytes-rate-ht {
                 type uint64;
                 description "RED drop rate for high-loss, TCP bytes";
               }
               leaf queue-counters-red-bytes-low {
                 type uint64;
                 description "Number of RED dropped low-loss bytes";
               }
               leaf queue-counters-red-bytes-rate-low {
                 type uint64;
                 description "RED drop rate for low-loss bytes";
               }
               leaf queue-counters-red-bytes-medium-low {
                 type uint64;
                 description "Number of RED dropped medium-low-loss bytes";
               }
               leaf queue-counters-red-bytes-rate-medium-low {
                 type uint64;
                 description "RED drop rate for medium-low-loss bytes";
               }
               leaf queue-counters-red-bytes-medium-high {
                 type uint64;
                 description "Number of RED dropped medium-high-loss bytes";
               }
               leaf queue-counters-red-bytes-rate-medium-high {
                 type uint64;
                 description "RED drop rate for medium-high-loss bytes";
               }
               leaf queue-counters-red-bytes-medium {
                 type uint64;
                 description "Number of RED dropped medium-loss bytes";
               }
               leaf queue-counters-red-bytes-rate-medium {
                 type uint64;
                 description "RED drop rate for medium-loss bytes";
               }
               leaf queue-counters-red-bytes-high {
                 type uint64;
                 description "Number of RED dropped high-loss bytes";
               }
               leaf queue-counters-red-bytes-rate-high {
                 type uint64;
                 description "RED drop rate for high-loss bytes";
               }
               leaf queue-counters-timestamp {
                 type uint64;
                 description "Last packet enqueued timestamp";
               }
               leaf queue-counters-total-drop-packets {
                 type uint64;
                 description "Number of total packets dropped at the queue";
               }
               leaf queue-counters-total-drop-packets-rate {
                 type uint64;
                 description "Number of total packets dropped at the queue";
               }
               leaf queue-counters-total-drop-bytes {
                 type uint64;
                 description "Number of total packets dropped at the queue";
               }
               leaf queue-counters-total-drop-bytes-rate {
                 type uint64;
                 description "Number of total packets dropped at the queue";
               }
               leaf queue-counters-reserved-buffer-packets {
                 type int32;
                 description "Queues's usage of reserved buffer pool in pkts";
               }
               leaf queue-counters-reserved-buffer-bytes {
                 type int32;
                 description "Queues's usage of reserved buffer pool in bytes";
               }
               leaf queue-counters-shared-buffer-packets {
                 type int32;
                 description "Queues's usage of shared buffer pool in pkts";
               }
               leaf queue-counters-shared-buffer-bytes {
                 type int32;
                 description "Queues's usage of shared buffer pool in bytes";
               }
               leaf queue-counters-depth-average {
                 type int32;
                 description "Time averaged queue depth";
               }
               leaf queue-counters-depth-current {
                 type int32;
                 description "Current instantaneous queue depth";
               }
               leaf queue-counters-depth-peak {
                 type int32;
                 description "Peak queue depth";
               }
               leaf queue-counters-depth-max {
                 type int32;
                 description "Maximum queue depth attained";
               }
               leaf queue-counters-srx-reserved-buffer-bytes {
                 type int32;
                 description "Queues's usage of reserved buffer pool in bytes";
               }
               leaf queue-counters-srx-depth-current {
                 type int32;
                 description "Current instantaneous queue depth";
               }
             }
             container interface-cos-summary {
               leaf intf-cos-forwarding-classes-supported {
                 type int32;
                 description "Number of forwarding classes supported on this interface";
               }
               leaf intf-cos-forwarding-classes-in-use {
                 type int32;
                 description "Number of forwarding classes currently in use on this interface";
               }
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
               leaf intf-cos-burst-size-for-ifl {
                 type int32;
                 description "Burst size for the logical interface";
               }
             }
             container interface-cos-short-summary {
               leaf intf-cos-queue-type {
                 type string;
                 description "Interface queue type";
               }
               leaf intf-cos-num-queues-supported {
                 type int32;
                 description "Number of queues supported on this interface";
               }
               leaf intf-cos-num-queues-in-use {
                 type int32;
                 description "Number of queues currently in use on this interface";
               }
               leaf intf-cos-queue-dedicated-or-shared {
                 type string;
                 description "Interface has dedicated or shared queues";
               }
               leaf intf-cos-sched-resource-type {
                 type string;
                 description "Interface scheduling resource type";
               }
               leaf intf-cos-sched-resource-usage-mic-limit {
                 type int32;
                 description "MIC/PIC scheduling resource usage limit";
               }
               leaf intf-cos-sched-resource-usage-mic-count {
                 type int32;
                 description "MIC/PIC scheduling resource usage count";
               }
               leaf intf-cos-sched-resource-usage-port-limit {
                 type int32;
                 description "Interface scheduling resource limit";
               }
               leaf intf-cos-sched-resource-usage-port-count {
                 type int32;
                 description "Interface scheduling resource usage";
               }
             }
             container queue-num-forwarding-class-name-map {
               leaf queue-number {
                 type int32;
                 description "Queue number";
               }
               leaf forwarding-class-name {
                 type string;
                 description "Forwarding class name associated with queue";
               }
             }
           }
           container forwarding-class-counters {
             leaf forwarding-class-counters-error-message {
               type string;
               description "Forwarding-class statistics not available for this interface";
             }
             container ipv4-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container ipv6-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container mpls-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container layer2-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container other-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container protocol-aggregate-forwarding-class-counters {
               leaf forwarding-class-stats-type {
                 type string;
               }
               container per-forwarding-class-counters {
                 leaf fc_name_header {
                   type string;
                 }
                 leaf forwarding-class-name {
                   type string;
                   description "Forwarding class name associated with queue";
                 }
                 leaf fc-input-bytes {
                   type int32;
                 }
                 leaf fc-input-bytes-rate {
                   type int32;
                   description "Input bytes rate";
                 }
                 leaf fc-output-bytes {
                   type int32;
                 }
                 leaf fc-output-bytes-rate {
                   type int32;
                   description "Output bytes rate";
                 }
                 leaf fc-input-packets {
                   type int32;
                 }
                 leaf fc-input-packets-rate {
                   type int32;
                   description "Input packets rate";
                 }
                 leaf fc-output-packets {
                   type int32;
                 }
                 leaf fc-output-packets-rate {
                   type int32;
                   description "Output packets rate";
                 }
                 leaf input-unicast-bytes {
                   type int32;
                 }
                 leaf output-unicast-bytes {
                   type int32;
                 }
                 leaf input-unicast-packets {
                   type int32;
                 }
                 leaf output-unicast-packets {
                   type int32;
                 }
                 leaf input-multicast-bytes {
                   type int32;
                 }
                 leaf output-multicast-bytes {
                   type int32;
                 }
                 leaf input-multicast-packets {
                   type int32;
                 }
                 leaf output-multicast-packets {
                   type int32;
                 }
               }
             }
             container forwarding-class-statistics {
               container protocol-aggregate-forwarding-class-counters {
               }
               container ipv4-forwarding-class-counters {
               }
               container ipv6-forwarding-class-counters {
               }
               container mpls-forwarding-class-counters {
               }
               container layer2-forwarding-class-counters {
               }
               container other-forwarding-class-counters {
               }
             }
             container forwarding-class-accounting-parameters {
               leaf forwarding-class-accounting-for-protocol {
                 type string;
               }
               leaf forwarding-class-accounting-for-traffic-direction {
                 type string;
               }
               leaf forwarding-class-accounting-for-traffic-type {
                 type string;
               }
               leaf forwarding-class-accounting-overhead-bytes {
                 type uint32;
               }
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container multilink-bundle-options {
             leaf filler-packet-interval {
               type int32;
             }
           }
           container multilink-traffic-statistics {
             container bundle {
             }
             container class {
             }
             container multilink-detail-statistics {
               container bundle-detail {
               }
               container class-detail {
               }
             }
             container crtp {
               container crtp-sessions {
                 leaf input-frames {
                   type int32;
                 }
                 leaf output-frames {
                   type int32;
                 }
               }
               list crtp-statistics {
                 leaf name {
                   type string;
                   description "Name of this item";
                 }
                 leaf input-frames {
                   type int32;
                 }
                 leaf input-fps {
                   type int32;
                 }
                 leaf input-bytes {
                   type int32;
                 }
                 leaf input-bps {
                   type int32;
                 }
                 leaf output-frames {
                   type int32;
                 }
                 leaf output-fps {
                   type int32;
                 }
                 leaf output-bytes {
                   type int32;
                 }
                 leaf output-bps {
                   type int32;
                 }
               }
             }
           }
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container multicast-statistics {
             leaf multicast-statistics-header {
               type empty;
             }
             container ipv4-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
             container ipv6-multicast-statistics {
               leaf input-bytes {
                 type int32;
               }
               leaf input-bps {
                 type int32;
               }
               leaf output-bytes {
                 type int32;
               }
               leaf output-bps {
                 type int32;
               }
               leaf input-packets {
                 type int32;
               }
               leaf input-pps {
                 type int32;
               }
               leaf output-packets {
                 type int32;
               }
               leaf output-pps {
                 type int32;
               }
             }
           }
           container ingress-traffic-statistics {
             leaf input-bps {
               type int32;
             }
             leaf input-pps {
               type int32;
             }
             leaf input-drop-bps {
               type int32;
               description "Drop rate at ingress in bits per second ";
             }
             leaf input-drop-pps {
               type int32;
               description "Drop rate at ingress in packets per second ";
             }
             leaf input-bytes {
               type int32;
             }
             leaf input-packets {
               type int32;
             }
             leaf input-drop-bytes {
               type int32;
               description "Drop statistics at ingress in bytes";
             }
             leaf input-drop-packets {
               type int32;
               description "Drop statistics at ingress in packets";
             }
           }
           container transit-traffic-statistics {
           }
           container keepalive-statistics {
             leaf keepalive-lmi-descriptor {
               type string;
             }
             leaf keepalive-input-count {
               type int32;
             }
             leaf keepalive-input-time {
               type string;
             }
             leaf keepalive-output-count {
               type int32;
             }
             leaf keepalive-output-time {
               type string;
             }
           }
           container virtual-circuit-information {
             container traffic-statistics {
               leaf input-bps {
                 type int32;
               }
               leaf input-pps {
                 type int32;
               }
               leaf output-bps {
                 type int32;
               }
               leaf output-pps {
                 type int32;
               }
               leaf input-packets {
                 type int32;
               }
               leaf output-packets {
                 type int32;
               }
               leaf input-bytes {
                 type int32;
               }
               leaf output-bytes {
                 type int32;
               }
               container ipv6-transit-statistics {
                 leaf input-bytes {
                   type int32;
                 }
                 leaf output-bytes {
                   type int32;
                 }
                 leaf input-packets {
                   type int32;
                 }
                 leaf output-packets {
                   type int32;
                 }
               }
               container ipv6-total-statistics {
                 leaf input-bytes {
                   type int32;
                 }
                 leaf output-bytes {
                   type int32;
                 }
                 leaf input-packets {
                   type int32;
                 }
                 leaf output-packets {
                   type int32;
                 }
               }
             }
             container atm-cos-information {
               leaf vc-cos-mode {
                 type string;
                 description "Virtual circuit CoS scheduling mode";
               }
               list atm-cos-queue {
                 container atm-cos-queue-parameters {
                   leaf cos-forwarding-class-name {
                     type string;
                     description "Forwarding class name associated with queue";
                   }
                   leaf cos-queue-number {
                     type int32;
                     description "Queue number";
                   }
                   leaf scheduling-priority {
                     type string;
                     description "Scheduling priority";
                   }
                   leaf transmit-weight-cells {
                     type int32;
                     description "Weight to apply to scheduling as number of cells";
                   }
                   leaf transmit-weight-percent {
                     type int32;
                     description "Weight to apply to scheduling as fill percentage";
                   }
                   leaf epd-threshold {
                     type int32;
                     description "Early packet drop threshold";
                   }
                   leaf epd-threshold-plp0 {
                     type int32;
                     description "Early packet drop threshold for PLP 0";
                   }
                   leaf epd-threshold-plp1 {
                     type int32;
                     description "Early packet drop threshold for PLP 1";
                   }
                   container linear-red-drop-profile {
                     leaf queue-depth {
                       type uint32;
                       description "Instantaneous queue depth";
                     }
                     leaf low-red {
                       type int32;
                       description "Fill level percentage when linear RED is applied for low PLP";
                     }
                     leaf high-red {
                       type int32;
                       description "Fill level percentage when linear RED is applied for high PLP";
                     }
                     leaf max-low-red {
                       type int32;
                       description "Fill level percentage with 100% packet drop for low PLP";
                     }
                     leaf max-high-red {
                       type int32;
                       description "Fill level percentage with 100% packet drop for high PLP";
                     }
                   }
                 }
                 container atm-cos-queue-statistics {
                   leaf atm-output-bytes {
                     type int32;
                   }
                   leaf atm-output-packets {
                     type int32;
                   }
                   leaf atm-packet-drops {
                     type int32;
                   }
                 }
                 container atm-cos-plp-statistics {
                   leaf atm-plp0-output-bytes {
                     type int32;
                   }
                   leaf atm-plp1-output-bytes {
                     type int32;
                   }
                   leaf atm-plp0-output-packets {
                     type int32;
                   }
                   leaf atm-plp1-output-packets {
                     type int32;
                   }
                   leaf atm-plp0-byte-drops {
                     type int32;
                   }
                   leaf atm-plp1-byte-drops {
                     type int32;
                   }
                   leaf atm-plp0-packet-drops {
                     type int32;
                   }
                   leaf atm-plp1-packet-drops {
                     type int32;
                   }
                 }
               }
             }
           }
           list policer-information {
             leaf policer-family {
               type string;
               description "Protocol family of the policer";
             }
             leaf policer-input {
               type string;
               description "Name of the input policer";
             }
             leaf policer-output {
               type string;
               description "Name of the output policer";
             }
           }
           list address-family {
             leaf local-bias-information {
               type string;
             }
             leaf ft-iff-dest-port {
               type uint32;
               description "Destination UDP port to be used for this family";
             }
             container pppoe-underlying-information {
               list pppoe-underlying-interface {
                 leaf dynamic-profile {
                   type string;
                   description "Dynamic Profile name";
                 }
                 leaf service-name-table {
                   type string;
                   description "Name of Service Name Table";
                 }
                 leaf max-sessions {
                   type int32;
                   description "Maximum number of PPPoE sessions";
                 }
                 leaf max-sessions-vsa-ignore {
                   type string;
                   description "Ignore max-sessions VSA";
                 }
                 leaf duplicate-protection {
                   type string;
                   description "Duplicate protection mode";
                 }
                 leaf short-cycle-protection {
                   type string;
                   description "Short cycle protection mode";
                 }
                 leaf direct-connect {
                   type string;
                   description "Direct connect mode";
                 }
                 leaf ac-name {
                   type string;
                   description "Access Concentrator name";
                 }
                 leaf underlying-interface-name {
                   type string;
                   description "Underlying interface name";
                 }
                 leaf underlying-interface-index {
                   type string;
                   description "Underlying interface index";
                 }
                 leaf encapsulation-type-identifier {
                   type string;
                   description "Encapsulation type identifier";
                 }
                 leaf state {
                   type string;
                   description "State";
                 }
                 leaf active-sessions {
                   type int32;
                   description "Number of active PPPoE sessions";
                 }
                 leaf aci-autosensing {
                   type string;
                   description "ACI VLAN Autosensing mode";
                 }
                 leaf line-identity-autosensing {
                   type string;
                   description "Line Identity Autosensing mode";
                 }
               }
             }
             list interface-address {
             }
             container destination-class-statistics {
             }
             container source-class-statistics {
             }
           }
           list bridge-iff-properties {
           }
           container l2circuit-info {
             leaf out-of-sequence {
               type int32;
             }
             leaf denied-packets {
               type int32;
             }
             leaf cell-bundle-size {
               type int32;
             }
             leaf cell-bundle-timeout {
               type int32;
             }
             leaf cell-timeout-count {
               type int32;
             }
           }
           container media-information {
             leaf media-type {
               type string;
               description "Type of media this information is for";
             }
             list media-alarm {
               leaf media-alarm-name {
                 type string;
               }
               leaf media-alarm-count {
                 type int32;
               }
               leaf media-alarm-seconds {
                 type int32;
               }
               leaf media-alarm-state {
                 type string;
               }
               leaf ce-counter-name {
                 type string;
                 description "Circuit Emulation counter information";
               }
               leaf ce-counter-packets {
                 type int32;
                 description "Circuit Emulation number of packets";
               }
               leaf ce-counter-bytes {
                 type int32;
                 description "Circuit Emulation number of bytes";
               }
               leaf ce-counter-count {
                 type int32;
                 description "Circuit Emulation number of event occurrences";
               }
             }
             leaf ds1-timeslots {
               type string;
             }
             leaf ds1-line-encoding {
               type string;
             }
             leaf ds1-byte-encoding {
               type string;
             }
             leaf ds1-data-inversion {
               type string;
             }
             leaf idle-cycle-flag {
               type string;
             }
             leaf start-end-flag {
               type string;
             }
             leaf ds0-byte-encoding {
               type string;
             }
             leaf ds0-data-inversion {
               type string;
             }
             leaf e3-data-inversion {
               type string;
             }
             leaf ds1-buildout {
               type string;
               description "Number of feet";
             }
           }
           list macsec-statistics {
             leaf interface-name {
               type string;
               description "Class-of-service interface name";
             }
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
             leaf ok-packets {
               type uint64;
               description "Macsec packets accepted";
             }
             leaf decrypted-bytes {
               type uint64;
               description "Macsec received bytes decrypted";
             }
             leaf decrypted-packets {
               type uint64;
               description "Macsec received packets decrypted";
             }
             leaf validated-packets {
               type uint64;
               description "Macsec received packets validated";
             }
             leaf validated-bytes {
               type uint64;
               description "Macsec received bytes validated";
             }
             leaf untagged-packets {
               type uint64;
               description "Macsec untagged packets";
             }
             leaf toolong-packets {
               type uint64;
               description "Macsec too long packets transmitted on a secure channel";
             }
             leaf control-packets {
               type uint64;
               description "Macsec control packets received on a secure channel";
             }
             leaf tagged-miss-packets {
               type uint64;
               description "Macsec tagged miss packets received on a secure channel";
             }
             leaf untagged-hit-packets {
               type uint64;
               description "Macsec untagged hit packets received on a secure channel";
             }
             leaf notag-packets {
               type uint64;
               description "Macsec no tag packets received on a secure channel";
             }
             leaf badtag-packets {
               type uint64;
               description "Macsec bad tag packets received on a secure channel";
             }
             leaf unknown-sci-packets {
               type uint64;
               description "Macsec unknown sci packets received on a secure channel";
             }
             leaf no-sci-packets {
               type uint64;
               description "Macsec no sci packets received on a secure channel";
             }
             leaf control-pass-packets {
               type uint64;
               description "Macsec allowed control packets received on a secure channel";
             }
             leaf uncontrol-pass-packets {
               type uint64;
               description "Macsec allowed uncontrol packets received on a secure channel";
             }
             leaf control-fail-packets {
               type uint64;
               description "Macsec dropped control packets received on a secure channel";
             }
             leaf uncontrol-fail-packets {
               type uint64;
               description "Macsec dropped uncontrol packets received on a secure channel";
             }
             leaf hit-dropped-packets {
               type uint64;
               description "Macsec hit dropped packets received on a security channel";
             }
             leaf notusing-sa-packets {
               type uint64;
               description "Macsec not using sa packets received on a security channel";
             }
             leaf unused-sa-packets {
               type uint64;
               description "Macsec unused sa packets received on a security channel";
             }
             leaf late-packets {
               type uint64;
               description "Macsec late packets dropped on a security channel";
             }
             leaf delayed-packets {
               type uint64;
               description "Macsec delayed packets accepted on a security channel";
             }
             leaf unchecked-packets {
               type uint64;
               description "Macsec unchecked packets accepted on a security channel";
             }
             leaf notvalid-packets {
               type uint64;
               description "Macsec not valid packets dropped on a security channel";
             }
             leaf invalid-packets {
               type uint64;
               description "Macsec invalid packets accepted on a security channel";
             }
             list secure-channel-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-association-sent {
               leaf encrypted-packets {
                 type uint64;
                 description "Macsec encrypted packets sent";
               }
               leaf encrypted-bytes {
                 type uint64;
                 description "Macsec encrypted bytes sent";
               }
               leaf protected-packets {
                 type uint64;
                 description "Macsec packets sent with only integrity protection";
               }
               leaf protected-bytes {
                 type uint64;
                 description "Macsec bytes sent with only integrity protection";
               }
             }
             list secure-channel-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list secure-association-received {
               leaf ok-packets {
                 type uint64;
                 description "Macsec packets accepted";
               }
               leaf decrypted-packets {
                 type uint64;
                 description "Macsec received packets decrypted";
               }
               leaf decrypted-bytes {
                 type uint64;
                 description "Macsec received bytes decrypted";
               }
               leaf validated-packets {
                 type uint64;
                 description "Macsec received packets validated";
               }
               leaf validated-bytes {
                 type uint64;
                 description "Macsec received bytes validated";
               }
             }
             list macsec-error-information {
               list secure-channel-sent-errors {
                 leaf untagged-packets {
                   type uint64;
                   description "Macsec untagged packets";
                 }
                 leaf toolong-packets {
                   type uint64;
                   description "Macsec too long packets transmitted on a secure channel";
                 }
               }
               list secure-channel-received-errors {
                 leaf control-packets {
                   type uint64;
                   description "Macsec control packets received on a secure channel";
                 }
                 leaf tagged-miss-packets {
                   type uint64;
                   description "Macsec tagged miss packets received on a secure channel";
                 }
                 leaf untagged-hit-packets {
                   type uint64;
                   description "Macsec untagged hit packets received on a secure channel";
                 }
                 leaf untagged-packets {
                   type uint64;
                   description "Macsec untagged packets";
                 }
                 leaf notag-packets {
                   type uint64;
                   description "Macsec no tag packets received on a secure channel";
                 }
                 leaf badtag-packets {
                   type uint64;
                   description "Macsec bad tag packets received on a secure channel";
                 }
                 leaf unknown-sci-packets {
                   type uint64;
                   description "Macsec unknown sci packets received on a secure channel";
                 }
                 leaf no-sci-packets {
                   type uint64;
                   description "Macsec no sci packets received on a secure channel";
                 }
                 leaf control-pass-packets {
                   type uint64;
                   description "Macsec allowed control packets received on a secure channel";
                 }
                 leaf control-fail-packets {
                   type uint64;
                   description "Macsec dropped control packets received on a secure channel";
                 }
                 leaf uncontrol-pass-packets {
                   type uint64;
                   description "Macsec allowed uncontrol packets received on a secure channel";
                 }
                 leaf uncontrol-fail-packets {
                   type uint64;
                   description "Macsec dropped uncontrol packets received on a secure channel";
                 }
               }
               list secure-channel-received-extended {
                 leaf hit-dropped-packets {
                   type uint64;
                   description "Macsec hit dropped packets received on a security channel";
                 }
                 leaf invalid-packets {
                   type uint64;
                   description "Macsec invalid packets accepted on a security channel";
                 }
                 leaf late-packets {
                   type uint64;
                   description "Macsec late packets dropped on a security channel";
                 }
                 leaf delayed-packets {
                   type uint64;
                   description "Macsec delayed packets accepted on a security channel";
                 }
                 leaf unchecked-packets {
                   type uint64;
                   description "Macsec unchecked packets accepted on a security channel";
                 }
                 leaf notvalid-packets {
                   type uint64;
                   description "Macsec not valid packets dropped on a security channel";
                 }
                 leaf notusing-sa-packets {
                   type uint64;
                   description "Macsec not using sa packets received on a security channel";
                 }
                 leaf unused-sa-packets {
                   type uint64;
                   description "Macsec unused sa packets received on a security channel";
                 }
                 leaf untagged-hit-packets {
                   type uint64;
                   description "Macsec untagged hit packets received on a secure channel";
                 }
               }
             }
           }
           container lag-traffic-statistics {
             container lag-multicast-statistics {
               leaf lag-multicast-statistics-header {
                 type empty;
               }
               container lag-ipv4-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
               container lag-ipv6-multicast-statistics {
                 leaf input-packets {
                   type int32;
                 }
                 leaf input-pps {
                   type int32;
                 }
                 leaf input-bytes {
                   type int32;
                 }
                 leaf input-bps {
                   type int32;
                 }
                 leaf output-packets {
                   type int32;
                 }
                 leaf output-pps {
                   type int32;
                 }
                 leaf output-bytes {
                   type int32;
                 }
                 leaf output-bps {
                   type int32;
                 }
               }
             }
             list if-distribution-list-information {
             }
           }
           container layer2-input-policer-statistics {
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container layer2-output-policer-statistics {
             leaf policer-medium-low-frames {
               type int32;
               description "Number of loss priority medium low frames";
             }
             leaf policer-medium-low-bytes {
               type int32;
               description "Number of loss priority medium low bytes";
             }
             leaf policer-medium-low-rate {
               type int32;
               description "Rate of loss priority medium low pkts";
             }
           }
           container mac-policer-information {
             container ether-policer-list {
             }
           }
         }
         container active-alarms-otn {
         }
         container active-defects-otn {
         }
         container active-alarms-optics {
         }
         container active-defects-optics {
         }
         container optics-defect-information {
           list media-alarm {
             leaf media-alarm-name {
               type string;
             }
             leaf media-alarm-seconds {
               type int32;
             }
             leaf media-alarm-count {
               type int32;
             }
             leaf media-alarm-state {
               type string;
             }
           }
         }
         container optics-fec-information {
           list media-alarm {
             leaf media-alarm-name {
               type string;
             }
             leaf media-alarm-seconds {
               type int32;
             }
             leaf media-alarm-count {
               type int32;
             }
             leaf media-alarm-state {
               type string;
             }
           }
         }
         container active-alerts-otn {
         }
         container links {
           list link-entry {
             leaf sonet-payload-pointer-curptr {
               type string;
               description "Value of the SONET/SDH payload pointer, derived from the H1 and H2 overhead bytes";
             }
             leaf sonet-payload-pointer-ptrinc-count {
               type string;
               description "Number of times the value of the SONET/SDH payload pointer had positive justification";
             }
             leaf sonet-payload-pointer-ptrdec-count {
               type string;
               description "Number of times the value of the SONET/SDH payload pointer had negative justification";
             }
             leaf sonet-payload-pointer-newptr-ndf-count {
               type string;
               description "Number of times a new payload pointer was created with the New Data Found flag set";
             }
             leaf sonet-rx-overhead {
               type string;
             }
             leaf sonet-tx-overhead {
               type string;
             }
             leaf sonet-rx-path-trace {
               type string;
               description "Received SONET path trace";
             }
             leaf sonet-tx-path-trace {
               type string;
               description "Transmitted SONET path trace";
             }
             container active-alarms {
             }
             container active-defects {
             }
             container sonet-errors {
               list media-alarm {
                 leaf media-alarm-name {
                   type string;
                 }
                 leaf media-alarm-count {
                   type int32;
                 }
               }
             }
             container sonet-physical-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-section-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-line-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-path-information {
               list media-alarm {
                 leaf media-alarm-name {
                   type string;
                 }
                 leaf media-alarm-seconds {
                   type int32;
                 }
                 leaf media-alarm-count {
                   type int32;
                 }
                 leaf media-alarm-state {
                   type string;
                 }
               }
             }
             container sonet-vt-information {
               list media-alarm {
                 leaf media-alarm-name {
                   type string;
                 }
                 leaf media-alarm-seconds {
                   type int32;
                 }
                 leaf media-alarm-count {
                   type int32;
                 }
                 leaf media-alarm-state {
                   type string;
                 }
               }
             }
             list optics-diagnostics {
               leaf optic-diagnostics-not-available {
                 type string;
                 description "Optical diagnostics not supported by this transceiver";
               }
               leaf laser-bias-current-not-available {
                 type string;
                 description "Laser bias current measurement not available";
               }
               leaf soa-bias-current-not-available {
                 type string;
                 description "SOA bias current measurement not available";
               }
               leaf laser-tx-power-not-available {
                 type string;
                 description "Laser output power measurement not available";
               }
               leaf module-temperature-not-available {
                 type string;
                 description "Module temperature measurement not available";
               }
               leaf tx-module-temperature-not-available {
                 type string;
                 description "Tx module temperature measurement not available";
               }
               leaf rx-module-temperature-not-available {
                 type string;
                 description "Rx module temperature measurement not available";
               }
               leaf laser-rx-power-not-available {
                 type string;
                 description "Laser receiver optical power measurement not available";
               }
               leaf laser-tx-power-high-alarm-threshold-not-available {
                 type string;
                 description "Laser output power high alarm threshold not available";
               }
               leaf laser-tx-power-low-alarm-threshold-not-available {
                 type string;
                 description "Laser output power low alarm threshold not available";
               }
               leaf laser-tx-power-high-warning-threshold-not-available {
                 type string;
                 description "Laser output power high warning threshold not available";
               }
               leaf laser-tx-power-low-warning-threshold-not-available {
                 type string;
                 description "Laser output power low warning threshold not available";
               }
               leaf laser-bias-current {
                 type string;
                 description "Laser bias current (milliamperes)";
               }
               leaf soa-bias-current {
                 type string;
                 description "SOA bias current (milliamperes)";
               }
               leaf laser-output-power {
                 type string;
                 description "Laser output power (milliwatts)";
               }
               leaf laser-output-power-dbm {
                 type string;
                 description "Laser output power (dBm)";
               }
               leaf module-temperature {
                 type string;
                 description "Module temperature";
               }
               leaf tx-module-temperature {
                 type string;
                 description "Tx module temperature";
               }
               leaf rx-module-temperature {
                 type string;
                 description "Rx module temperature";
               }
               leaf module-voltage {
                 type string;
                 description "Module voltage";
               }
               leaf corrected-error-ratio {
                 type string;
                 description "Corrected error ratio";
               }
               leaf uncorrected-words-ratio {
                 type string;
                 description "Uncorrected words ratio";
               }
               leaf tx-module-voltage {
                 type string;
                 description "Tx module voltage";
               }
               leaf rx-module-voltage {
                 type string;
                 description "Rx module voltage";
               }
               leaf rx-signal-avg-optical-power {
                 type string;
                 description "Receiver signal average power (milliwatts)";
               }
               leaf rx-signal-avg-optical-power-dbm {
                 type string;
                 description "Receiver signal average power (dBm)";
               }
               leaf laser-rx-optical-power {
                 type string;
                 description "Laser receiver optical power (milliwatts)";
               }
               leaf laser-rx-optical-power-dbm {
                 type string;
                 description "Laser receiver optical power (dBm)";
               }
               leaf wavelength-channel {
                 type string;
                 description "Wavelength channel number set";
               }
               leaf wavelength-setpoint {
                 type string;
                 description "Wavelength point set";
               }
               leaf tx-dither {
                 type string;
                 description "Tx dither status";
               }
               leaf frequency-error {
                 type string;
                 description "Frequency error value";
               }
               leaf wavelength-error {
                 type string;
                 description "Wavelength error value";
               }
               leaf laser-bias-current-high-alarm {
                 type string;
                 description "Laser bias current high alarm";
               }
               leaf laser-bias-current-low-alarm {
                 type string;
                 description "Laser bias current low alarm";
               }
               leaf laser-bias-current-high-warn {
                 type string;
                 description "Laser bias current high warning";
               }
               leaf laser-bias-current-low-warn {
                 type string;
                 description "Laser bias current low warning";
               }
               leaf soa-bias-current-high-alarm {
                 type string;
                 description "SOA bias current high alarm";
               }
               leaf soa-bias-current-low-alarm {
                 type string;
                 description "SOA bias current low alarm";
               }
               leaf soa-bias-current-high-warn {
                 type string;
                 description "SOA bias current high warning";
               }
               leaf soa-bias-current-low-warn {
                 type string;
                 description "SOA bias current low warning";
               }
               leaf laser-tx-power-high-alarm {
                 type string;
                 description "Laser output power high alarm";
               }
               leaf laser-tx-power-low-alarm {
                 type string;
                 description "Laser output power low alarm";
               }
               leaf laser-tx-power-high-warn {
                 type string;
                 description "Laser output power high warning";
               }
               leaf laser-tx-power-low-warn {
                 type string;
                 description "Laser output power low warning";
               }
               leaf tx-power-high-alarm {
                 type string;
                 description "Tx power high alarm";
               }
               leaf tx-power-low-alarm {
                 type string;
                 description "Tx power low alarm";
               }
               leaf tx-power-high-warn {
                 type string;
                 description "Tx power high warning";
               }
               leaf tx-power-low-warn {
                 type string;
                 description "Tx power low warning";
               }
               leaf module-temperature-high-alarm {
                 type string;
                 description "Module temperature high alarm";
               }
               leaf module-temperature-low-alarm {
                 type string;
                 description "Module temperature low alarm";
               }
               leaf module-temperature-high-warn {
                 type string;
                 description "Module temperature high warning";
               }
               leaf module-temperature-low-warn {
                 type string;
                 description "Module temperature low warning";
               }
               leaf tx-module-temperature-high-alarm {
                 type string;
                 description "Tx module temperature high alarm";
               }
               leaf tx-module-temperature-low-alarm {
                 type string;
                 description "Tx module temperature low alarm";
               }
               leaf rx-module-temperature-high-alarm {
                 type string;
                 description "Rx module temperature high alarm";
               }
               leaf rx-module-temperature-low-alarm {
                 type string;
                 description "Rx module temperature low alarm";
               }
               leaf module-voltage-high-alarm {
                 type string;
                 description "Module voltage high alarm";
               }
               leaf module-voltage-low-alarm {
                 type string;
                 description "Module voltage low alarm";
               }
               leaf module-voltage-high-warn {
                 type string;
                 description "Module voltage high warning";
               }
               leaf module-voltage-low-warn {
                 type string;
                 description "Module voltage low warning";
               }
               leaf tx-module-voltage-high-alarm {
                 type string;
                 description "Tx module voltage high alarm";
               }
               leaf tx-module-voltage-low-alarm {
                 type string;
                 description "Tx module voltage low alarm";
               }
               leaf rx-module-voltage-high-alarm {
                 type string;
                 description "Rx module voltage high alarm";
               }
               leaf rx-module-voltage-low-alarm {
                 type string;
                 description "Rx module voltage low alarm";
               }
               leaf laser-rx-power-high-alarm {
                 type string;
                 description "Laser receiver power high alarm";
               }
               leaf laser-rx-power-low-alarm {
                 type string;
                 description "Laser receiver power low alarm";
               }
               leaf laser-rx-power-high-warn {
                 type string;
                 description "Laser receiver power high warning";
               }
               leaf laser-rx-power-low-warn {
                 type string;
                 description "Laser receiver power low warning";
               }
               leaf rx-power-high-alarm {
                 type string;
                 description "Receiver power high alarm";
               }
               leaf rx-power-low-alarm {
                 type string;
                 description "Receiver power low alarm";
               }
               leaf rx-power-high-warn {
                 type string;
                 description "Receiver power high warning";
               }
               leaf rx-power-low-warn {
                 type string;
                 description "Receiver power low warning";
               }
               leaf laser-end-of-life-alarm {
                 type string;
                 description "Laser end-of-life alarm";
               }
               leaf laser-wavelength-alarm {
                 type string;
                 description "Laser wavelength alarm";
               }
               leaf laser-bias-current-alarm {
                 type string;
                 description "Laser bias current alarm";
               }
               leaf module-temperature-alarm {
                 type string;
                 description "Module temperature alarm";
               }
               leaf laser-power-alarm {
                 type string;
                 description "Laser power alarm";
               }
               leaf modulator-temperature-alarm {
                 type string;
                 description "Modulator temperature alarm";
               }
               leaf modulator-bias-alarm {
                 type string;
                 description "Modulator bias alarm";
               }
               leaf module-not-ready-alarm {
                 type string;
                 description "Module not ready alarm";
               }
               leaf module-power-down-alarm {
                 type string;
                 description "Module power down alarm";
               }
               leaf module-not-init-done-alarm {
                 type string;
                 description "Module initialization not done alarm";
               }
               leaf module-not-high-power-on-alarm {
                 type string;
                 description "Module not high powered on alarm";
               }
               leaf module-fault-alarm {
                 type string;
                 description "Module in fault state alarm";
               }
               leaf pld-flash-init-fault-alarm {
                 type string;
                 description "PLD or Flash initialization fault alarm";
               }
               leaf power-supply-fault-alarm {
                 type string;
                 description "Power supply fault alarm";
               }
               leaf checksum-fault-alarm {
                 type string;
                 description "Checksum fault alarm";
               }
               leaf apd-supply-fault-alarm {
                 type string;
                 description "APD supply fault alarm";
               }
               leaf tec-fault-alarm {
                 type string;
                 description "TEC fault alarm";
               }
               leaf wavelength-unlocked-alarm {
                 type string;
                 description "Wavelength unlocked alarm";
               }
               leaf tx-tune-alarm {
                 type string;
                 description "Tx tune alarm";
               }
               leaf tx-mux-fifo-error-alarm {
                 type string;
                 description "Tx multiplexer fifo error alarm";
               }
               leaf tx-loss-of-pll-alarm {
                 type string;
                 description "Tx loss of PLL alarm";
               }
               leaf tx-data-not-ready-alarm {
                 type string;
                 description "Tx data not ready alarm";
               }
               leaf tx-not-ready-alarm {
                 type string;
                 description "Tx not ready alarm";
               }
               leaf tx-laser-fault-alarm {
                 type string;
                 description "Tx laser fault alarm";
               }
               leaf tx-laser-disabled-alarm {
                 type string;
                 description "Tx laser disabled alarm";
               }
               leaf tx-loss-of-signal-functionality-alarm {
                 type string;
                 description "Tx loss of signal functionality alarm";
               }
               leaf tx-cdr-loss-of-lock-alarm {
                 type string;
                 description "Tx CDR loss of lock alarm";
               }
               leaf rx-loss-avg-opt-power-alarm {
                 type string;
                 description "Receiver loss of average optical power alarm";
               }
               leaf rx-loss-ac-power-alarm {
                 type string;
                 description "Receiver loss of AC power alarm";
               }
               leaf rx-loss-of-pll-alarm {
                 type string;
                 description "Receiver loss of PLL alarm";
               }
               leaf rx-not-ready-alarm {
                 type string;
                 description "Receiver not ready alarm";
               }
               leaf rx-loss-of-signal-alarm {
                 type string;
                 description "Receiver loss of signal alarm";
               }
               leaf rx-cdr-loss-of-lock-alarm {
                 type string;
                 description "Receiver CDR loss of lock alarm";
               }
               leaf laser-bias-current-high-alarm-threshold {
                 type string;
                 description "Laser bias current high alarm threshold (milliamperes)";
               }
               leaf laser-bias-current-low-alarm-threshold {
                 type string;
                 description "Laser bias current low alarm threshold (milliamperes)";
               }
               leaf laser-bias-current-high-warn-threshold {
                 type string;
                 description "Laser bias current high warning threshold (milliamperes)";
               }
               leaf laser-bias-current-low-warn-threshold {
                 type string;
                 description "Laser bias current low warning threshold (milliamperes)";
               }
               leaf soa-bias-current-high-alarm-threshold {
                 type string;
                 description "SOA bias current high alarm threshold (milliamperes)";
               }
               leaf soa-bias-current-low-alarm-threshold {
                 type string;
                 description "SOA bias current low alarm threshold (milliamperes)";
               }
               leaf soa-bias-current-high-warn-threshold {
                 type string;
                 description "SOA bias current high warning threshold (milliamperes)";
               }
               leaf soa-bias-current-low-warn-threshold {
                 type string;
                 description "SOA bias current low warning threshold (milliamperes)";
               }
               leaf laser-tx-power-high-alarm-threshold {
                 type string;
                 description "Laser transmitter power high alarm threshold (milliwatts)";
               }
               leaf laser-tx-power-high-alarm-threshold-dbm {
                 type string;
                 description "Laser transmitter power high alarm threshold (dBm)";
               }
               leaf laser-tx-power-low-alarm-threshold {
                 type string;
                 description "Laser transmitter power low alarm threshold (milliwatts)";
               }
               leaf laser-tx-power-low-alarm-threshold-dbm {
                 type string;
                 description "Laser transmitter power low alarm threshold (dBm)";
               }
               leaf laser-tx-power-high-warn-threshold {
                 type string;
                 description "Laser transmitter power high warning threshold (milliwatts)";
               }
               leaf laser-tx-power-high-warn-threshold-dbm {
                 type string;
                 description "Laser transmitter power high warning threshold (dBm)";
               }
               leaf laser-tx-power-low-warn-threshold {
                 type string;
                 description "Laser transmitter power low warning threshold (milliwatts)";
               }
               leaf laser-tx-power-low-warn-threshold-dbm {
                 type string;
                 description "Laser transmitter power low warning threshold (dBm)";
               }
               leaf module-temperature-high-alarm-threshold {
                 type string;
                 description "Module temperature high alarm threshold";
               }
               leaf module-temperature-low-alarm-threshold {
                 type string;
                 description "Module temperature low alarm threshold";
               }
               leaf module-temperature-high-warn-threshold {
                 type string;
                 description "Module temperature high warning threshold";
               }
               leaf module-temperature-low-warn-threshold {
                 type string;
                 description "Module temperature low warning threshold";
               }
               leaf laser-temperature-high-alarm-threshold {
                 type string;
                 description "Laser temperature high alarm threshold";
               }
               leaf laser-temperature-low-alarm-threshold {
                 type string;
                 description "Laser temperature low alarm threshold";
               }
               leaf laser-temperature-high-warn-threshold {
                 type string;
                 description "Laser temperature high warning threshold";
               }
               leaf laser-temperature-low-warn-threshold {
                 type string;
                 description "Laser temperature low warning threshold";
               }
               leaf module-voltage-high-alarm-threshold {
                 type string;
                 description "Module voltage high alarm threshold (volts)";
               }
               leaf module-voltage-low-alarm-threshold {
                 type string;
                 description "Module voltage low alarm threshold (volts)";
               }
               leaf module-voltage-high-warn-threshold {
                 type string;
                 description "Module voltage high warning threshold (volts)";
               }
               leaf module-voltage-low-warn-threshold {
                 type string;
                 description "Module voltage low warning threshold (volts)";
               }
               leaf laser-rx-power-high-alarm-threshold {
                 type string;
                 description "Laser receiver power high alarm (milliwatts)";
               }
               leaf laser-rx-power-high-alarm-threshold-dbm {
                 type string;
                 description "Laser receiver power high alarm (dBm)";
               }
               leaf laser-rx-power-low-alarm-threshold {
                 type string;
                 description "Laser receiver power low alarm (milliwatts)";
               }
               leaf laser-rx-power-low-alarm-threshold-dbm {
                 type string;
                 description "Laser receiver power low alarm (dBm)";
               }
               leaf laser-rx-power-high-warn-threshold {
                 type string;
                 description "Laser receiver power high warning (milliwatts)";
               }
               leaf laser-rx-power-high-warn-threshold-dbm {
                 type string;
                 description "Laser receiver power high warning (dBm)";
               }
               leaf laser-rx-power-low-warn-threshold {
                 type string;
                 description "Laser receiver power low warning (milliwatts)";
               }
               leaf laser-rx-power-low-warn-threshold-dbm {
                 type string;
                 description "Laser receiver power low warning (dBm)";
               }
               leaf rx-power-high-alarm-threshold {
                 type string;
                 description "Receiver power high alarm (milliwatts)";
               }
               leaf rx-power-high-alarm-threshold-dbm {
                 type string;
                 description "Receiver power high alarm (dBm)";
               }
               leaf rx-power-low-alarm-threshold {
                 type string;
                 description "Receiver power low alarm (milliwatts)";
               }
               leaf rx-power-low-alarm-threshold-dbm {
                 type string;
                 description "Receiver power low alarm (dBm)";
               }
               leaf rx-power-high-warning-threshold {
                 type string;
                 description "Receiver power high warning (milliwatts)";
               }
               leaf rx-power-high-warning-threshold-dbm {
                 type string;
                 description "Receiver power high warning (dBm)";
               }
               leaf rx-power-low-warning-threshold {
                 type string;
                 description "Receiver power low warning (milliwatts)";
               }
               leaf rx-power-low-warning-threshold-dbm {
                 type string;
                 description "Receiver power low warning (dBm)";
               }
               leaf los-alarm-threshold {
                 type string;
                 description "LOS alarm threshold (milliwatts)";
               }
               leaf los-alarm-threshold-dbm {
                 type string;
                 description "LOS alarm threshold (dBm)";
               }
               leaf los-warning-threshold {
                 type string;
                 description "LOS warning threshold (milliwatts)";
               }
               leaf los-warning-threshold-dbm {
                 type string;
                 description "LOS warning threshold (dBm)";
               }
               leaf dsp-module-state {
                 type string;
                 description "DSP module state";
               }
               leaf output-power {
                 type string;
                 description "Output power (milliwatts)";
               }
               leaf output-power-dbm {
                 type string;
                 description "Output power (dBm)";
               }
               leaf input-power {
                 type string;
                 description "Input power (milliwatts)";
               }
               leaf input-power-dbm {
                 type string;
                 description "Input power (dBm)";
               }
               leaf per-wave-rx-optical-power {
                 type string;
                 description "Per-wavelength receiver optical power (milliwatts)";
               }
               leaf per-wave-rx-optical-power-dbm {
                 type string;
                 description "Per-wavelength receiver optical power (dBm)";
               }
               leaf lane-laser-frequency-error {
                 type string;
                 description "Lane laser frequency error (MHz)";
               }
               leaf tec-current {
                 type string;
                 description "Tec current";
               }
               leaf residual-isi {
                 type string;
                 description "Residual ISI";
               }
               container optics-diagnostics-ot {
                 leaf module-temp-fault {
                   type string;
                   description "Module temperature fault";
                 }
                 leaf specific-hw-fault {
                   type string;
                   description "Specific HW fault";
                 }
                 leaf internal-power-fault {
                   type string;
                   description "Internal power fault";
                 }
                 leaf post-therm-fault {
                   type string;
                   description "Power thermal fault";
                 }
                 leaf post-fault {
                   type string;
                   description "Post fault";
                 }
                 leaf command-error {
                   type string;
                   description "Command error";
                 }
                 leaf rx-pll-lock {
                   type string;
                   description "RX PLL lock";
                 }
                 leaf network-lane-los {
                   type string;
                   description "Network Lane LOS";
                 }
                 leaf network-lane-lof {
                   type string;
                   description "Network Lane LOF";
                 }
                 leaf network-lane-oof {
                   type string;
                   description "Network Lane OOF";
                 }
                 leaf network-lane-lom {
                   type string;
                   description "Network Lane LOM";
                 }
                 leaf network-lane-oom {
                   type string;
                   description "Network Lane OOM";
                 }
                 leaf network-lane-otu-bdi {
                   type string;
                   description "Network Lane OTU BDI";
                 }
                 leaf lane-rx-fifo-error {
                   type string;
                   description "Lane RX FIFO error";
                 }
                 leaf tx-reference-clock-fault {
                   type string;
                   description "TX reference clock fault";
                 }
                 leaf rx-modem-sync-fault {
                   type string;
                   description "Rx modem sync fault";
                 }
                 leaf rx-modem-loss-of-lock {
                   type string;
                   description "RX modem loss of lock";
                 }
                 leaf rx-loss-of-alignment {
                   type string;
                   description "RX loss of alignment";
                 }
                 leaf rx-out-of-alignment {
                   type string;
                   description "RX out of alignment";
                 }
                 leaf rx-timing-fault {
                   type string;
                   description "Rx timing fault";
                 }
                 leaf link-msg-data-available {
                   type string;
                   description "Link msg data available";
                 }
                 leaf modulator-bias-control-loop-fail {
                   type string;
                   description "Modulator Bias Control Loop Fail";
                 }
                 leaf itla-fault {
                   type string;
                   description "ITLA fault";
                 }
                 leaf dac-calib-fault {
                   type string;
                   description "DAC calib fault";
                 }
                 leaf adc-calib-fault {
                   type string;
                   description "ADC calib fault";
                 }
                 leaf prom-fault {
                   type string;
                   description "PROM fault";
                 }
                 leaf tx-mod-bias-voa-ctrl-loop-high-alarm {
                   type string;
                   description "TX mod bias VOA ctrl loop high alarm";
                 }
                 leaf tx-mod-bias-voa-ctrl-loop-low-alarm {
                   type string;
                   description "TX mod bias VOA ctrl loop low alarm";
                 }
                 leaf rx-phase-control-loop-high-alarm {
                   type string;
                   description "RX phase control loop high alarm";
                 }
                 leaf rx-phase-control-loop-low-alarm {
                   type string;
                   description "RX phase control loop low alarm";
                 }
                 leaf rx-phase-control-loop-high-warning {
                   type string;
                   description "RX phase control loop high warning";
                 }
                 leaf rx-phase-control-loop-low-warning {
                   type string;
                   description "RX phase control loop low warning";
                 }
                 leaf oa-pump-bias-current-high-alarm {
                   type string;
                   description "OA pump bias current high alarm";
                 }
                 leaf oa-pump-bias-current-low-alarm {
                   type string;
                   description "OA pump bias current low alarm";
                 }
                 leaf oa-pump-bias-current-high-warning {
                   type string;
                   description "OA pump bias current high warning";
                 }
                 leaf oa-pump-bias-current-low-warning {
                   type string;
                   description "OA pump bias current low warning";
                 }
                 leaf tx-jitter-pll-lol-input-nw-lane {
                   type string;
                   description "Tx jitter PLL LOL i/p nw lane";
                 }
                 leaf tx-out-of-alignment {
                   type string;
                   description "TX out of alignment";
                 }
                 leaf tx-cmu-lock-fault {
                   type string;
                   description "Tx CMU lock fault";
                 }
                 leaf adc-signal-below-threshold {
                   type string;
                   description "ADC signal below threshold";
                 }
                 leaf tx-output-power-adjustment-fault {
                   type string;
                   description "Tx output power adjustment fault";
                 }
                 leaf tx-output-mod-converge-fault {
                   type string;
                   description "TX output mod converge fault";
                 }
                 leaf tx-laser-ready-fault {
                   type string;
                   description "Tx laser ready fault";
                 }
                 leaf tx-laser-ready-off-fault {
                   type string;
                   description "Tx laser ready off fault";
                 }
                 leaf tx-asic-ready-fault {
                   type string;
                   description "Tx asic ready fault";
                 }
                 leaf tx-initialization-fault {
                   type string;
                   description "Tx initialization fault";
                 }
                 leaf rx-demodulator-lock-fault {
                   type string;
                   description "Rx demodulator lock fault";
                 }
                 leaf rx-dispersion-lock-fault {
                   type string;
                   description "Rx dispersion lock fault";
                 }
                 leaf rx-adc-output-fault {
                   type string;
                   description "Rx ADC output fault";
                 }
                 leaf rx-optical-input-fault {
                   type string;
                   description "Rx optical input fault";
                 }
                 leaf rx-asic-ready-fault {
                   type string;
                   description "Rx asic ready fault";
                 }
                 leaf rx-initialization-fault {
                   type string;
                   description "Rx initialization fault";
                 }
                 leaf tx-mod-bias-high-alarm {
                   type string;
                   description "TX modulator bias high alarm";
                 }
                 leaf tx-mod-bias-low-alarm {
                   type string;
                   description "TX modulator bias low alarm";
                 }
                 leaf tx-mod-bias-high-warning {
                   type string;
                   description "TX modulator bias high warning";
                 }
                 leaf tx-mod-bias-low-warning {
                   type string;
                   description "TX modulator bias low warning";
                 }
                 leaf rx-pwr-high-alarm {
                   type string;
                   description "RX power high alarm";
                 }
                 leaf rx-pwr-low-alarm {
                   type string;
                   description "RX power low alarm";
                 }
                 leaf rx-pwr-high-warn {
                   type string;
                   description "RX power high warning";
                 }
                 leaf rx-pwr-low-warn {
                   type string;
                   description "RX power low warning";
                 }
                 leaf tx-laser-power-high-alarm {
                   type string;
                   description "TX laser power high alarm";
                 }
                 leaf tx-laser-power-low-alarm {
                   type string;
                   description "TX laser power low alarm";
                 }
                 leaf tx-laser-power-high-warn {
                   type string;
                   description "TX laser power high warning";
                 }
                 leaf tx-laser-power-low-warn {
                   type string;
                   description "TX laser power low warning";
                 }
                 leaf tx-bias-high-alarm {
                   type string;
                   description "TX laser current high alarm";
                 }
                 leaf tx-bias-low-alarm {
                   type string;
                   description "TX laser current low alarm";
                 }
                 leaf tx-bias-high-warn {
                   type string;
                   description "TX laser current high warning";
                 }
                 leaf tx-bias-low-warn {
                   type string;
                   description "TX laser current low warning";
                 }
                 leaf tx-laser-temp-high-alarm {
                   type string;
                   description "TX laser temperature high alarm";
                 }
                 leaf tx-laser-temp-low-alarm {
                   type string;
                   description "TX laser temperature low alarm";
                 }
                 leaf tx-laser-temp-high-warn {
                   type string;
                   description "TX laser temperature high warning";
                 }
                 leaf tx-laser-temp-low-warn {
                   type string;
                   description "TX laser temperature low warning";
                 }
               }
             }
             list optics-diagnostics-vendor-extension {
               leaf optics-vendor-part-number {
                 type string;
                 description "Optics component vendor part number";
               }
               leaf optics-vendor-material-number {
                 type string;
                 description "Optic component vendor material number";
               }
             }
           }
         }
         container peer-configuration-status {
           leaf peer-nonmatching-dlci {
             type int32;
             description "DCE end DLCIs that does not match the DTE";
           }
         }
         container lsi-traffic-statistics {
           leaf input-bytes {
             type int32;
           }
           leaf input-bps {
             type int32;
           }
           leaf input-packets {
             type int32;
           }
           leaf input-pps {
             type int32;
           }
         }
         container stp-traffic-statistics {
           leaf stp-input-bytes-dropped {
             type int32;
             description "Drop statistics due to stp state at ingress in bytes";
           }
           leaf stp-output-bytes-dropped {
             type int32;
             description "Drop statistics due to stp state at egress in bytes";
           }
           leaf stp-input-packets-dropped {
             type int32;
             description "Drop statistics due to stp state at ingress in packets";
           }
           leaf stp-output-packets-dropped {
             type int32;
             description "Drop statistics due to stp state at egress in packets";
           }
         }
         container af-fe-info {
         }
         container af-fe-q-pkts {
         }
         container af-fe-q-bytes {
         }
         container chassis-queue-counters {
           container interface-chassis-cos-summary {
             leaf intf-cos-chassis-num-queues-supported {
               type int32;
               description "Number of Packet Forwarding Engine chassis queues the interface supports";
             }
             leaf intf-cos-chassis-num-queues-in-use {
               type int32;
               description "Number of Packet Forwarding Engine chassis queues in use on the interface";
             }
           }
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container otn-oc-information {
           list media-alarm {
             leaf media-alarm-name {
               type string;
             }
             leaf media-alarm-seconds {
               type int32;
             }
             leaf media-alarm-count {
               type int32;
             }
             leaf media-alarm-state {
               type string;
             }
           }
         }
         container otn-otu-information {
           list media-alarm {
             leaf media-alarm-name {
               type string;
             }
             leaf media-alarm-seconds {
               type int32;
             }
             leaf media-alarm-count {
               type int32;
             }
             leaf media-alarm-state {
               type string;
             }
           }
         }
         container otn-odu-information {
           list media-alarm {
             leaf media-alarm-name {
               type string;
             }
             leaf media-alarm-seconds {
               type int32;
             }
             leaf media-alarm-count {
               type int32;
             }
             leaf media-alarm-state {
               type string;
             }
           }
         }
         container otn-ot-module-information {
           list media-alarm {
             leaf media-alarm-name {
               type string;
             }
             leaf media-alarm-seconds {
               type int32;
             }
             leaf media-alarm-count {
               type int32;
             }
             leaf media-alarm-state {
               type string;
             }
           }
         }
         list otn-odu-tcm-information {
           list media-alarm {
             leaf media-alarm-name {
               type string;
             }
             leaf media-alarm-seconds {
               type int32;
             }
             leaf media-alarm-count {
               type int32;
             }
             leaf media-alarm-state {
               type string;
             }
           }
         }
         container ima-group-information {
         }
         container ima-link-information {
         }
         container ethernet-mac-pfc-statistics {
           leaf mac-pfc-dot1p {
             type int32;
           }
           leaf input-mac-pfc-frames {
             type int32;
           }
           leaf output-mac-pfc-frames {
             type int32;
           }
         }
         container cos-information {
           list cos-stream-information {
           }
           container cos-forwarding-class-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-forwarding-class-map-information {
             container fc-map {
               list fc-map-item {
                 leaf fc-name {
                   type string;
                   description "Class-of-service forwarding class name";
                 }
                 leaf fc-number {
                   type uint32;
                   description "Identifier for Class-of-service forwarding class";
                 }
                 leaf fc-queue-number {
                   type uint32;
                   description "Class-of-service forwarding class queue number";
                 }
                 leaf fc-rqueue-number {
                   type uint32;
                   description "Class-of-service forwarding class restricted queue number";
                 }
                 leaf fc-priority {
                   type string;
                   description "Class-of-service forwarding class queue priority";
                 }
                 leaf fc-policing-priority {
                   type string;
                   description "Class-of-service forwarding class policing priority";
                 }
                 leaf fc-spu-priority {
                   type string;
                   description "Class-of-service forwarding class spu priority";
                 }
                 leaf fc-no-loss {
                   type string;
                   description "Class-of-service forwarding class no-loss";
                 }
                 leaf fc-pfc-priority {
                   type uint32;
                   description "Class-of-service forwarding class pfc-priority";
                 }
                 leaf fc-multicast {
                   type string;
                   description "Class-of-service forwarding class multicast";
                 }
               }
             }
           }
           container cos-classifier-information {
             list classifier {
               leaf classifier-name {
                 type string;
                 description "Class-of-service classifier name";
               }
               leaf code-point-type {
                 type string;
                 description "Class-of-service code point type";
               }
               leaf table-index {
                 type uint32;
                 description "Table index";
               }
               container classifier-map {
                 list classifier-map-item {
                   leaf code-point {
                     type string;
                     description "Class-of-service code point alias name or bits";
                   }
                   leaf fc-name {
                     type string;
                     description "Class-of-service forwarding class name";
                   }
                   leaf loss-priority {
                     type string;
                     description "Class-of-service loss priority";
                   }
                   leaf cntag-present {
                     type string;
                     description "Class-of-service cntag present";
                   }
                 }
               }
             }
           }
           container cos-loss-priority-map-information {
             list loss-priority-map {
               leaf loss-priority-map-name {
                 type string;
                 description "Name of class-of-service loss priority map";
               }
               leaf code-point-type {
                 type string;
                 description "Class-of-service code point type";
               }
               leaf table-index {
                 type uint32;
                 description "Table index";
               }
               list loss-priority-map-table {
                 list loss-priority-map-item {
                   leaf code-point {
                     type string;
                     description "Class-of-service code point alias name or bits";
                   }
                   leaf loss-priority {
                     type string;
                     description "Class-of-service loss priority";
                   }
                 }
                 list loss-priority-map-table-entry {
                   leaf table-index {
                     type uint32;
                     description "Table index";
                   }
                   leaf code-point {
                     type string;
                     description "Class-of-service code point alias name or bits";
                   }
                   leaf loss-priority {
                     type string;
                     description "Class-of-service loss priority";
                   }
                 }
               }
             }
           }
           container cos-drop-profile-information {
             list drop-profile {
               leaf profile-name {
                 type string;
                 description "Class-of-service drop profile name";
               }
               leaf profile-type {
                 type string;
                 description "Class-of-service drop profile type";
               }
               leaf table-index {
                 type uint32;
                 description "Table index";
               }
               container profile-map {
                 container profile-map-item {
                   leaf fill-level {
                     type uint32;
                     description "Class-of-service drop profile fill level value";
                   }
                   leaf probability {
                     type uint32;
                     description "Class-of-service drop profile probability value";
                   }
                 }
               }
             }
           }
           container cos-mpls-ecn-map-information {
             list cos-mpls-ecn-map-info {
               leaf ecn-capable-exp {
                 type int32;
                 description "ECN capable exp";
               }
               leaf congestion-experienced-exp {
                 type int32;
                 description "Congestion Expereienced exp";
               }
             }
           }
           container cos-monitoring-profile-information {
             list monitoring-profile {
               leaf monitoring-profile-name {
                 type string;
                 description "Class-of-service monitoring profile name";
               }
               container export-filters {
                 container export-filter {
                   leaf filter-name {
                     type string;
                     description "Class-of-service monitoring profile filter name";
                   }
                   leaf monitoring-queue-number {
                     type uint32;
                     description "Class-of-service monitoring profile filter queue value";
                   }
                   leaf peak-queue-length-value {
                     type uint32;
                     description "Class-of-service monitoring profile peak queue length value";
                   }
                 }
               }
             }
           }
           container cos-rewrite-information {
             list rewrite {
               leaf rewrite-name {
                 type string;
                 description "Class-of-service rewrite rule name";
               }
               leaf code-point-type {
                 type string;
                 description "Class-of-service code point type";
               }
               leaf table-index {
                 type uint32;
                 description "Table index";
               }
               container rewrite-map {
                 list rewrite-map-item {
                   leaf fc-name {
                     type string;
                     description "Class-of-service forwarding class name";
                   }
                   leaf loss-priority {
                     type string;
                     description "Class-of-service loss priority";
                   }
                   leaf code-point {
                     type string;
                     description "Class-of-service code point alias name or bits";
                   }
                 }
               }
             }
           }
           container cos-loss-priority-rewrite-information {
             list loss-priority-rewrite {
               leaf loss-priority-rewrite-name {
                 type string;
                 description "Name of class-of-service loss priority rewrite";
               }
               leaf code-point-type {
                 type string;
                 description "Class-of-service code point type";
               }
               leaf table-index {
                 type uint32;
                 description "Table index";
               }
               list loss-priority-rewrite-table {
                 list loss-priority-rewrite-item {
                   leaf loss-priority {
                     type string;
                     description "Class-of-service loss priority";
                   }
                   leaf code-point {
                     type string;
                     description "Class-of-service code point alias name or bits";
                   }
                 }
                 list loss-priority-rewrite-table-entry {
                   leaf table-index {
                     type uint32;
                     description "Table index";
                   }
                   leaf loss-priority {
                     type string;
                     description "Class-of-service loss priority";
                   }
                   leaf code-point {
                     type string;
                     description "Class-of-service code point alias name or bits";
                   }
                 }
               }
             }
           }
           container cos-code-point-map-information {
             list code-point-map {
               leaf code-point-type {
                 type string;
                 description "Class-of-service code point type";
               }
               container alias-map {
                 list alias-map-item {
                   leaf code-point-alias {
                     type string;
                     description "Class-of-service code point alias name";
                   }
                   leaf code-point-bits {
                     type string;
                     description "Class-of-service code point bit sequence";
                   }
                 }
               }
             }
           }
           container cos-fragmentation-map-information {
             list fragmentation-map {
               leaf fragmentation-map-name {
                 type string;
                 description "Class-of-service fragmentation map name";
               }
               leaf fragmentation-map-index {
                 type uint32;
                 description "Index number for Class-of-service fragmentation map";
               }
               list fragment-map {
                 leaf fc-name {
                   type string;
                   description "Class-of-service forwarding class name";
                 }
                 leaf no-fragmentation {
                   type empty;
                   description "Do not fragment packets of this class";
                 }
                 leaf fragment-threshold {
                   type string;
                   description "Fragmentation threshold";
                 }
                 leaf fragment-multilink-class {
                   type int32;
                   description "Identifier for multilink class";
                 }
               }
             }
           }
           container cos-translation-table-map-information {
             list translation-table {
               leaf translation-table-name {
                 type string;
                 description "Class-of-service translation table name";
               }
               leaf translation-table-type {
                 type string;
                 description "Class-of-service translation table type";
               }
               leaf table-index {
                 type uint32;
                 description "Table index";
               }
               container translation-table-map {
                 container translation-table-map-item {
                   leaf from-code-point {
                     type string;
                     description "Class-of-service code point alias name or bits";
                   }
                   leaf to-code-point {
                     type string;
                     description "Class-of-service code point alias name or bits";
                   }
                 }
               }
               list translation-table-entry {
                 leaf table-index {
                   type uint32;
                   description "Table index";
                 }
                 leaf from-code-point {
                   type string;
                   description "Class-of-service code point alias name or bits";
                 }
                 leaf to-code-point {
                   type string;
                   description "Class-of-service code point alias name or bits";
                 }
               }
             }
           }
           container cos-multi-destination-information {
             container sm-md-map {
               leaf scheduler-map-name {
                 type string;
                 description "Class-of-service scheduler map name";
               }
               leaf scheduler-map-index {
                 type uint64;
                 description "Class-of-service scheduler map index";
               }
             }
             container fc-md-map {
               leaf fc-name {
                 type string;
                 description "Class-of-service forwarding class name";
               }
               leaf fc-queue-number {
                 type uint32;
                 description "Class-of-service forwarding class queue number";
               }
             }
             container cls-md-map {
               leaf multidest-classifier-name {
                 type string;
                 description "Multi destination classifier name";
               }
               leaf multidest-classifier-type {
                 type string;
                 description "Multi destination classifier type";
               }
               leaf multidest-classifier-index {
                 type uint32;
                 description "Multi destination classifier id";
               }
             }
           }
           container cos-forwarding-class-set-information {
             list forwarding-class-set {
               list forwarding-class-set-entry {
                 leaf forwarding-class-set-name {
                   type string;
                   description "Class-of-service forwarding class set name";
                 }
                 leaf forwarding-class-set-type {
                   type string;
                   description "Identifier for Class-of-service forwarding class set type";
                 }
                 leaf forwarding-class-set-index {
                   type uint32;
                   description "Identifier for Class-of-service forwarding class set";
                 }
                 container fc-map {
                   list fc-map-item {
                     leaf fc-name {
                       type string;
                       description "Class-of-service forwarding class name";
                     }
                     leaf fc-number {
                       type uint32;
                       description "Identifier for Class-of-service forwarding class";
                     }
                     leaf fc-queue-number {
                       type uint32;
                       description "Class-of-service forwarding class queue number";
                     }
                     leaf fc-rqueue-number {
                       type uint32;
                       description "Class-of-service forwarding class restricted queue number";
                     }
                     leaf fc-priority {
                       type string;
                       description "Class-of-service forwarding class queue priority";
                     }
                     leaf fc-policing-priority {
                       type string;
                       description "Class-of-service forwarding class policing priority";
                     }
                     leaf fc-spu-priority {
                       type string;
                       description "Class-of-service forwarding class spu priority";
                     }
                     leaf fc-no-loss {
                       type string;
                       description "Class-of-service forwarding class no-loss";
                     }
                     leaf fc-pfc-priority {
                       type uint32;
                       description "Class-of-service forwarding class pfc-priority";
                     }
                     leaf fc-multicast {
                       type string;
                       description "Class-of-service forwarding class multicast";
                     }
                   }
                 }
               }
             }
           }
           container cos-policy-map-information {
             list policy-map {
               leaf policy-map-name {
                 type string;
                 description "Class-of-service Policy-map name";
               }
               leaf table-index {
                 type uint32;
                 description "Table index";
               }
               leaf policy-map-user-attribute {
                 type uint32;
                 description "User-defined attribute";
               }
               container policy-map-cp-entries {
                 leaf code-point-type {
                   type string;
                   description "Class-of-service code point type";
                 }
                 leaf code-point {
                   type string;
                   description "Class-of-service code point alias name or bits";
                 }
                 leaf code-point-option {
                   type string;
                   description "Class-of-service code point option flag";
                 }
               }
             }
           }
           container cos-client-info {
             list cos-client {
               leaf cos-client-info-internal-id {
                 type uint32;
                 description "Junos client internal identifier";
               }
               leaf cos-client-info-requests {
                 type uint32;
                 description "Number of requests from Junos client";
               }
               leaf cos-client-info-responses {
                 type uint32;
                 description "Number of responses to Junos client";
               }
               leaf cos-client-info-failures {
                 type uint32;
                 description "Number of failures while handling Junos client requests";
               }
               leaf cos-client-info-identifier {
                 type string;
                 description "Junos client identifier";
               }
               leaf cos-client-name {
                 type string;
                 description "Junos client name";
               }
               leaf cos-client-state {
                 type string;
                 description "Junos client state information";
               }
               leaf cos-client-internal-name {
                 type string;
                 description "Junos client internal name";
               }
               leaf cos-client-stats {
                 type string;
                 description "Junos client statistics";
               }
               leaf cos-client-failure-stats {
                 type string;
                 description "Junos client failure/error statistics";
               }
               leaf cos-client-validate-failures {
                 type uint32;
                 description "Junos client request validation failures";
               }
               leaf cos-client-ownership-failures {
                 type uint32;
                 description "Junos client ownership validation failures";
               }
               leaf cos-client-info-name {
                 type string;
                 description "CoS client name";
               }
               leaf cos-client-internal-id {
                 type uint32;
                 description "Junos client internal identifier";
               }
               leaf cos-client-requests {
                 type uint64;
                 description "Number of requests from Junos client";
               }
               leaf cos-client-responses {
                 type uint64;
                 description "Number of responses to Junos client";
               }
               leaf cos-client-failures {
                 type uint64;
                 description "Number of failures while handling Junos client requests";
               }
               leaf cos-client-identifier {
                 type string;
                 description "Junos client identifier";
               }
               leaf cos-client-status {
                 type string;
                 description "Junos client status";
               }
               leaf cos-client-connected-time {
                 type string;
                 description "Junos client time of connect";
               }
               leaf cos-client-reconnected-time {
                 type string;
                 description "Junos client time of reconnect";
               }
               leaf cos-client-disconnected-time {
                 type string;
                 description "Junos client time of disconnect";
               }
               leaf cos-client-message-type {
                 type string;
                 description "Junos client message type";
               }
               leaf cos-client-operation-type {
                 type string;
                 description "Junos client operation type";
               }
               leaf-list cos-bind-point-type {
                 type string;
                 description "Class-of-service bind point type";
               }
               leaf-list cos-bind-point-owner-type {
                 type string;
                 description "Class-of-service bind point owner type";
               }
               leaf-list cos-bind-point-owner-internal-id {
                 type uint32;
                 description "Junos client internal identifier";
               }
               leaf-list cos-bind-point-name {
                 type string;
                 description "Class-of-service bind point name";
               }
               leaf cos-bind-point-feature {
                 type string;
                 description "Class-of-service bind point feature name";
               }
               leaf cos-bind-point-feature-object-name {
                 type string;
                 description "Class-of-service bind point feature object name";
               }
             }
           }
           container cos-host-outbound-info {
             list cos-host-outbound-traffic-info {
               leaf cos-host-outbound-traffic-protocol-name {
                 type string;
                 description "CoS host outbound traffic protocol name";
               }
               leaf cos-host-outbound-traffic-dscp {
                 type string;
                 description "CoS host outbound traffic dscp";
               }
               leaf cos-host-outbound-traffic-dot1p {
                 type string;
                 description "CoS host outbound traffic ieee 802.1p";
               }
               leaf cos-host-outbound-traffic-fc-id {
                 type string;
                 description "CoS host outbound traffic forwarding class id";
               }
               leaf cos-host-outbound-traffic-queue-id {
                 type string;
                 description "CoS host outbound traffic queue id";
               }
               leaf cos-host-outbound-traffic-restrict-queue-id {
                 type string;
                 description "CoS host outbound traffic restrict queue id";
               }
               leaf cos-host-outbound-traffic-override-firewall {
                 type string;
                 description "CoS host outbound traffic override firwall action";
               }
               leaf cos-host-outbound-traffic-rw-dot1p {
                 type string;
                 description "CoS host outbound traffic - use ieee 802.1p rewrite rules";
               }
             }
           }
           container cos-drop-congestion-notification-information {
             list cos-drop-congestion-notification-info {
               leaf cos-dcn-fc-name {
                 type string;
                 description "Cos DCN forwarding class";
               }
               leaf cos-dcn-udp-port {
                 type int32;
                 description "Cos DCN udp port number";
               }
             }
           }
           container cos-dedicated-buffer-profile-information {
             list dedicated-buffer-profile {
               leaf dedicated-buffer-profile-name {
                 type string;
                 description "Class-of-service dedicated buffer profile name";
               }
               leaf dedicated-buffer-profile-index {
                 type int32;
                 description "Class-of-service dedicated buffer profile index";
               }
               leaf ingress-buffer-size {
                 type string;
                 description "Ingress per port dedicated buffer in cells";
               }
               leaf egress-buffer-size {
                 type string;
                 description "Egress per port dedicated buffer in cells";
               }
             }
           }
           container cos-dynamic-threshold-profile-information {
             list dynamic-threshold-profile {
               leaf dynamic-threshold-profile-name {
                 type string;
                 description "Class-of-service dynamic threshold profile name";
               }
               leaf dynamic-threshold-profile-index {
                 type uint64;
                 description "Class-of-service dynamic threshold profile index";
               }
               list dynamic-threshold-profile-entry {
                 leaf dynamic-threshold-profile-priority-group {
                   type string;
                   description "Class-of-service dynamic threshold profile priority group";
                 }
                 leaf dynamic-threshold-profile-threshold-value {
                   type uint32;
                   description "Class-of-service dynamic threshold profile threshold value";
                 }
               }
             }
           }
           container cos-decn-profile-information {
             list decn-profile {
               leaf decn-profile-name {
                 type string;
                 description "Class-of-service decn profile name";
               }
               leaf decn-profile-index {
                 type uint64;
                 description "Class-of-service decn profile index";
               }
               list decn-profile-queue {
                 leaf dynamic-explicit-congestion-notification-queue {
                   type uint32;
                   description "Class-of-service DECN queue";
                 }
                 leaf dynamic-explicit-congestion-notification-offset {
                   type uint32;
                   description "Class-of-service DECN offset";
                 }
                 leaf dynamic-explicit-congestion-notification-floor {
                   type uint32;
                   description "Class-of-service DECN floor";
                 }
               }
             }
           }
           container cos-scheduler-map-information {
             list scheduler-map {
               leaf scheduler-map-name {
                 type string;
                 description "Class-of-service scheduler map name";
               }
               leaf scheduler-map-index {
                 type uint64;
                 description "Class-of-service scheduler map index";
               }
               leaf user-plane-name {
                 type string;
                 description "Class-of-service user-plane name for XDA";
               }
               list scheduler {
                 leaf scheduler-name {
                   type string;
                   description "Class-of-service scheduler name";
                 }
                 leaf fc-name {
                   type string;
                   description "Class-of-service forwarding class name";
                 }
                 leaf scheduler-index {
                   type uint64;
                   description "Class of service scheduler index";
                 }
                 leaf scheduler-tx-rate {
                   type string;
                   description "Class-of-service scheduler transmit rate";
                 }
                 leaf scheduler-tx-limit {
                   type string;
                   description "Class-of-service scheduler transmit limit";
                 }
                 leaf scheduler-buffer-size {
                   type string;
                   description "Class-of-service scheduler buffer size";
                 }
                 leaf scheduler-buffer-multicast-share {
                   type uint32;
                   description "Class-of-service scheduler multicast buffer share";
                 }
                 leaf scheduler-buffer-limit {
                   type string;
                   description "Class-of-service scheduler buffer limit";
                 }
                 leaf scheduler-buffer-rate {
                   type string;
                   description "Class-of-service scheduler buffer rate";
                 }
                 leaf scheduler-shared-buffer-maximum-percentage {
                   type uint32;
                   description "Shared Buffer maximum percentage";
                 }
                 leaf scheduler-shared-buffer-multicast-maximum-percentage {
                   type uint32;
                   description "Shared Buffer multicast maximum percentage";
                 }
                 leaf scheduler-buffer-dynamic-threshold {
                   type uint32;
                   description "Queue shared-buffer dynamic threshold";
                 }
                 leaf scheduler-priority {
                   type string;
                   description "Class-of-service scheduler priority";
                 }
                 leaf scheduler-shaping-rate {
                   type string;
                   description "Class-of-service scheduler shaping rate";
                 }
                 leaf scheduler-shaping-rate-burst {
                   type string;
                   description "Class-of-service scheduler shaping rate burst";
                 }
                 leaf scheduler-adjust-minimum {
                   type int32;
                   description "Class-of-service scheduler adjustment minimum rate";
                 }
                 leaf scheduler-adjust-percent {
                   type int32;
                   description "Class-of-service scheduler percent adjustment for a queue";
                 }
                 leaf scheduler-excess-priority {
                   type string;
                   description "Class-of-service scheduler excess priority";
                 }
                 leaf scheduler-excess-rate {
                   type string;
                   description "Class-of-service scheduler excess rate";
                 }
                 leaf scheduler-explicit-congestion-notification {
                   type string;
                   description "Class-of-service ECN status of queue";
                 }
                 leaf scheduler-ecn-rtlog-rate-limit {
                   type uint32;
                   description "Class-of-service ECN Security Log Rate Limit";
                 }
                 leaf scheduler-ecn-no-pfc-assist {
                   type string;
                   description "Class-of-service ECN no pfc assist";
                 }
                 leaf scheduler-queue-monitoring {
                   type string;
                   description "Class-of-service queue depth monitoring of queue";
                 }
                 leaf scheduler-drop-profile-ln-index {
                   type uint32;
                   description "Class-of-service scheduler drop profile index low, non-TCP";
                 }
                 leaf scheduler-drop-profile-ln {
                   type string;
                   description "Class-of-service scheduler drop profile low, non-TCP";
                 }
                 leaf scheduler-drop-profile-lt-index {
                   type uint32;
                   description "Class-of-service scheduler drop profile index low, TCP";
                 }
                 leaf scheduler-drop-profile-lt {
                   type string;
                   description "Class-of-service scheduler drop profile low, TCP";
                 }
                 leaf scheduler-drop-profile-hn-index {
                   type uint32;
                   description "Class-of-service scheduler drop profile index high, non-TCP";
                 }
                 leaf scheduler-drop-profile-hn {
                   type string;
                   description "Class-of-service scheduler drop profile high, non-TCP";
                 }
                 leaf scheduler-drop-profile-ht-index {
                   type uint32;
                   description "Class-of-service scheduler drop profile index high, TCP";
                 }
                 leaf scheduler-drop-profile-ht {
                   type string;
                   description "Class-of-service scheduler drop profile high, TCP";
                 }
                 leaf scheduler-drop-profile-la-index {
                   type uint32;
                   description "Class-of-service scheduler drop profile index low";
                 }
                 leaf scheduler-drop-profile-la {
                   type string;
                   description "Class-of-service scheduler drop profile low";
                 }
                 leaf scheduler-drop-profile-ma-index {
                   type uint32;
                   description "Class-of-service scheduler drop profile index medium";
                 }
                 leaf scheduler-drop-profile-ma {
                   type string;
                   description "Class-of-service scheduler drop profile medium";
                 }
                 leaf scheduler-drop-profile-mla-index {
                   type uint32;
                   description "Class-of-service scheduler drop profile index medium-low";
                 }
                 leaf scheduler-drop-profile-mla {
                   type string;
                   description "Class-of-service scheduler drop profile medium-low";
                 }
                 leaf scheduler-drop-profile-mha-index {
                   type uint32;
                   description "Class-of-service scheduler drop profile index medium-high";
                 }
                 leaf scheduler-drop-profile-mha {
                   type string;
                   description "Class-of-service scheduler drop profile medium-high";
                 }
                 leaf scheduler-drop-profile-ha-index {
                   type uint32;
                   description "Class-of-service scheduler drop profile index high";
                 }
                 leaf scheduler-drop-profile-ha {
                   type string;
                   description "Class-of-service scheduler drop profile high";
                 }
               }
             }
           }
           container cos-traffic-control-profile-information {
             list traffic-control-profile {
               leaf traffic-control-profile-name {
                 type string;
                 description "Class-of-service traffic control profile name";
               }
               leaf traffic-control-profile-index {
                 type uint64;
                 description "Index number for Class-of-service traffic control profile";
               }
               leaf user-plane-name {
                 type string;
                 description "Class-of-service user-plane name for XDA";
               }
               leaf scheduler-map-name {
                 type string;
                 description "Class-of-service scheduler map name";
               }
               leaf atm-service {
                 type string;
                 description "Class-of-service traffic control profile atm service";
               }
               leaf shaping-rate {
                 type uint64;
                 description "Class-of-service shaping rate";
               }
               leaf shaping-rate-burst {
                 type uint32;
                 description "Class-of-service shaping rate burst, in bytes";
               }
               leaf low-granularity {
                 type uint32;
                 description "Class-of-service low-granularity mode support";
               }
               leaf queue-mode-4q {
                 type uint32;
                 description "Class-of-service tcp-voq-mode(4Q) mode support";
               }
               leaf shaping-rate-priority-strict-high {
                 type uint64;
                 description "Class-of-service shaping rate for priority strict high";
               }
               leaf shaping-rate-priority-strict-high-burst {
                 type uint32;
                 description "Class-of-service shaping rate burst for priority strict-high";
               }
               leaf shaping-rate-priority-high {
                 type uint64;
                 description "Class-of-service shaping rate for priority high";
               }
               leaf shaping-rate-priority-high-burst {
                 type uint32;
                 description "Class-of-service shaping rate for priority high burst";
               }
               leaf shaping-rate-priority-medium {
                 type uint64;
                 description "Class-of-service shaping rate for priority medium";
               }
               leaf shaping-rate-priority-medium-burst {
                 type uint32;
                 description "Class-of-service shaping rate for priority medium burst";
               }
               leaf shaping-rate-priority-medium-low {
                 type uint64;
                 description "Class-of-service shaping rate for priority medium-low";
               }
               leaf shaping-rate-priority-medium-low-burst {
                 type uint32;
                 description "Class-of-service shaping rate burst for priority medium-low";
               }
               leaf shaping-rate-priority-low {
                 type uint64;
                 description "Class-of-service shaping rate for priority low";
               }
               leaf shaping-rate-priority-low-burst {
                 type uint32;
                 description "Class-of-service shaping rate for priority low burst";
               }
               leaf shaping-rate-excess-high {
                 type uint64;
                 description "Class-of-service shaping rate for excess high";
               }
               leaf shaping-rate-excess-high-burst {
                 type uint32;
                 description "Class-of-service shaping rate for excess high burst";
               }
               leaf shaping-rate-excess-medium-high {
                 type uint64;
                 description "Class-of-service shaping rate for excess medium-high";
               }
               leaf shaping-rate-excess-medium-high-burst {
                 type uint32;
                 description "Class-of-service shaping rate burst for excess medium-high";
               }
               leaf shaping-rate-excess-medium-low {
                 type uint64;
                 description "Class-of-service shaping rate for excess medium-low";
               }
               leaf shaping-rate-excess-medium-low-burst {
                 type uint32;
                 description "Class-of-service shaping rate burst for excess medium-low";
               }
               leaf shaping-rate-excess-low {
                 type uint64;
                 description "Class-of-service shaping rate for excess low";
               }
               leaf shaping-rate-excess-low-burst {
                 type uint32;
                 description "Class-of-service shaping rate for excess low burst";
               }
               leaf guaranteed-rate {
                 type uint64;
                 description "Class-of-service guaranteed rate";
               }
               leaf guaranteed-rate-burst {
                 type uint32;
                 description "Class-of-service guaranteed rate burst, in bytes";
               }
               leaf delay-buffer-rate {
                 type uint64;
                 description "Class-of-service delay buffer rate";
               }
               leaf excess-rate {
                 type uint32;
                 description "Class-of-service excess rate";
               }
               leaf excess-rate-high {
                 type uint32;
                 description "Class-of-service excess rate for excess-high priority traffic";
               }
               leaf excess-rate-medium-high {
                 type uint32;
                 description "Class-of-service excess rate for excess-medium-high priority traffic";
               }
               leaf excess-rate-medium-low {
                 type uint32;
                 description "Class-of-service excess rate for excess-medium-low priority traffic";
               }
               leaf excess-rate-low {
                 type uint32;
                 description "Class-of-service excess rate for excess-low priority traffic";
               }
               leaf adjust-minimum {
                 type uint64;
                 description "Class-of-service adjustment minimum rate";
               }
               leaf overhead-bytes {
                 type int32;
                 description "Class-of-service Overhead bytes";
               }
               leaf frame-mode-bytes {
                 type int32;
                 description "Class-of-service overhead bytes when in frame-mode";
               }
               leaf cell-mode-bytes {
                 type int32;
                 description "Class-of-service overhead bytes when in cell-mode";
               }
               leaf overhead-accounting-mode {
                 type string;
                 description "Class-of-service Overhead Accounting Mode";
               }
               list traffic-control-profile-instance {
                 leaf traffic-control-profile-instance-name {
                   type string;
                   description "Class-of-service traffic control profile instance";
                 }
                 leaf traffic-control-profile-instance-index {
                   type uint32;
                   description "Index number for Class-of-service traffic control profile instance";
                 }
                 leaf instance-reference-count {
                   type uint32;
                   description "Instance reference count";
                 }
               }
             }
           }
           container cos-routing-instance-information {
             list routing-instance-map {
               leaf routing-instance-name {
                 type string;
                 description "Name of class-of-service routing instance";
               }
               list i-logical-map {
                 leaf i-logical-name {
                   type string;
                   description "Class-of-service logical interface name";
                 }
                 leaf i-logical-index {
                   type uint32;
                   description "Class-of-service logical interface index";
                 }
                 leaf monitoring-profile-map-name {
                   type string;
                   description "Monitoring Profile Name";
                 }
                 list cos-objects {
                   leaf cos-object-type {
                     type string;
                     description "Class-of-service object type";
                   }
                   leaf cos-object-name {
                     type string;
                     description "Class-of-service object name";
                   }
                   leaf cos-object-subtype {
                     type string;
                     description "Class-of-service object subtype";
                   }
                   leaf cos-object-index {
                     type uint64;
                     description "Class-of-service object index";
                   }
                 }
               }
             }
           }
           container cos-fabric-scheduler-map-information {
             container fabric-scheduler-map {
               list fabric-scheduler {
                 leaf fabric-scheduler-name {
                   type string;
                   description "Class-of-service scheduler name";
                 }
                 leaf fabric-scheduler-index {
                   type uint32;
                   description "Class of service scheduler index";
                 }
                 leaf fabric-scheduler-drop-profile-ln-index {
                   type uint32;
                   description "Class-of-service scheduler drop profile index low, non-TCP";
                 }
                 leaf fabric-scheduler-drop-profile-ln {
                   type string;
                   description "Class-of-service scheduler drop profile low, non-TCP";
                 }
                 leaf fabric-scheduler-drop-profile-lt-index {
                   type uint32;
                   description "Class-of-service scheduler drop profile index low, TCP";
                 }
                 leaf fabric-scheduler-drop-profile-lt {
                   type string;
                   description "Class-of-service scheduler drop profile low, TCP";
                 }
                 leaf fabric-scheduler-drop-profile-hn-index {
                   type uint32;
                   description "Class-of-service scheduler drop profile index high, non-TCP";
                 }
                 leaf fabric-scheduler-drop-profile-hn {
                   type string;
                   description "Class-of-service scheduler drop profile high, non-TCP";
                 }
                 leaf fabric-scheduler-drop-profile-ht-index {
                   type uint32;
                   description "Class-of-service scheduler drop profile index high, TCP";
                 }
                 leaf fabric-scheduler-drop-profile-ht {
                   type string;
                   description "Class-of-service scheduler drop profile high, TCP";
                 }
                 leaf fabric-scheduler-priority {
                   type string;
                 }
               }
             }
           }
           container cos-tcm-information {
             list tcm {
               leaf tcm-name {
                 type string;
                 description "Class-of-service traffic-class-map name";
               }
               leaf tcm-type {
                 type string;
                 description "Class-of-service traffic-class-map type";
               }
               leaf table-index {
                 type uint32;
                 description "Table index";
               }
               container tcm-map {
                 list tcm-map-item {
                   leaf code-point {
                     type string;
                     description "Class-of-service code point alias name or bits";
                   }
                   leaf tc-name {
                     type string;
                     description "Class-of-service traffic-class-map traffic-class name";
                   }
                 }
               }
             }
           }
         }
         container physical-interface-cos-information {
         }
         container precl-statistics {
           container precl-information {
           }
         }
         container mlfr-uni-nni-traffic-statistics {
           container bundle {
           }
         }
       }
       list logical-interface {
         leaf name {
           type string;
           description "Name of this item";
         }
         leaf admin-status {
           type string;
           description "Desired state of the interface";
         }
         leaf oper-status {
           type string;
           description "Current operational state of the interface";
         }
         leaf vrfname {
           type string;
           description "Routing instance name";
         }
         leaf zonename {
           type string;
           description "Zone name";
         }
         leaf subunit {
           type int32;
           description "Subunit for this interface";
         }
         leaf dialer-time-to-disconnect {
           type string;
           description "Time for dialer to disconnect due to idle timeout";
         }
         leaf lcp-state {
           type string;
           description "State of the Line Control Protocol";
         }
         leaf chap-state {
           type string;
           description "State of the Challenge Handshake Authentication Protocol";
         }
         leaf pap-state {
           type string;
           description "State of the Password Authentication Protocol";
         }
         container layer2-input-policer-information {
           leaf layer2-input-policer {
             type string;
             description "Name of the Layer 2 input policer";
           }
         }
         container layer2-output-policer-information {
           leaf layer2-output-policer {
             type string;
             description "Name of the Layer 2 output policer";
           }
         }
         container pppoe-information {
           list pppoe-interface {
             leaf state {
               type string;
               description "State";
             }
             leaf session-id {
               type string;
               description "Session ID";
             }
             leaf ac-name-session {
               type string;
               description "Session AC name";
             }
             leaf remote-mac {
               type string;
               description "Remote MAC address";
             }
             leaf ac-name-config {
               type string;
               description "Configured AC name";
             }
             leaf service-name {
               type string;
               description "Service name";
             }
             leaf auto-reconnect {
               type string;
               description "Autoreconnect timeout";
             }
             leaf idle-timeout {
               type string;
               description "Idle timeout";
             }
             leaf underlying-interface-name {
               type string;
               description "Underlying interface name";
             }
             leaf underlying-interface-index {
               type string;
               description "Underlying interface index";
             }
             leaf padg-credits {
               type int32;
               description "PADG transmit credits";
             }
             leaf pppoe-credit-scale-factor {
               type string;
               description "Scaling factor";
             }
             leaf ignore-eol-tag {
               type string;
               description "Ignore End-of-List TAG";
             }
             leaf ppp-max-payload-tag {
               type int32;
               description "PPP-Max-Payload TAG";
             }
             leaf interface-name {
               type string;
               description "Class-of-service interface name";
             }
             leaf interface-index {
               type uint32;
               description "Class-of-service interface index";
             }
             leaf aci-iflset-name {
               type string;
               description "ACI Interface Set name";
             }
             leaf aci-iflset-index {
               type string;
               description "ACI Interface Set index";
             }
             leaf ifl-type {
               type string;
               description "Type";
             }
             leaf session-uptime {
               type string;
               description "Duration for which the session has been up";
             }
             leaf dynamic-profile {
               type string;
               description "Dynamic Profile name";
             }
             leaf pppoe-credits {
               type string;
               description "Forwarding credit balances";
             }
             leaf dynamic-interface-bandwidth {
               type string;
               description "Dynamic interface bandwidth";
             }
             leaf agent-circuit-id {
               type string;
               description "Agent Circuit ID";
             }
             leaf agent-remote-id {
               type string;
               description "Agent Remote ID";
             }
             leaf padm-motm {
               type string;
               description "PADM Message of the Moment tag";
             }
             leaf padm-hurl {
               type string;
               description "PADM HTTP URL tag";
             }
           }
         }
         container pppoe-underlying-information {
           list pppoe-underlying-interface {
             leaf dynamic-profile {
               type string;
               description "Dynamic Profile name";
             }
             leaf service-name-table {
               type string;
               description "Name of Service Name Table";
             }
             leaf max-sessions {
               type int32;
               description "Maximum number of PPPoE sessions";
             }
             leaf max-sessions-vsa-ignore {
               type string;
               description "Ignore max-sessions VSA";
             }
             leaf duplicate-protection {
               type string;
               description "Duplicate protection mode";
             }
             leaf short-cycle-protection {
               type string;
               description "Short cycle protection mode";
             }
             leaf direct-connect {
               type string;
               description "Direct connect mode";
             }
             leaf ac-name {
               type string;
               description "Access Concentrator name";
             }
             leaf underlying-interface-name {
               type string;
               description "Underlying interface name";
             }
             leaf underlying-interface-index {
               type string;
               description "Underlying interface index";
             }
             leaf encapsulation-type-identifier {
               type string;
               description "Encapsulation type identifier";
             }
             leaf state {
               type string;
               description "State";
             }
             leaf active-sessions {
               type int32;
               description "Number of active PPPoE sessions";
             }
             leaf aci-autosensing {
               type string;
               description "ACI VLAN Autosensing mode";
             }
             leaf line-identity-autosensing {
               type string;
               description "Line Identity Autosensing mode";
             }
           }
         }
         container aci-vlan-information {
           leaf dynamic-profile {
             type string;
             description "Dynamic Profile name";
           }
         }
         container line-identity-information {
           leaf dynamic-profile {
             type string;
             description "Dynamic Profile name";
           }
           leaf circuit-id {
             type string;
             description "Aci vlan attribute";
           }
           leaf remote-id {
             type string;
             description "Aci vlan attribute";
           }
           leaf accept-no-ids {
             type string;
             description "Aci vlan attribute";
           }
         }
         container demux-information {
           container demux-interface {
             leaf demux-underlying-interface-name {
               type string;
               description "Underlying interface name";
             }
             leaf demux-underlying-interface-index {
               type string;
               description "Underlying interface index";
             }
             leaf demux-inet-prefix-type {
               type string;
               description "Prefix type";
             }
             leaf demux-inet-prefix-count {
               type string;
               description "IPv4 Prefix count";
             }
             leaf demux-inet-prefix {
               type string;
               description "IPv4 Prefix";
             }
             leaf demux-inet6-prefix-type {
               type string;
               description "Prefix type";
             }
             leaf demux-inet6-prefix-count {
               type string;
               description "IPv6 Prefix count";
             }
             leaf demux-inet6-prefix {
               type string;
               description "IPv6 Prefix";
             }
           }
         }
         container dual-ad-icl-color-information {
           container dual-ad-icl-color-info {
             leaf dual-ad-icl-color-type {
               type uint32;
               description "Dual-AD ICL Color Type";
             }
             leaf dual-ad-icl-color {
               type uint32;
               description "Dual-AD ICL Color";
             }
           }
         }
         container dialer-information {
           leaf dialer-time-to-disconnect {
             type string;
             description "Time for dialer to disconnect due to idle timeout";
           }
           container dialer-interface {
             leaf dialer-interface-name {
               type string;
               description "Interface name";
             }
             leaf dialer-interface-state {
               type string;
               description "Dialer interface state";
             }
             leaf pool-id {
               type string;
               description "Pool identifier";
             }
             leaf primary-interface {
               type string;
               description "Primary interface";
             }
             leaf activation-delay {
               type string;
               description "Activation delay";
             }
             leaf deactivation-delay {
               type string;
               description "Deactivation delay";
             }
             leaf activation-delay-elapsed {
               type string;
               description "Activation delay elapsed";
             }
             leaf deactivation-delay-elapsed {
               type string;
               description "Deactivation delay elapsed";
             }
             leaf call-idle-timeout {
               type string;
               description "Call idle timeout";
             }
             leaf initial-route-check {
               type string;
               description "Initial route check delay";
             }
             leaf redial-delay {
               type string;
               description "Delay before dialer dials out again (seconds)";
             }
             leaf callback-wait-period {
               type string;
               description "Delay before dialer attempts callback (seconds)";
             }
             leaf callback-wait-period-elapsed {
               type string;
               description "Number of seconds in callback wait period that have elapsed";
             }
             leaf load-threshold {
               type string;
               description "Load threshold that determines when interfaces are added to bundle";
             }
             leaf load-interval {
               type string;
               description "Interval over which average load is calculated";
             }
             container dialer-interface-flags {
               leaf backup {
                 type empty;
                 description "Dialer backup";
               }
               leaf multilink {
                 type empty;
                 description "Dialer multilink";
               }
               leaf watchlist {
                 type empty;
                 description "Dialer watchlist";
               }
               leaf interesting-detected {
                 type empty;
                 description "Interesting packet detected";
               }
             }
           }
         }
         container shared-interface-information {
           container shared-interface-logical-interface {
             leaf peer-interface-name {
               type string;
               description "Peer interface name";
             }
             leaf interface-shared-with {
               type string;
               description "Logical interface owner";
             }
             leaf rx-fe {
               type string;
               description "Rx tunnel token forwarding element";
             }
             leaf rx-nhid {
               type string;
               description "Rx tunnel token next hop index";
             }
             leaf tx-fe {
               type string;
               description "Tx tunnel token forwarding element";
             }
             leaf tx-nhid {
               type string;
               description "Tx tunnel token next hop index";
             }
           }
         }
         container mac-database {
         }
         container queue-counters {
           leaf queue-counters-error-message {
             type string;
             description "Queue statistics not available for this interface";
           }
           list queue {
             leaf queue-number {
               type int32;
               description "Queue number";
             }
             leaf queue-counters-queued-packets {
               type uint64;
               description "Queued packet count";
             }
             leaf queue-counters-trans-packets {
               type uint64;
               description "Total number of transmitted packets";
             }
             leaf queue-counters-total-drop-packets {
               type uint64;
               description "Number of total packets dropped at the queue";
             }
             leaf forwarding-class-name {
               type string;
               description "Forwarding class name associated with queue";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
         }
         container ingress-queue-counters {
           list queue {
             leaf queue-number {
               type int32;
               description "Queue number";
             }
             leaf forwarding-class-name {
               type string;
               description "Forwarding class name associated with queue";
             }
             leaf queue-counters-queued-packets {
               type uint64;
               description "Queued packet count";
             }
             leaf queue-counters-queued-packets-rate {
               type uint64;
               description "Rate at which packets are queued";
             }
             leaf queue-counters-queued-bytes {
               type uint64;
               description "Queued bytes count";
             }
             leaf queue-counters-queued-bytes-rate {
               type uint64;
               description "Rate at which bytes are queued";
             }
             leaf queue-counters-queued-packets-na {
               type string;
               description "Queued packets not available";
             }
             leaf queue-counters-queued-bytes-na {
               type string;
               description "Queued bytes not available";
             }
             leaf queue-counters-trans-packets {
               type uint64;
               description "Total number of transmitted packets";
             }
             leaf queue-counters-trans-packets-rate {
               type uint64;
               description "Rate at which packets are transmitted";
             }
             leaf queue-counters-trans-bytes {
               type uint64;
               description "Total number of transmitted bytes";
             }
             leaf queue-counters-trans-bytes-rate {
               type uint64;
               description "Rate at which bytes are transmitted";
             }
             leaf queue-counters-tail-drop-packets-na {
               type string;
               description "Number of packets dropped due to tail drop not available";
             }
             leaf queue-counters-tail-drop-packets {
               type uint64;
               description "Number of packets dropped at the tail of the queue";
             }
             leaf queue-counters-tail-drop-packets-rate {
               type uint64;
               description "Rate at which packets are dropped at tail of queue";
             }
             leaf queue-counters-tail-drop-bytes {
               type uint64;
               description "Number of packets dropped at tail drop of the queue";
             }
             leaf queue-counters-tail-drop-bytes-rate {
               type uint64;
               description "Number of packets dropped at tail drop of the queue";
             }
             leaf queue-counters-rate-limit-drop-packets-na {
               type string;
               description "Number of packets dropped due to rate-limit drop not available";
             }
             leaf queue-counters-rate-limit-drop-packets {
               type uint64;
               description "Number of packets dropped by rate-limit for the queue";
             }
             leaf queue-counters-rate-limit-drop-packets-rate {
               type uint64;
               description "Rate at which packets are dropped by rate-limit for the queue";
             }
             leaf queue-counters-rate-limit-drop-bytes-na {
               type string;
               description "Number of bytes dropped due to tail drop not available";
             }
             leaf queue-counters-rate-limit-drop-bytes {
               type uint64;
               description "Number of bytes dropped at the tail of the queue";
             }
             leaf queue-counters-rate-limit-drop-bytes-rate {
               type uint64;
               description "Rate at which bytes are dropped at the tail of the queue";
             }
             leaf queue-counters-red-packets-na {
               type string;
               description "Number of packets dropped due to RED not available";
             }
             leaf queue-counters-red-packets {
               type uint64;
               description "Number of packets dropped due to RED";
             }
             leaf queue-counters-red-packets-rate {
               type uint64;
               description "Rate at which packets are dropped due to RED";
             }
             leaf queue-counters-red-packets-ln {
               type uint64;
               description "Number of RED dropped low-loss, non-TCP packets";
             }
             leaf queue-counters-red-packets-rate-ln {
               type uint64;
               description "RED drop rate for low-loss, non-TCP packets";
             }
             leaf queue-counters-red-packets-lt {
               type uint64;
               description "Number of RED dropped of low-loss, TCP packets";
             }
             leaf queue-counters-red-packets-rate-lt {
               type uint64;
               description "RED drop rate for low-loss, TCP packets";
             }
             leaf queue-counters-red-packets-hn {
               type uint64;
               description "Number of RED dropped high-loss, non-TCP packets";
             }
             leaf queue-counters-red-packets-rate-hn {
               type uint64;
               description "RED drop rate for high-loss, non-TCP packets";
             }
             leaf queue-counters-red-packets-ht {
               type uint64;
               description "Number of RED dropped high-loss, TCP packets";
             }
             leaf queue-counters-red-packets-rate-ht {
               type uint64;
               description "RED drop rate for high-loss, TCP packets";
             }
             leaf queue-counters-red-packets-low {
               type uint64;
               description "Number of RED dropped low-loss packets";
             }
             leaf queue-counters-red-packets-rate-low {
               type uint64;
               description "RED drop rate for low-loss packets";
             }
             leaf queue-counters-red-packets-medium-low {
               type uint64;
               description "Number of RED dropped medium-low-loss packets";
             }
             leaf queue-counters-red-packets-rate-medium-low {
               type uint64;
               description "RED drop rate for medium-low-loss packets";
             }
             leaf queue-counters-red-packets-medium-high {
               type uint64;
               description "Number of RED dropped medium-high-loss packets";
             }
             leaf queue-counters-red-packets-rate-medium-high {
               type uint64;
               description "RED drop rate for medium-high-loss packets";
             }
             leaf queue-counters-red-packets-medium {
               type uint64;
               description "Number of RED dropped medium-loss packets";
             }
             leaf queue-counters-red-packets-rate-medium {
               type uint64;
               description "RED drop rate for medium-loss packets";
             }
             leaf queue-counters-red-packets-high {
               type uint64;
               description "Number of RED dropped high-loss packets";
             }
             leaf queue-counters-red-packets-rate-high {
               type uint64;
               description "RED drop rate for high-loss packets";
             }
             leaf queue-counters-red-bytes-na {
               type string;
               description "Number of bytes dropped due to RED not available";
             }
             leaf queue-counters-red-bytes {
               type uint64;
               description "Number of bytes dropped due to RED";
             }
             leaf queue-counters-red-bytes-rate {
               type uint64;
               description "Rate at which bytes are dropped due to RED";
             }
             leaf queue-counters-red-bytes-ln {
               type uint64;
               description "Number of RED dropped low-loss, non-TCP bytes";
             }
             leaf queue-counters-red-bytes-rate-ln {
               type uint64;
               description "RED drop rate for low-loss, non-TCP bytes";
             }
             leaf queue-counters-red-bytes-lt {
               type uint64;
               description "Number of RED dropped low-loss, TCP bytes";
             }
             leaf queue-counters-red-bytes-rate-lt {
               type uint64;
               description "RED drop rate for low-loss, TCP bytes";
             }
             leaf queue-counters-red-bytes-hn {
               type uint64;
               description "Number of RED dropped high-loss, non-TCP bytes";
             }
             leaf queue-counters-red-bytes-rate-hn {
               type uint64;
               description "RED drop rate for high-loss, non-TCP bytes";
             }
             leaf queue-counters-red-bytes-ht {
               type uint64;
               description "Number of RED dropped high-loss, TCP bytes";
             }
             leaf queue-counters-red-bytes-rate-ht {
               type uint64;
               description "RED drop rate for high-loss, TCP bytes";
             }
             leaf queue-counters-red-bytes-low {
               type uint64;
               description "Number of RED dropped low-loss bytes";
             }
             leaf queue-counters-red-bytes-rate-low {
               type uint64;
               description "RED drop rate for low-loss bytes";
             }
             leaf queue-counters-red-bytes-medium-low {
               type uint64;
               description "Number of RED dropped medium-low-loss bytes";
             }
             leaf queue-counters-red-bytes-rate-medium-low {
               type uint64;
               description "RED drop rate for medium-low-loss bytes";
             }
             leaf queue-counters-red-bytes-medium-high {
               type uint64;
               description "Number of RED dropped medium-high-loss bytes";
             }
             leaf queue-counters-red-bytes-rate-medium-high {
               type uint64;
               description "RED drop rate for medium-high-loss bytes";
             }
             leaf queue-counters-red-bytes-medium {
               type uint64;
               description "Number of RED dropped medium-loss bytes";
             }
             leaf queue-counters-red-bytes-rate-medium {
               type uint64;
               description "RED drop rate for medium-loss bytes";
             }
             leaf queue-counters-red-bytes-high {
               type uint64;
               description "Number of RED dropped high-loss bytes";
             }
             leaf queue-counters-red-bytes-rate-high {
               type uint64;
               description "RED drop rate for high-loss bytes";
             }
             leaf queue-counters-timestamp {
               type uint64;
               description "Last packet enqueued timestamp";
             }
             leaf queue-counters-total-drop-packets {
               type uint64;
               description "Number of total packets dropped at the queue";
             }
             leaf queue-counters-total-drop-packets-rate {
               type uint64;
               description "Number of total packets dropped at the queue";
             }
             leaf queue-counters-total-drop-bytes {
               type uint64;
               description "Number of total packets dropped at the queue";
             }
             leaf queue-counters-total-drop-bytes-rate {
               type uint64;
               description "Number of total packets dropped at the queue";
             }
             leaf queue-counters-reserved-buffer-packets {
               type int32;
               description "Queues's usage of reserved buffer pool in pkts";
             }
             leaf queue-counters-reserved-buffer-bytes {
               type int32;
               description "Queues's usage of reserved buffer pool in bytes";
             }
             leaf queue-counters-shared-buffer-packets {
               type int32;
               description "Queues's usage of shared buffer pool in pkts";
             }
             leaf queue-counters-shared-buffer-bytes {
               type int32;
               description "Queues's usage of shared buffer pool in bytes";
             }
             leaf queue-counters-depth-average {
               type int32;
               description "Time averaged queue depth";
             }
             leaf queue-counters-depth-current {
               type int32;
               description "Current instantaneous queue depth";
             }
             leaf queue-counters-depth-peak {
               type int32;
               description "Peak queue depth";
             }
             leaf queue-counters-depth-max {
               type int32;
               description "Maximum queue depth attained";
             }
             leaf queue-counters-srx-reserved-buffer-bytes {
               type int32;
               description "Queues's usage of reserved buffer pool in bytes";
             }
             leaf queue-counters-srx-depth-current {
               type int32;
               description "Current instantaneous queue depth";
             }
           }
           container interface-cos-summary {
             leaf intf-cos-forwarding-classes-supported {
               type int32;
               description "Number of forwarding classes supported on this interface";
             }
             leaf intf-cos-forwarding-classes-in-use {
               type int32;
               description "Number of forwarding classes currently in use on this interface";
             }
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
             leaf intf-cos-burst-size-for-ifl {
               type int32;
               description "Burst size for the logical interface";
             }
           }
           container interface-cos-short-summary {
             leaf intf-cos-queue-type {
               type string;
               description "Interface queue type";
             }
             leaf intf-cos-num-queues-supported {
               type int32;
               description "Number of queues supported on this interface";
             }
             leaf intf-cos-num-queues-in-use {
               type int32;
               description "Number of queues currently in use on this interface";
             }
             leaf intf-cos-queue-dedicated-or-shared {
               type string;
               description "Interface has dedicated or shared queues";
             }
             leaf intf-cos-sched-resource-type {
               type string;
               description "Interface scheduling resource type";
             }
             leaf intf-cos-sched-resource-usage-mic-limit {
               type int32;
               description "MIC/PIC scheduling resource usage limit";
             }
             leaf intf-cos-sched-resource-usage-mic-count {
               type int32;
               description "MIC/PIC scheduling resource usage count";
             }
             leaf intf-cos-sched-resource-usage-port-limit {
               type int32;
               description "Interface scheduling resource limit";
             }
             leaf intf-cos-sched-resource-usage-port-count {
               type int32;
               description "Interface scheduling resource usage";
             }
           }
           container queue-num-forwarding-class-name-map {
             leaf queue-number {
               type int32;
               description "Queue number";
             }
             leaf forwarding-class-name {
               type string;
               description "Forwarding class name associated with queue";
             }
           }
         }
         container forwarding-class-counters {
           leaf forwarding-class-counters-error-message {
             type string;
             description "Forwarding-class statistics not available for this interface";
           }
           container ipv4-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container ipv6-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container mpls-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container layer2-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container other-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container protocol-aggregate-forwarding-class-counters {
             leaf forwarding-class-stats-type {
               type string;
             }
             container per-forwarding-class-counters {
               leaf fc_name_header {
                 type string;
               }
               leaf forwarding-class-name {
                 type string;
                 description "Forwarding class name associated with queue";
               }
               leaf fc-input-bytes {
                 type int32;
               }
               leaf fc-input-bytes-rate {
                 type int32;
                 description "Input bytes rate";
               }
               leaf fc-output-bytes {
                 type int32;
               }
               leaf fc-output-bytes-rate {
                 type int32;
                 description "Output bytes rate";
               }
               leaf fc-input-packets {
                 type int32;
               }
               leaf fc-input-packets-rate {
                 type int32;
                 description "Input packets rate";
               }
               leaf fc-output-packets {
                 type int32;
               }
               leaf fc-output-packets-rate {
                 type int32;
                 description "Output packets rate";
               }
               leaf input-unicast-bytes {
                 type int32;
               }
               leaf output-unicast-bytes {
                 type int32;
               }
               leaf input-unicast-packets {
                 type int32;
               }
               leaf output-unicast-packets {
                 type int32;
               }
               leaf input-multicast-bytes {
                 type int32;
               }
               leaf output-multicast-bytes {
                 type int32;
               }
               leaf input-multicast-packets {
                 type int32;
               }
               leaf output-multicast-packets {
                 type int32;
               }
             }
           }
           container forwarding-class-statistics {
             container protocol-aggregate-forwarding-class-counters {
             }
             container ipv4-forwarding-class-counters {
             }
             container ipv6-forwarding-class-counters {
             }
             container mpls-forwarding-class-counters {
             }
             container layer2-forwarding-class-counters {
             }
             container other-forwarding-class-counters {
             }
           }
           container forwarding-class-accounting-parameters {
             leaf forwarding-class-accounting-for-protocol {
               type string;
             }
             leaf forwarding-class-accounting-for-traffic-direction {
               type string;
             }
             leaf forwarding-class-accounting-for-traffic-type {
               type string;
             }
             leaf forwarding-class-accounting-overhead-bytes {
               type uint32;
             }
           }
           container per-forwarding-class-counters {
             leaf fc_name_header {
               type string;
             }
             leaf forwarding-class-name {
               type string;
               description "Forwarding class name associated with queue";
             }
             leaf fc-input-bytes {
               type int32;
             }
             leaf fc-input-bytes-rate {
               type int32;
               description "Input bytes rate";
             }
             leaf fc-output-bytes {
               type int32;
             }
             leaf fc-output-bytes-rate {
               type int32;
               description "Output bytes rate";
             }
             leaf fc-input-packets {
               type int32;
             }
             leaf fc-input-packets-rate {
               type int32;
               description "Input packets rate";
             }
             leaf fc-output-packets {
               type int32;
             }
             leaf fc-output-packets-rate {
               type int32;
               description "Output packets rate";
             }
             leaf input-unicast-bytes {
               type int32;
             }
             leaf output-unicast-bytes {
               type int32;
             }
             leaf input-unicast-packets {
               type int32;
             }
             leaf output-unicast-packets {
               type int32;
             }
             leaf input-multicast-bytes {
               type int32;
             }
             leaf output-multicast-bytes {
               type int32;
             }
             leaf input-multicast-packets {
               type int32;
             }
             leaf output-multicast-packets {
               type int32;
             }
           }
         }
         container multilink-bundle-options {
           leaf filler-packet-interval {
             type int32;
           }
         }
         container multilink-traffic-statistics {
           container bundle {
           }
           container class {
           }
           container multilink-detail-statistics {
             container bundle-detail {
             }
             container class-detail {
             }
           }
           container crtp {
             container crtp-sessions {
               leaf input-frames {
                 type int32;
               }
               leaf output-frames {
                 type int32;
               }
             }
             list crtp-statistics {
               leaf name {
                 type string;
                 description "Name of this item";
               }
               leaf input-frames {
                 type int32;
               }
               leaf input-fps {
                 type int32;
               }
               leaf input-bytes {
                 type int32;
               }
               leaf input-bps {
                 type int32;
               }
               leaf output-frames {
                 type int32;
               }
               leaf output-fps {
                 type int32;
               }
               leaf output-bytes {
                 type int32;
               }
               leaf output-bps {
                 type int32;
               }
             }
           }
         }
         container traffic-statistics {
           leaf input-bps {
             type int32;
           }
           leaf input-pps {
             type int32;
           }
           leaf output-bps {
             type int32;
           }
           leaf output-pps {
             type int32;
           }
           leaf input-packets {
             type int32;
           }
           leaf output-packets {
             type int32;
           }
           leaf input-bytes {
             type int32;
           }
           leaf output-bytes {
             type int32;
           }
           container ipv6-transit-statistics {
             leaf input-bytes {
               type int32;
             }
             leaf output-bytes {
               type int32;
             }
             leaf input-packets {
               type int32;
             }
             leaf output-packets {
               type int32;
             }
           }
           container ipv6-total-statistics {
             leaf input-bytes {
               type int32;
             }
             leaf output-bytes {
               type int32;
             }
             leaf input-packets {
               type int32;
             }
             leaf output-packets {
               type int32;
             }
           }
         }
         container multicast-statistics {
           leaf multicast-statistics-header {
             type empty;
           }
           container ipv4-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
           container ipv6-multicast-statistics {
             leaf input-bytes {
               type int32;
             }
             leaf input-bps {
               type int32;
             }
             leaf output-bytes {
               type int32;
             }
             leaf output-bps {
               type int32;
             }
             leaf input-packets {
               type int32;
             }
             leaf input-pps {
               type int32;
             }
             leaf output-packets {
               type int32;
             }
             leaf output-pps {
               type int32;
             }
           }
         }
         container ingress-traffic-statistics {
           leaf input-bps {
             type int32;
           }
           leaf input-pps {
             type int32;
           }
           leaf input-drop-bps {
             type int32;
             description "Drop rate at ingress in bits per second ";
           }
           leaf input-drop-pps {
             type int32;
             description "Drop rate at ingress in packets per second ";
           }
           leaf input-bytes {
             type int32;
           }
           leaf input-packets {
             type int32;
           }
           leaf input-drop-bytes {
             type int32;
             description "Drop statistics at ingress in bytes";
           }
           leaf input-drop-packets {
             type int32;
             description "Drop statistics at ingress in packets";
           }
         }
         container transit-traffic-statistics {
         }
         container keepalive-statistics {
           leaf keepalive-lmi-descriptor {
             type string;
           }
           leaf keepalive-input-count {
             type int32;
           }
           leaf keepalive-input-time {
             type string;
           }
           leaf keepalive-output-count {
             type int32;
           }
           leaf keepalive-output-time {
             type string;
           }
         }
         container virtual-circuit-information {
           container traffic-statistics {
             leaf input-bps {
               type int32;
             }
             leaf input-pps {
               type int32;
             }
             leaf output-bps {
               type int32;
             }
             leaf output-pps {
               type int32;
             }
             leaf input-packets {
               type int32;
             }
             leaf output-packets {
               type int32;
             }
             leaf input-bytes {
               type int32;
             }
             leaf output-bytes {
               type int32;
             }
             container ipv6-transit-statistics {
               leaf input-bytes {
                 type int32;
               }
               leaf output-bytes {
                 type int32;
               }
               leaf input-packets {
                 type int32;
               }
               leaf output-packets {
                 type int32;
               }
             }
             container ipv6-total-statistics {
               leaf input-bytes {
                 type int32;
               }
               leaf output-bytes {
                 type int32;
               }
               leaf input-packets {
                 type int32;
               }
               leaf output-packets {
                 type int32;
               }
             }
           }
           container atm-cos-information {
             leaf vc-cos-mode {
               type string;
               description "Virtual circuit CoS scheduling mode";
             }
             list atm-cos-queue {
               container atm-cos-queue-parameters {
                 leaf cos-forwarding-class-name {
                   type string;
                   description "Forwarding class name associated with queue";
                 }
                 leaf cos-queue-number {
                   type int32;
                   description "Queue number";
                 }
                 leaf scheduling-priority {
                   type string;
                   description "Scheduling priority";
                 }
                 leaf transmit-weight-cells {
                   type int32;
                   description "Weight to apply to scheduling as number of cells";
                 }
                 leaf transmit-weight-percent {
                   type int32;
                   description "Weight to apply to scheduling as fill percentage";
                 }
                 leaf epd-threshold {
                   type int32;
                   description "Early packet drop threshold";
                 }
                 leaf epd-threshold-plp0 {
                   type int32;
                   description "Early packet drop threshold for PLP 0";
                 }
                 leaf epd-threshold-plp1 {
                   type int32;
                   description "Early packet drop threshold for PLP 1";
                 }
                 container linear-red-drop-profile {
                   leaf queue-depth {
                     type uint32;
                     description "Instantaneous queue depth";
                   }
                   leaf low-red {
                     type int32;
                     description "Fill level percentage when linear RED is applied for low PLP";
                   }
                   leaf high-red {
                     type int32;
                     description "Fill level percentage when linear RED is applied for high PLP";
                   }
                   leaf max-low-red {
                     type int32;
                     description "Fill level percentage with 100% packet drop for low PLP";
                   }
                   leaf max-high-red {
                     type int32;
                     description "Fill level percentage with 100% packet drop for high PLP";
                   }
                 }
               }
               container atm-cos-queue-statistics {
                 leaf atm-output-bytes {
                   type int32;
                 }
                 leaf atm-output-packets {
                   type int32;
                 }
                 leaf atm-packet-drops {
                   type int32;
                 }
               }
               container atm-cos-plp-statistics {
                 leaf atm-plp0-output-bytes {
                   type int32;
                 }
                 leaf atm-plp1-output-bytes {
                   type int32;
                 }
                 leaf atm-plp0-output-packets {
                   type int32;
                 }
                 leaf atm-plp1-output-packets {
                   type int32;
                 }
                 leaf atm-plp0-byte-drops {
                   type int32;
                 }
                 leaf atm-plp1-byte-drops {
                   type int32;
                 }
                 leaf atm-plp0-packet-drops {
                   type int32;
                 }
                 leaf atm-plp1-packet-drops {
                   type int32;
                 }
               }
             }
           }
         }
         list policer-information {
           leaf policer-family {
             type string;
             description "Protocol family of the policer";
           }
           leaf policer-input {
             type string;
             description "Name of the input policer";
           }
           leaf policer-output {
             type string;
             description "Name of the output policer";
           }
         }
         list address-family {
           leaf local-bias-information {
             type string;
           }
           leaf ft-iff-dest-port {
             type uint32;
             description "Destination UDP port to be used for this family";
           }
           container pppoe-underlying-information {
             list pppoe-underlying-interface {
               leaf dynamic-profile {
                 type string;
                 description "Dynamic Profile name";
               }
               leaf service-name-table {
                 type string;
                 description "Name of Service Name Table";
               }
               leaf max-sessions {
                 type int32;
                 description "Maximum number of PPPoE sessions";
               }
               leaf max-sessions-vsa-ignore {
                 type string;
                 description "Ignore max-sessions VSA";
               }
               leaf duplicate-protection {
                 type string;
                 description "Duplicate protection mode";
               }
               leaf short-cycle-protection {
                 type string;
                 description "Short cycle protection mode";
               }
               leaf direct-connect {
                 type string;
                 description "Direct connect mode";
               }
               leaf ac-name {
                 type string;
                 description "Access Concentrator name";
               }
               leaf underlying-interface-name {
                 type string;
                 description "Underlying interface name";
               }
               leaf underlying-interface-index {
                 type string;
                 description "Underlying interface index";
               }
               leaf encapsulation-type-identifier {
                 type string;
                 description "Encapsulation type identifier";
               }
               leaf state {
                 type string;
                 description "State";
               }
               leaf active-sessions {
                 type int32;
                 description "Number of active PPPoE sessions";
               }
               leaf aci-autosensing {
                 type string;
                 description "ACI VLAN Autosensing mode";
               }
               leaf line-identity-autosensing {
                 type string;
                 description "Line Identity Autosensing mode";
               }
             }
           }
           list interface-address {
           }
           container destination-class-statistics {
           }
           container source-class-statistics {
           }
         }
         list bridge-iff-properties {
         }
         container l2circuit-info {
           leaf out-of-sequence {
             type int32;
           }
           leaf denied-packets {
             type int32;
           }
           leaf cell-bundle-size {
             type int32;
           }
           leaf cell-bundle-timeout {
             type int32;
           }
           leaf cell-timeout-count {
             type int32;
           }
         }
         container media-information {
           leaf media-type {
             type string;
             description "Type of media this information is for";
           }
           list media-alarm {
             leaf media-alarm-name {
               type string;
             }
             leaf media-alarm-count {
               type int32;
             }
             leaf media-alarm-seconds {
               type int32;
             }
             leaf media-alarm-state {
               type string;
             }
             leaf ce-counter-name {
               type string;
               description "Circuit Emulation counter information";
             }
             leaf ce-counter-packets {
               type int32;
               description "Circuit Emulation number of packets";
             }
             leaf ce-counter-bytes {
               type int32;
               description "Circuit Emulation number of bytes";
             }
             leaf ce-counter-count {
               type int32;
               description "Circuit Emulation number of event occurrences";
             }
           }
           leaf ds1-timeslots {
             type string;
           }
           leaf ds1-line-encoding {
             type string;
           }
           leaf ds1-byte-encoding {
             type string;
           }
           leaf ds1-data-inversion {
             type string;
           }
           leaf idle-cycle-flag {
             type string;
           }
           leaf start-end-flag {
             type string;
           }
           leaf ds0-byte-encoding {
             type string;
           }
           leaf ds0-data-inversion {
             type string;
           }
           leaf e3-data-inversion {
             type string;
           }
           leaf ds1-buildout {
             type string;
             description "Number of feet";
           }
         }
         list macsec-statistics {
           leaf interface-name {
             type string;
             description "Class-of-service interface name";
           }
           leaf encrypted-packets {
             type uint64;
             description "Macsec encrypted packets sent";
           }
           leaf encrypted-bytes {
             type uint64;
             description "Macsec encrypted bytes sent";
           }
           leaf protected-packets {
             type uint64;
             description "Macsec packets sent with only integrity protection";
           }
           leaf protected-bytes {
             type uint64;
             description "Macsec bytes sent with only integrity protection";
           }
           leaf ok-packets {
             type uint64;
             description "Macsec packets accepted";
           }
           leaf decrypted-bytes {
             type uint64;
             description "Macsec received bytes decrypted";
           }
           leaf decrypted-packets {
             type uint64;
             description "Macsec received packets decrypted";
           }
           leaf validated-packets {
             type uint64;
             description "Macsec received packets validated";
           }
           leaf validated-bytes {
             type uint64;
             description "Macsec received bytes validated";
           }
           leaf untagged-packets {
             type uint64;
             description "Macsec untagged packets";
           }
           leaf toolong-packets {
             type uint64;
             description "Macsec too long packets transmitted on a secure channel";
           }
           leaf control-packets {
             type uint64;
             description "Macsec control packets received on a secure channel";
           }
           leaf tagged-miss-packets {
             type uint64;
             description "Macsec tagged miss packets received on a secure channel";
           }
           leaf untagged-hit-packets {
             type uint64;
             description "Macsec untagged hit packets received on a secure channel";
           }
           leaf notag-packets {
             type uint64;
             description "Macsec no tag packets received on a secure channel";
           }
           leaf badtag-packets {
             type uint64;
             description "Macsec bad tag packets received on a secure channel";
           }
           leaf unknown-sci-packets {
             type uint64;
             description "Macsec unknown sci packets received on a secure channel";
           }
           leaf no-sci-packets {
             type uint64;
             description "Macsec no sci packets received on a secure channel";
           }
           leaf control-pass-packets {
             type uint64;
             description "Macsec allowed control packets received on a secure channel";
           }
           leaf uncontrol-pass-packets {
             type uint64;
             description "Macsec allowed uncontrol packets received on a secure channel";
           }
           leaf control-fail-packets {
             type uint64;
             description "Macsec dropped control packets received on a secure channel";
           }
           leaf uncontrol-fail-packets {
             type uint64;
             description "Macsec dropped uncontrol packets received on a secure channel";
           }
           leaf hit-dropped-packets {
             type uint64;
             description "Macsec hit dropped packets received on a security channel";
           }
           leaf notusing-sa-packets {
             type uint64;
             description "Macsec not using sa packets received on a security channel";
           }
           leaf unused-sa-packets {
             type uint64;
             description "Macsec unused sa packets received on a security channel";
           }
           leaf late-packets {
             type uint64;
             description "Macsec late packets dropped on a security channel";
           }
           leaf delayed-packets {
             type uint64;
             description "Macsec delayed packets accepted on a security channel";
           }
           leaf unchecked-packets {
             type uint64;
             description "Macsec unchecked packets accepted on a security channel";
           }
           leaf notvalid-packets {
             type uint64;
             description "Macsec not valid packets dropped on a security channel";
           }
           leaf invalid-packets {
             type uint64;
             description "Macsec invalid packets accepted on a security channel";
           }
           list secure-channel-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-association-sent {
             leaf encrypted-packets {
               type uint64;
               description "Macsec encrypted packets sent";
             }
             leaf encrypted-bytes {
               type uint64;
               description "Macsec encrypted bytes sent";
             }
             leaf protected-packets {
               type uint64;
               description "Macsec packets sent with only integrity protection";
             }
             leaf protected-bytes {
               type uint64;
               description "Macsec bytes sent with only integrity protection";
             }
           }
           list secure-channel-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list secure-association-received {
             leaf ok-packets {
               type uint64;
               description "Macsec packets accepted";
             }
             leaf decrypted-packets {
               type uint64;
               description "Macsec received packets decrypted";
             }
             leaf decrypted-bytes {
               type uint64;
               description "Macsec received bytes decrypted";
             }
             leaf validated-packets {
               type uint64;
               description "Macsec received packets validated";
             }
             leaf validated-bytes {
               type uint64;
               description "Macsec received bytes validated";
             }
           }
           list macsec-error-information {
             list secure-channel-sent-errors {
               leaf untagged-packets {
                 type uint64;
                 description "Macsec untagged packets";
               }
               leaf toolong-packets {
                 type uint64;
                 description "Macsec too long packets transmitted on a secure channel";
               }
             }
             list secure-channel-received-errors {
               leaf control-packets {
                 type uint64;
                 description "Macsec control packets received on a secure channel";
               }
               leaf tagged-miss-packets {
                 type uint64;
                 description "Macsec tagged miss packets received on a secure channel";
               }
               leaf untagged-hit-packets {
                 type uint64;
                 description "Macsec untagged hit packets received on a secure channel";
               }
               leaf untagged-packets {
                 type uint64;
                 description "Macsec untagged packets";
               }
               leaf notag-packets {
                 type uint64;
                 description "Macsec no tag packets received on a secure channel";
               }
               leaf badtag-packets {
                 type uint64;
                 description "Macsec bad tag packets received on a secure channel";
               }
               leaf unknown-sci-packets {
                 type uint64;
                 description "Macsec unknown sci packets received on a secure channel";
               }
               leaf no-sci-packets {
                 type uint64;
                 description "Macsec no sci packets received on a secure channel";
               }
               leaf control-pass-packets {
                 type uint64;
                 description "Macsec allowed control packets received on a secure channel";
               }
               leaf control-fail-packets {
                 type uint64;
                 description "Macsec dropped control packets received on a secure channel";
               }
               leaf uncontrol-pass-packets {
                 type uint64;
                 description "Macsec allowed uncontrol packets received on a secure channel";
               }
               leaf uncontrol-fail-packets {
                 type uint64;
                 description "Macsec dropped uncontrol packets received on a secure channel";
               }
             }
             list secure-channel-received-extended {
               leaf hit-dropped-packets {
                 type uint64;
                 description "Macsec hit dropped packets received on a security channel";
               }
               leaf invalid-packets {
                 type uint64;
                 description "Macsec invalid packets accepted on a security channel";
               }
               leaf late-packets {
                 type uint64;
                 description "Macsec late packets dropped on a security channel";
               }
               leaf delayed-packets {
                 type uint64;
                 description "Macsec delayed packets accepted on a security channel";
               }
               leaf unchecked-packets {
                 type uint64;
                 description "Macsec unchecked packets accepted on a security channel";
               }
               leaf notvalid-packets {
                 type uint64;
                 description "Macsec not valid packets dropped on a security channel";
               }
               leaf notusing-sa-packets {
                 type uint64;
                 description "Macsec not using sa packets received on a security channel";
               }
               leaf unused-sa-packets {
                 type uint64;
                 description "Macsec unused sa packets received on a security channel";
               }
               leaf untagged-hit-packets {
                 type uint64;
                 description "Macsec untagged hit packets received on a secure channel";
               }
             }
           }
         }
         container lag-traffic-statistics {
           container lag-multicast-statistics {
             leaf lag-multicast-statistics-header {
               type empty;
             }
             container lag-ipv4-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
             container lag-ipv6-multicast-statistics {
               leaf input-packets {
                 type int32;
               }
               leaf input-pps {
                 type int32;
               }
               leaf input-bytes {
                 type int32;
               }
               leaf input-bps {
                 type int32;
               }
               leaf output-packets {
                 type int32;
               }
               leaf output-pps {
                 type int32;
               }
               leaf output-bytes {
                 type int32;
               }
               leaf output-bps {
                 type int32;
               }
             }
           }
           list if-distribution-list-information {
           }
         }
         container layer2-input-policer-statistics {
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container layer2-output-policer-statistics {
           leaf policer-medium-low-frames {
             type int32;
             description "Number of loss priority medium low frames";
           }
           leaf policer-medium-low-bytes {
             type int32;
             description "Number of loss priority medium low bytes";
           }
           leaf policer-medium-low-rate {
             type int32;
             description "Rate of loss priority medium low pkts";
           }
         }
         container mac-policer-information {
           container ether-policer-list {
           }
         }
       }
     }
     list interface-map {
       description "Class-of-service interface mappings";
       leaf interface-name {
         type string;
         description "Class-of-service interface name";
       }
       leaf interface-index {
         type uint32;
         description "Class-of-service interface index";
       }
       leaf interface-queues-supported {
         type uint32;
         description "Number of queues supported on this interface";
       }
       leaf interface-queues-in-use {
         type uint32;
         description "Number of queues in use on this interface";
       }
       leaf interface-total-egress-queues-created {
         type uint32;
         description "Total number of non-default egress queues in use on this interface";
       }
       leaf interface-total-ingress-queues-created {
         type uint32;
         description "Total number of non-default ingress queues in use on this interface";
       }
       leaf interface-exclude-queue-overhead-bytes {
         type string;
         description "Setting for excluding queue overhead bytes for aggregate statistics";
       }
       leaf interface-logical-interface-aggregate-statistics {
         type string;
         description "Whether interface statistics for a logical interface are enabled or disabled";
       }
       leaf interface-shaping-rate {
         type string;
         description "Class-of-service interface shaping rate";
       }
       leaf scheduler-map-name {
         type string;
         description "Class-of-service scheduler map name";
       }
       leaf scheduler-map-index {
         type uint64;
         description "Class-of-service scheduler map index";
       }
       leaf interface-input-shaping-rate {
         type string;
         description "Class-of-service interface input shaping rate";
       }
       leaf input-scheduler-map-name {
         type string;
         description "Class-of-service input scheduler map name";
       }
       leaf input-scheduler-map-index {
         type uint32;
         description "Index number for Class-of-service input scheduler map";
       }
       leaf chassis-scheduler-map-name {
         type string;
         description "Class-of-service chassis scheduler map name";
       }
       leaf chassis-scheduler-map-index {
         type uint32;
         description "Index number for Class-of-service chassis scheduler map";
       }
       leaf input-traffic-control-profile-name {
         type string;
         description "Class-of-service input traffic control profile name";
       }
       leaf input-traffic-control-profile-index {
         type uint64;
         description "Index number for Class-of-service input traffic control profile";
       }
       leaf input-traffic-control-profile-remaining-name {
         type string;
         description "Class-of-service input traffic control profile remaining name";
       }
       leaf input-traffic-control-profile-remaining-index {
         type uint64;
         description "Index number for Class-of-service input traffic control profile remaining";
       }
       leaf output-traffic-control-profile-name {
         type string;
         description "Class-of-service output traffic control profile name";
       }
       leaf output-traffic-control-profile-index {
         type uint64;
         description "Index number for Class-of-service output traffic control profile";
       }
       leaf output-traffic-control-profile-remaining-name {
         type string;
         description "Class-of-service output traffic control profile remaining name";
       }
       leaf output-traffic-control-profile-remaining-index {
         type uint64;
         description "Index number for Class-of-service output traffic control profile remaining";
       }
       leaf forwarding-class-map-name {
         type string;
         description "Class-of-service forwarding class map name";
       }
       leaf forwarding-class-map-index {
         type uint32;
         description "Index number for Class-of-service forwarding class map";
       }
       leaf interface-congestion-notification-map {
         type string;
         description "Congestion notification enabled/disabled on interface";
       }
       leaf interface-congestion-notification-map-name {
         type string;
         description "Congestion notification Profile Name";
       }
       leaf interface-congestion-notification-map-index {
         type uint32;
         description "Congestion notification Profile Index";
       }
       leaf dcbx-congestion-notification-map {
         type string;
         description "Congestion notification enabled/disabled by DCBX on interface";
       }
       leaf monitoring-profile-map-name {
         type string;
         description "Monitoring Profile Name";
       }
       leaf monitoring-profile-map-index {
         type uint32;
         description "Monitoring Profile Index";
       }
       leaf interface-rewrite-value {
         type string;
         description "Interface rewrite value input / output";
       }
       leaf code-point-type {
         type string;
         description "Class-of-service code point type";
       }
       leaf code-point-bits {
         type string;
         description "Class-of-service code point bit sequence";
       }
       leaf scheduler-map-forwarding-class-set-name {
         type string;
         description "Class-of-service scheduler map forwarding-class-set name";
       }
       leaf scheduler-map-forwarding-class-set-index {
         type uint32;
         description "Class-of-service scheduler map forwarding class set index";
       }
       leaf interface-drop-congestion-notification {
         type string;
         description "Drop Congestion notification on interface";
       }
       leaf interface-dedicated-buffer-profile-name {
         type string;
         description "Dedicated Buffer Profile Name";
       }
       leaf interface-decn-profile-name {
         type string;
         description "DECN Profile Name";
       }
       leaf interface-dynamic-threshold-profile-name {
         type string;
         description "Dynamic Threshold Profile Name";
       }
       list forwarding-class-set-attachment {
         description "Class-of-service forwarding class set interface attachment ";
         leaf forwarding-class-set-name {
           type string;
           description "Class-of-service forwarding class set name";
         }
         leaf table-index {
           type uint32;
           description "Table index";
         }
         leaf output-traffic-control-profile-name {
           type string;
           description "Class-of-service output traffic control profile name";
         }
         leaf output-traffic-control-profile-index {
           type uint64;
           description "Index number for Class-of-service output traffic control profile";
         }
       }
       list cos-objects {
         description "Class-of-service object  mappings";
         leaf cos-object-type {
           type string;
           description "Class-of-service object type";
         }
         leaf cos-object-name {
           type string;
           description "Class-of-service object name";
         }
         leaf cos-object-subtype {
           type string;
           description "Class-of-service object subtype";
         }
         leaf cos-object-index {
           type uint64;
           description "Class-of-service object index";
         }
       }
       list i-logical-map {
         leaf i-logical-name {
           type string;
           description "Class-of-service logical interface name";
         }
         leaf i-logical-index {
           type uint32;
           description "Class-of-service logical interface index";
         }
         leaf policy-map-marking {
           type string;
           description "Class-of-service logical interface policy map";
         }
         leaf interface-has-dedicated-queues {
           type string;
           description "Whether interface has dedicated queues";
         }
         leaf user-plane-name {
           type string;
           description "Class-of-service user-plane name for XDA";
         }
         leaf policer-bandwidth {
           type uint32;
           description "Class-of-service logical interface policer bandwidth";
         }
         leaf policer-burst {
           type uint32;
           description "Class-of-service logical interface policer burst";
         }
         leaf shaper-bandwidth {
           type uint32;
           description "Class-of-service logical interface shaper bandwidth";
         }
         leaf shaper-burst {
           type uint32;
           description "Class-of-service logical interface shaper burst";
         }
         leaf shaping-rate {
           type uint64;
           description "Class-of-service shaping rate";
         }
         leaf burst-size {
           type string;
           description "Class-of-service logical interface burst size";
         }
         leaf input-shaping-rate {
           type uint64;
           description "Class-of-service input shaping rate";
         }
         leaf input-burst-size {
           type string;
           description "Class-of-service logical interface input burst size";
         }
         leaf adjusting-application-name {
           type string;
           description "The name of the application performing the rate adjustment";
         }
         leaf adjustment-type {
           type string;
           description "Class-of-service rate adjustment type";
         }
         leaf configured-shaping-rate {
           type string;
           description "Class-of-service configured shaping rate";
         }
         leaf adjustment-value {
           type string;
           description "Class-of-service adjusted shaping rate value";
         }
         leaf adjustment-overhead-accounting-mode {
           type string;
           description "Class-of-service adjusted overhead-accounting mode";
         }
         leaf adjustment-overhead-bytes {
           type int32;
           description "Class-of-service adjusted overhead bytes";
         }
         leaf adjustment-target {
           type string;
           description "Class-of-service rate adjustment target";
         }
         leaf adjustment-priority {
           type uint32;
           description "Class-of-service rate adjustment priority";
         }
         leaf monitoring-profile-map-name {
           type string;
           description "Monitoring Profile Name";
         }
         list cos-objects {
           description "Class-of-service object  mappings";
           leaf cos-object-type {
             type string;
             description "Class-of-service object type";
           }
           leaf cos-object-name {
             type string;
             description "Class-of-service object name";
           }
           leaf cos-object-subtype {
             type string;
             description "Class-of-service object subtype";
           }
           leaf cos-object-index {
             type uint64;
             description "Class-of-service object index";
           }
         }
       }
     }
     leaf sample-string {
       type string;
     }
     leaf local-string-local {
       type string;
     }
     list physical-interface {
       leaf interface-name {
         type jt:interface-device;
       }
       leaf logical-interface-name {
         type string;
       }
       leaf lcp-state {
         type string;
       }
     }
   }
   grouping cos-interface-set-information-block {
     list interface-set-map {
       leaf interface-set-name {
         type string;
         description "Class-of-service interface-set name";
       }
       leaf interface-set-index {
         type uint64;
         description "Class-of-service logical interface index";
       }
       leaf interface-name {
         type string;
         description "Class-of-service interface name";
       }
       leaf interface-index {
         type uint32;
         description "Class-of-service interface index";
       }
       leaf user-plane-name {
         type string;
         description "Class-of-service user-plane name for XDA";
       }
       leaf interface-queues-supported {
         type uint32;
         description "Number of queues supported on this interface";
       }
       leaf interface-queues-in-use {
         type uint32;
         description "Number of queues in use on this interface";
       }
       leaf input-traffic-control-profile-name {
         type string;
         description "Class-of-service input traffic control profile name";
       }
       leaf input-traffic-control-profile-index {
         type uint64;
         description "Index number for Class-of-service input traffic control profile";
       }
       leaf input-traffic-control-profile-remaining-name {
         type string;
         description "Class-of-service input traffic control profile remaining name";
       }
       leaf input-traffic-control-profile-remaining-index {
         type uint64;
         description "Index number for Class-of-service input traffic control profile remaining";
       }
       leaf output-traffic-control-profile-name {
         type string;
         description "Class-of-service output traffic control profile name";
       }
       leaf output-traffic-control-profile-index {
         type uint64;
         description "Index number for Class-of-service output traffic control profile";
       }
       leaf output-traffic-control-profile-remaining-name {
         type string;
         description "Class-of-service output traffic control profile remaining name";
       }
       leaf output-traffic-control-profile-remaining-index {
         type uint64;
         description "Index number for Class-of-service output traffic control profile remaining";
       }
       leaf monitoring-profile-map-name {
         type string;
         description "Monitoring Profile Name";
       }
       leaf monitoring-profile-map-index {
         type uint32;
         description "Monitoring Profile Index";
       }
       leaf adjusting-application-name {
         type string;
         description "The name of the application performing the rate adjustment";
       }
       leaf adjustment-type {
         type string;
         description "Class-of-service rate adjustment type";
       }
       leaf configured-shaping-rate {
         type string;
         description "Class-of-service configured shaping rate";
       }
       leaf adjustment-value {
         type string;
         description "Class-of-service adjusted shaping rate value";
       }
       leaf adjustment-overhead-accounting-mode {
         type string;
         description "Class-of-service adjusted overhead-accounting mode";
       }
       leaf adjustment-overhead-bytes {
         type int32;
         description "Class-of-service adjusted overhead bytes";
       }
       leaf adjustment-target {
         type string;
         description "Class-of-service rate adjustment target";
       }
       leaf adjustment-priority {
         type uint32;
         description "Class-of-service rate adjustment priority";
       }
     }
   }
   grouping cos-routing-instance-information-block {
     list routing-instance-map {
       description "Mapping between class-of-service objects and routing instances";
       leaf routing-instance-name {
         type string;
         description "Name of class-of-service routing instance";
       }
       list i-logical-map {
         leaf i-logical-name {
           type string;
           description "Class-of-service logical interface name";
         }
         leaf i-logical-index {
           type uint32;
           description "Class-of-service logical interface index";
         }
         leaf monitoring-profile-map-name {
           type string;
           description "Monitoring Profile Name";
         }
         list cos-objects {
           description "Class-of-service object  mappings";
           leaf cos-object-type {
             type string;
             description "Class-of-service object type";
           }
           leaf cos-object-name {
             type string;
             description "Class-of-service object name";
           }
           leaf cos-object-subtype {
             type string;
             description "Class-of-service object subtype";
           }
           leaf cos-object-index {
             type uint64;
             description "Class-of-service object index";
           }
         }
       }
     }
   }
   grouping cos-table-information-block {
     container cos-classifier-table-information {
       list classifier-table {
         leaf table-index {
           type uint32;
           description "Table index";
         }
         leaf number-of-entries {
           type uint32;
           description "Number of entries in an output list";
         }
         leaf table-type {
           type string;
           description "Table type";
         }
         list classifier-table-entry {
           leaf table-index {
             type uint32;
             description "Table index";
           }
           leaf code-point {
             type string;
             description "Class-of-service code point alias name or bits";
           }
           leaf fc-queue-number {
             type uint32;
             description "Class-of-service forwarding class queue number";
           }
           leaf loss-priority {
             type string;
             description "Class-of-service loss priority";
           }
         }
       }
     }
     container cos-classifier-table-map-information {
       list classifier-table-map {
         leaf logical-interface-name {
           type string;
           description "Logical interface name";
         }
         leaf logical-interface-index {
           type uint32;
           description "Logical interface index";
         }
         leaf table-index {
           type uint32;
           description "Table index";
         }
         leaf table-type {
           type string;
           description "Table type";
         }
       }
     }
     container cos-loss-priority-map-table-information {
       list loss-priority-map-table {
         leaf table-index {
           type uint32;
           description "Table index";
         }
         leaf number-of-entries {
           type uint32;
           description "Number of entries in an output list";
         }
         leaf table-type {
           type string;
           description "Table type";
         }
         list loss-priority-map-item {
           leaf code-point {
             type string;
             description "Class-of-service code point alias name or bits";
           }
           leaf loss-priority {
             type string;
             description "Class-of-service loss priority";
           }
         }
         list loss-priority-map-table-entry {
           leaf table-index {
             type uint32;
             description "Table index";
           }
           leaf code-point {
             type string;
             description "Class-of-service code point alias name or bits";
           }
           leaf loss-priority {
             type string;
             description "Class-of-service loss priority";
           }
         }
       }
     }
     container cos-loss-priority-map-table-binding-information {
       list loss-priority-map-table-binding {
         leaf logical-interface-name {
           type string;
           description "Logical interface name";
         }
         leaf logical-interface-index {
           type uint32;
           description "Logical interface index";
         }
         leaf table-index {
           type uint32;
           description "Table index";
         }
         leaf table-type {
           type string;
           description "Table type";
         }
       }
     }
     container cos-scheduler-map-table-information {
       list policy {
         leaf interface {
           type string;
         }
         leaf interface-index {
           type uint32;
           description "Class-of-service interface index";
         }
         leaf policy-index {
           type uint32;
         }
         leaf policy-type {
           type string;
         }
         leaf policy-number-of-queues {
           type uint32;
           description "Number of queues in this policy";
         }
         leaf if-traffic-control-profile-name {
           type string;
           description "Class-of-service traffic control profile name";
         }
         leaf if-traffic-control-profile-index {
           type uint32;
           description "Index number for Class-of-service traffic control profile";
         }
         leaf if-traffic-control-profile-instance-index {
           type uint32;
           description "Index number for traffic control profile instance";
         }
         leaf policy-shaping-rate {
           type uint64;
           description "Shaping rate";
         }
         leaf policy-shaping-rate-percentage {
           type uint32;
           description "Shaping rate as percentage";
         }
         leaf policy-shaping-rate-burst {
           type int32;
           description "Shaping rate burst";
         }
         leaf policy-guaranteed-rate {
           type uint64;
           description "Guaranteed rate";
         }
         leaf policy-guaranteed-rate-percent {
           type uint32;
           description "Guaranteed rate as percentage";
         }
         leaf policy-guaranteed-rate-burst {
           type uint32;
           description "Guaranteed rate burst";
         }
         leaf policy-delay-buffer-rate {
           type uint64;
           description "Delay buffer rate";
         }
         leaf policy-delay-buffer-time {
           type uint32;
           description "Delay buffer time";
         }
         leaf policy-excess-rate-proportion {
           type uint32;
           description "Excess rate";
         }
         leaf policy-excess-rate-percent {
           type uint32;
           description "Excess rate as percentage";
         }
         leaf policy-overhead-bytes {
           type uint32;
           description "Overhead bytes";
         }
         leaf policy-adjust-min-shaping-rate {
           type uint64;
           description "Adjust minimum shaping rate";
         }
         leaf policy-flags {
           type uint32;
           description "Traffic control profile flags";
         }
         leaf policy-level {
           type uint32;
           description "Traffic control profile level";
         }
         list policy-entry {
           leaf table-index {
             type uint32;
             description "Table index";
           }
           leaf policy-entry-identifier {
             type uint32;
             description "Policy entry ID number";
           }
           leaf fc-number {
             type uint32;
             description "Identifier for Class-of-service forwarding class";
           }
           leaf fc-queue-number {
             type uint32;
             description "Class-of-service forwarding class queue number";
           }
           leaf policy-transmit-rate {
             type uint32;
             description "Transmit rate";
           }
           leaf policy-transmit-rate-percentage {
             type uint32;
             description "Transmit rate percentage";
           }
           leaf policy-transmit-rate-remainder {
             type uint32;
             description "Transmit rate is remainder";
           }
           leaf policy-buffer-size-temporal {
             type uint32;
             description "Buffer size in units of time";
           }
           leaf policy-buffer-size-percentage {
             type uint32;
             description "Buffer size percentage";
           }
           leaf policy-buffer-size-remainder {
             type string;
             description "Buffer size is remainder";
           }
           leaf policy-buffer-size-shared {
             type string;
             description "Buffer size is shared";
           }
           leaf policy-buffer-multicast-share {
             type uint32;
             description "Buffer size share percent for multicaste";
           }
           leaf policy-buffer-size-multi-destination-buffers {
             type uint32;
             description "Buffer size in units of bits";
           }
           leaf policy-shared-buffer-maximum-percentage {
             type uint32;
             description "Shared Buffer maximum percentage";
           }
           leaf policy-shared-buffer-multicast-maximum-percentage {
             type uint32;
             description "Shared Buffer multicast maximum percentage";
           }
           leaf policy-entry-shaping-rate {
             type uint32;
             description "Shaping rate";
           }
           leaf policy-entry-shaping-rate-percentage {
             type uint32;
             description "Shaping rate as percentage";
           }
           leaf policy-excess-rate-proportional {
             type uint32;
             description "Excess rate as proportion";
           }
           leaf policy-excess-rate-percentage {
             type uint32;
             description "Excess rate as percentage";
           }
           leaf policy-excess-priority {
             type string;
             description "Excess priority";
           }
           leaf policy-scheduling-priority {
             type string;
             description "Scheduling priority";
           }
           leaf policy-exact {
             type uint32;
             description "Policy is exact Boolean";
           }
           container policy-packet-loss-profile {
             leaf high-drop-profile-identifier {
               type uint32;
               description "PLP high drop profile ID";
             }
             leaf medium-drop-profile-identifier {
               type uint32;
               description "PLP medium drop profile ID";
             }
             leaf low-drop-profile-identifier {
               type uint32;
               description "PLP low drop profile ID";
             }
             leaf medium-high-drop-profile-identifier {
               type uint32;
               description "PLP medium-high drop profile ID";
             }
             leaf medium-low-drop-profile-identifier {
               type uint32;
               description "PLP medium-low drop profile ID";
             }
             leaf tcp-high-drop-profile-identifier {
               type uint32;
               description "TCP PLP high drop profile ID";
             }
             leaf tcp-low-drop-profile-identifier {
               type uint32;
               description "TCP PLP low drop profile ID";
             }
           }
         }
       }
     }
     container cos-red-information {
       list red {
         leaf red-drop-profile-identifier {
           type uint32;
         }
         leaf number-of-entries {
           type uint32;
           description "Number of entries in an output list";
         }
         list red-entry {
           leaf red-entry-index {
             type uint32;
           }
           leaf red-fullness {
             type uint32;
           }
           leaf red-drop-probability {
             type uint32;
           }
         }
       }
     }
     container cos-rewrite-table-information {
       list rewrite-table {
         leaf table-index {
           type uint32;
           description "Table index";
         }
         leaf number-of-entries {
           type uint32;
           description "Number of entries in an output list";
         }
         leaf table-type {
           type string;
           description "Table type";
         }
         list rewrite-table-entry {
           leaf fc-queue-number {
             type uint32;
             description "Class-of-service forwarding class queue number";
           }
           leaf rewrite-low-codepoint {
             type string;
             description "Low loss-priority code point";
           }
           leaf rewrite-low-enable-state {
             type string;
             description "Rewrite state for loss-priority low";
           }
           leaf rewrite-high-codepoint {
             type string;
             description "High loss-priority code point";
           }
           leaf rewrite-high-enable-state {
             type string;
             description "Rewrite state for loss-priority high";
           }
           leaf rewrite-medium-codepoint {
             type string;
             description "Medium loss-priority code point";
           }
           leaf rewrite-medium-enable-state {
             type string;
             description "Rewrite state for loss-priority medium";
           }
           leaf rewrite-medium-low-codepoint {
             type string;
             description "Medium-low loss-priority code point";
           }
           leaf rewrite-medium-low-enable-state {
             type string;
             description "Rewrite state for loss-priority medium-low";
           }
           leaf rewrite-medium-high-codepoint {
             type string;
             description "Medium-high loss-priority code point";
           }
           leaf rewrite-medium-high-enable-state {
             type string;
             description "Rewrite state for loss-priority medium-high";
           }
         }
       }
     }
     container cos-rewrite-table-map-information {
       list rewrite-table-map {
         leaf logical-interface-name {
           type string;
           description "Logical interface name";
         }
         leaf logical-interface-index {
           type uint32;
           description "Logical interface index";
         }
         leaf table-index {
           type uint32;
           description "Table index";
         }
         leaf table-type {
           type string;
           description "Table type";
         }
       }
     }
     container cos-loss-priority-rewrite-table-information {
       list loss-priority-rewrite-table {
         leaf table-index {
           type uint32;
           description "Table index";
         }
         leaf number-of-entries {
           type uint32;
           description "Number of entries in an output list";
         }
         leaf table-type {
           type string;
           description "Table type";
         }
         list loss-priority-rewrite-item {
           leaf loss-priority {
             type string;
             description "Class-of-service loss priority";
           }
           leaf code-point {
             type string;
             description "Class-of-service code point alias name or bits";
           }
         }
         list loss-priority-rewrite-table-entry {
           leaf table-index {
             type uint32;
             description "Table index";
           }
           leaf loss-priority {
             type string;
             description "Class-of-service loss priority";
           }
           leaf code-point {
             type string;
             description "Class-of-service code point alias name or bits";
           }
         }
       }
     }
     container cos-loss-priority-rewrite-table-binding-information {
       list loss-priority-rewrite-table-binding {
         leaf logical-interface-name {
           type string;
           description "Logical interface name";
         }
         leaf logical-interface-index {
           type uint32;
           description "Logical interface index";
         }
         leaf table-index {
           type uint32;
           description "Table index";
         }
         leaf table-type {
           type string;
           description "Table type";
         }
       }
     }
     container cos-policer-table-map-information {
       list policer-table-map {
         leaf p-interface {
           type string;
         }
         leaf p-interface-index {
           type uint32;
         }
         leaf policer-bandwidth {
           type uint32;
           description "Class-of-service logical interface policer bandwidth";
         }
         leaf policer-burst {
           type uint32;
           description "Class-of-service logical interface policer burst";
         }
       }
     }
     container cos-shaper-table-map-information {
       list shaper-table-map {
         leaf s-interface {
           type string;
         }
         leaf s-interface-index {
           type uint32;
         }
         leaf shaper-bandwidth {
           type uint32;
           description "Class-of-service logical interface shaper bandwidth";
         }
         leaf shaper-burst {
           type uint32;
           description "Class-of-service logical interface shaper burst";
         }
       }
     }
     container cos-slice-table-information {
       description "Slice name to id information";
       list slice {
         leaf slice-name {
           type string;
           description "Class-of-service slice name";
         }
         leaf slice-index {
           type uint32;
           description "Class-of-service slice index";
         }
       }
     }
   }
   grouping cos-classifier-table-information-block {
     list classifier-table {
       leaf table-index {
         type uint32;
         description "Table index";
       }
       leaf number-of-entries {
         type uint32;
         description "Number of entries in an output list";
       }
       leaf table-type {
         type string;
         description "Table type";
       }
       list classifier-table-entry {
         leaf table-index {
           type uint32;
           description "Table index";
         }
         leaf code-point {
           type string;
           description "Class-of-service code point alias name or bits";
         }
         leaf fc-queue-number {
           type uint32;
           description "Class-of-service forwarding class queue number";
         }
         leaf loss-priority {
           type string;
           description "Class-of-service loss priority";
         }
       }
     }
   }
   grouping cos-classifier-table-map-information-block {
     list classifier-table-map {
       leaf logical-interface-name {
         type string;
         description "Logical interface name";
       }
       leaf logical-interface-index {
         type uint32;
         description "Logical interface index";
       }
       leaf table-index {
         type uint32;
         description "Table index";
       }
       leaf table-type {
         type string;
         description "Table type";
       }
     }
   }
   grouping cos-tcm-table-information-block {
     list tcm-table {
       leaf table-index {
         type uint32;
         description "Table index";
       }
       leaf number-of-entries {
         type uint32;
         description "Number of entries in an output list";
       }
       leaf table-type {
         type string;
         description "Table type";
       }
       list tcm-table-entry {
         leaf table-index {
           type uint32;
           description "Table index";
         }
         leaf code-point {
           type string;
           description "Class-of-service code point alias name or bits";
         }
         leaf tc-name {
           type string;
           description "Class-of-service traffic-class-map traffic-class name";
         }
       }
     }
   }
   grouping cos-tcm-table-map-information-block {
     list tcm-table-map {
       leaf logical-interface-name {
         type string;
         description "Logical interface name";
       }
       leaf logical-interface-index {
         type uint32;
         description "Logical interface index";
       }
       leaf table-index {
         type uint32;
         description "Table index";
       }
       leaf table-type {
         type string;
         description "Table type";
       }
     }
   }
   grouping cos-policy-map-table-information-block {
     list policy-map-table {
       leaf table-index {
         type uint32;
         description "Table index";
       }
       leaf number-of-entries {
         type uint32;
         description "Number of entries in an output list";
       }
       leaf policy-map-name {
         type string;
         description "Class-of-service Policy-map name";
       }
       leaf policy-map-user-attribute {
         type uint32;
         description "User-defined attribute";
       }
       list policy-map-table-cp-entry {
         leaf table-index {
           type uint32;
           description "Table index";
         }
         leaf code-point {
           type string;
           description "Class-of-service code point alias name or bits";
         }
         leaf code-point-type {
           type string;
           description "Class-of-service code point type";
         }
         leaf code-point-option {
           type string;
           description "Class-of-service code point option flag";
         }
       }
     }
   }
   grouping cos-policy-map-table-mapping-information-block {
     list policy-map-table-map {
       leaf logical-interface-name {
         type string;
         description "Logical interface name";
       }
       leaf logical-interface-index {
         type uint32;
         description "Logical interface index";
       }
       leaf table-index {
         type uint32;
         description "Table index";
       }
       leaf policy-map-name {
         type string;
         description "Class-of-service Policy-map name";
       }
     }
   }
   grouping cos-loss-priority-map-table-information-block {
     list loss-priority-map-table {
       leaf table-index {
         type uint32;
         description "Table index";
       }
       leaf number-of-entries {
         type uint32;
         description "Number of entries in an output list";
       }
       leaf table-type {
         type string;
         description "Table type";
       }
       list loss-priority-map-item {
         leaf code-point {
           type string;
           description "Class-of-service code point alias name or bits";
         }
         leaf loss-priority {
           type string;
           description "Class-of-service loss priority";
         }
       }
       list loss-priority-map-table-entry {
         leaf table-index {
           type uint32;
           description "Table index";
         }
         leaf code-point {
           type string;
           description "Class-of-service code point alias name or bits";
         }
         leaf loss-priority {
           type string;
           description "Class-of-service loss priority";
         }
       }
     }
   }
   grouping cos-loss-priority-map-table-binding-information-block {
     list loss-priority-map-table-binding {
       leaf logical-interface-name {
         type string;
         description "Logical interface name";
       }
       leaf logical-interface-index {
         type uint32;
         description "Logical interface index";
       }
       leaf table-index {
         type uint32;
         description "Table index";
       }
       leaf table-type {
         type string;
         description "Table type";
       }
     }
   }
   grouping cos-loss-priority-rewrite-table-information-block {
     list loss-priority-rewrite-table {
       leaf table-index {
         type uint32;
         description "Table index";
       }
       leaf number-of-entries {
         type uint32;
         description "Number of entries in an output list";
       }
       leaf table-type {
         type string;
         description "Table type";
       }
       list loss-priority-rewrite-item {
         leaf loss-priority {
           type string;
           description "Class-of-service loss priority";
         }
         leaf code-point {
           type string;
           description "Class-of-service code point alias name or bits";
         }
       }
       list loss-priority-rewrite-table-entry {
         leaf table-index {
           type uint32;
           description "Table index";
         }
         leaf loss-priority {
           type string;
           description "Class-of-service loss priority";
         }
         leaf code-point {
           type string;
           description "Class-of-service code point alias name or bits";
         }
       }
     }
   }
   grouping cos-loss-priority-rewrite-table-binding-information-block {
     list loss-priority-rewrite-table-binding {
       leaf logical-interface-name {
         type string;
         description "Logical interface name";
       }
       leaf logical-interface-index {
         type uint32;
         description "Logical interface index";
       }
       leaf table-index {
         type uint32;
         description "Table index";
       }
       leaf table-type {
         type string;
         description "Table type";
       }
     }
   }
   grouping cos-slice-table-information-block {
     list slice {
       leaf slice-name {
         type string;
         description "Class-of-service slice name";
       }
       leaf slice-index {
         type uint32;
         description "Class-of-service slice index";
       }
     }
   }
   grouping cos-scheduler-map-table-information-block {
     list policy {
       leaf interface {
         type string;
       }
       leaf interface-index {
         type uint32;
         description "Class-of-service interface index";
       }
       leaf policy-index {
         type uint32;
       }
       leaf policy-type {
         type string;
       }
       leaf policy-number-of-queues {
         type uint32;
         description "Number of queues in this policy";
       }
       leaf if-traffic-control-profile-name {
         type string;
         description "Class-of-service traffic control profile name";
       }
       leaf if-traffic-control-profile-index {
         type uint32;
         description "Index number for Class-of-service traffic control profile";
       }
       leaf if-traffic-control-profile-instance-index {
         type uint32;
         description "Index number for traffic control profile instance";
       }
       leaf policy-shaping-rate {
         type uint64;
         description "Shaping rate";
       }
       leaf policy-shaping-rate-percentage {
         type uint32;
         description "Shaping rate as percentage";
       }
       leaf policy-shaping-rate-burst {
         type int32;
         description "Shaping rate burst";
       }
       leaf policy-guaranteed-rate {
         type uint64;
         description "Guaranteed rate";
       }
       leaf policy-guaranteed-rate-percent {
         type uint32;
         description "Guaranteed rate as percentage";
       }
       leaf policy-guaranteed-rate-burst {
         type uint32;
         description "Guaranteed rate burst";
       }
       leaf policy-delay-buffer-rate {
         type uint64;
         description "Delay buffer rate";
       }
       leaf policy-delay-buffer-time {
         type uint32;
         description "Delay buffer time";
       }
       leaf policy-excess-rate-proportion {
         type uint32;
         description "Excess rate";
       }
       leaf policy-excess-rate-percent {
         type uint32;
         description "Excess rate as percentage";
       }
       leaf policy-overhead-bytes {
         type uint32;
         description "Overhead bytes";
       }
       leaf policy-adjust-min-shaping-rate {
         type uint64;
         description "Adjust minimum shaping rate";
       }
       leaf policy-flags {
         type uint32;
         description "Traffic control profile flags";
       }
       leaf policy-level {
         type uint32;
         description "Traffic control profile level";
       }
       list policy-entry {
         leaf table-index {
           type uint32;
           description "Table index";
         }
         leaf policy-entry-identifier {
           type uint32;
           description "Policy entry ID number";
         }
         leaf fc-number {
           type uint32;
           description "Identifier for Class-of-service forwarding class";
         }
         leaf fc-queue-number {
           type uint32;
           description "Class-of-service forwarding class queue number";
         }
         leaf policy-transmit-rate {
           type uint32;
           description "Transmit rate";
         }
         leaf policy-transmit-rate-percentage {
           type uint32;
           description "Transmit rate percentage";
         }
         leaf policy-transmit-rate-remainder {
           type uint32;
           description "Transmit rate is remainder";
         }
         leaf policy-buffer-size-temporal {
           type uint32;
           description "Buffer size in units of time";
         }
         leaf policy-buffer-size-percentage {
           type uint32;
           description "Buffer size percentage";
         }
         leaf policy-buffer-size-remainder {
           type string;
           description "Buffer size is remainder";
         }
         leaf policy-buffer-size-shared {
           type string;
           description "Buffer size is shared";
         }
         leaf policy-buffer-multicast-share {
           type uint32;
           description "Buffer size share percent for multicaste";
         }
         leaf policy-buffer-size-multi-destination-buffers {
           type uint32;
           description "Buffer size in units of bits";
         }
         leaf policy-shared-buffer-maximum-percentage {
           type uint32;
           description "Shared Buffer maximum percentage";
         }
         leaf policy-shared-buffer-multicast-maximum-percentage {
           type uint32;
           description "Shared Buffer multicast maximum percentage";
         }
         leaf policy-entry-shaping-rate {
           type uint32;
           description "Shaping rate";
         }
         leaf policy-entry-shaping-rate-percentage {
           type uint32;
           description "Shaping rate as percentage";
         }
         leaf policy-excess-rate-proportional {
           type uint32;
           description "Excess rate as proportion";
         }
         leaf policy-excess-rate-percentage {
           type uint32;
           description "Excess rate as percentage";
         }
         leaf policy-excess-priority {
           type string;
           description "Excess priority";
         }
         leaf policy-scheduling-priority {
           type string;
           description "Scheduling priority";
         }
         leaf policy-exact {
           type uint32;
           description "Policy is exact Boolean";
         }
         container policy-packet-loss-profile {
           leaf high-drop-profile-identifier {
             type uint32;
             description "PLP high drop profile ID";
           }
           leaf medium-drop-profile-identifier {
             type uint32;
             description "PLP medium drop profile ID";
           }
           leaf low-drop-profile-identifier {
             type uint32;
             description "PLP low drop profile ID";
           }
           leaf medium-high-drop-profile-identifier {
             type uint32;
             description "PLP medium-high drop profile ID";
           }
           leaf medium-low-drop-profile-identifier {
             type uint32;
             description "PLP medium-low drop profile ID";
           }
           leaf tcp-high-drop-profile-identifier {
             type uint32;
             description "TCP PLP high drop profile ID";
           }
           leaf tcp-low-drop-profile-identifier {
             type uint32;
             description "TCP PLP low drop profile ID";
           }
         }
       }
     }
   }
   grouping cos-policer-table-map-information-block {
     list policer-table-map {
       leaf p-interface {
         type string;
       }
       leaf p-interface-index {
         type uint32;
       }
       leaf policer-bandwidth {
         type uint32;
         description "Class-of-service logical interface policer bandwidth";
       }
       leaf policer-burst {
         type uint32;
         description "Class-of-service logical interface policer burst";
       }
     }
   }
   grouping cos-shaper-table-map-information-block {
     list shaper-table-map {
       leaf s-interface {
         type string;
       }
       leaf s-interface-index {
         type uint32;
       }
       leaf shaper-bandwidth {
         type uint32;
         description "Class-of-service logical interface shaper bandwidth";
       }
       leaf shaper-burst {
         type uint32;
         description "Class-of-service logical interface shaper burst";
       }
     }
   }
   grouping cos-red-information-block {
     list red {
       leaf red-drop-profile-identifier {
         type uint32;
       }
       leaf number-of-entries {
         type uint32;
         description "Number of entries in an output list";
       }
       list red-entry {
         leaf red-entry-index {
           type uint32;
         }
         leaf red-fullness {
           type uint32;
         }
         leaf red-drop-probability {
           type uint32;
         }
       }
     }
   }
   grouping cos-rewrite-table-information-block {
     list rewrite-table {
       leaf table-index {
         type uint32;
         description "Table index";
       }
       leaf number-of-entries {
         type uint32;
         description "Number of entries in an output list";
       }
       leaf table-type {
         type string;
         description "Table type";
       }
       list rewrite-table-entry {
         leaf fc-queue-number {
           type uint32;
           description "Class-of-service forwarding class queue number";
         }
         leaf rewrite-low-codepoint {
           type string;
           description "Low loss-priority code point";
         }
         leaf rewrite-low-enable-state {
           type string;
           description "Rewrite state for loss-priority low";
         }
         leaf rewrite-high-codepoint {
           type string;
           description "High loss-priority code point";
         }
         leaf rewrite-high-enable-state {
           type string;
           description "Rewrite state for loss-priority high";
         }
         leaf rewrite-medium-codepoint {
           type string;
           description "Medium loss-priority code point";
         }
         leaf rewrite-medium-enable-state {
           type string;
           description "Rewrite state for loss-priority medium";
         }
         leaf rewrite-medium-low-codepoint {
           type string;
           description "Medium-low loss-priority code point";
         }
         leaf rewrite-medium-low-enable-state {
           type string;
           description "Rewrite state for loss-priority medium-low";
         }
         leaf rewrite-medium-high-codepoint {
           type string;
           description "Medium-high loss-priority code point";
         }
         leaf rewrite-medium-high-enable-state {
           type string;
           description "Rewrite state for loss-priority medium-high";
         }
       }
     }
   }
   grouping cos-rewrite-table-map-information-block {
     list rewrite-table-map {
       leaf logical-interface-name {
         type string;
         description "Logical interface name";
       }
       leaf logical-interface-index {
         type uint32;
         description "Logical interface index";
       }
       leaf table-index {
         type uint32;
         description "Table index";
       }
       leaf table-type {
         type string;
         description "Table type";
       }
     }
   }
   grouping cos-forwarding-class-map-table-information-block {
     list forwarding-class-queue-table {
       leaf table-index {
         type uint32;
         description "Table index";
       }
       leaf number-of-entries {
         type uint32;
         description "Number of entries in an output list";
       }
       list forwarding-class-queue-table-entry {
         leaf fc-number {
           type uint32;
           description "Identifier for Class-of-service forwarding class";
         }
         leaf fc-queue-number {
           type uint32;
           description "Class-of-service forwarding class queue number";
         }
         leaf fc-rqueue-number {
           type uint32;
           description "Class-of-service forwarding class restricted queue number";
         }
       }
     }
   }
   grouping cos-forwarding-class-map-interface-table-information-block {
     list forwarding-class-queue-table-map {
       leaf logical-interface-name {
         type string;
         description "Logical interface name";
       }
       leaf logical-interface-index {
         type uint32;
         description "Logical interface index";
       }
       leaf table-index {
         type uint32;
         description "Table index";
       }
     }
   }
   grouping cos-fabric-scheduler-map-table-information-block {
     container fabric-scheduler-map-table {
       list fabric-scheduler-table {
         leaf fabric-scheduler-drop-profile-hn-index {
           type uint32;
           description "Class-of-service scheduler drop profile index high, non-TCP";
         }
         leaf fabric-scheduler-drop-profile-ln-index {
           type uint32;
           description "Class-of-service scheduler drop profile index low, non-TCP";
         }
         leaf fabric-scheduler-drop-profile-ht-index {
           type uint32;
           description "Class-of-service scheduler drop profile index high, TCP";
         }
         leaf fabric-scheduler-drop-profile-lt-index {
           type uint32;
           description "Class-of-service scheduler drop profile index low, TCP";
         }
         leaf fabric-scheduler-index {
           type uint32;
           description "Class of service scheduler index";
         }
         leaf fabric-scheduler-priority {
           type string;
         }
         leaf-list fabric-scheduler-queues {
           type string;
         }
       }
     }
   }
   grouping cos-translation-table-information-block {
     list translation-table {
       description "Class-of-service code point translation table";
       leaf table-index {
         type uint32;
         description "Table index";
       }
       leaf number-of-entries {
         type uint32;
         description "Number of entries in an output list";
       }
       leaf translation-table-type {
         type string;
         description "Class-of-service translation table type";
       }
       container translation-table-map {
         container translation-table-map-item {
           leaf from-code-point {
             type string;
             description "Class-of-service code point alias name or bits";
           }
           leaf to-code-point {
             type string;
             description "Class-of-service code point alias name or bits";
           }
         }
       }
       list translation-table-entry {
         leaf table-index {
           type uint32;
           description "Table index";
         }
         leaf from-code-point {
           type string;
           description "Class-of-service code point alias name or bits";
         }
         leaf to-code-point {
           type string;
           description "Class-of-service code point alias name or bits";
         }
       }
     }
   }
   grouping cos-translation-table-mapping-information-block {
     list translation-table-mapping {
       leaf logical-interface-name {
         type string;
         description "Logical interface name";
       }
       leaf logical-interface-index {
         type uint32;
         description "Logical interface index";
       }
       leaf table-index {
         type uint32;
         description "Table index";
       }
       leaf translation-table-type {
         type string;
         description "Class-of-service translation table type";
       }
     }
   }
   grouping fabric-queue-information-block {
     list fpc-queue-information {
       description "Show fabric queuing information for an FPC";
       leaf dest-fpc-index {
         type string;
         description "Destination FPC index";
       }
       leaf src-fpc-index {
         type string;
         description "Source FPC index";
       }
       container total-statistics {
         description "Total statistics";
         leaf total-pkts-high {
           type uint64;
           description "Total packet count for high-priority queue";
         }
         leaf total-pkts-low {
           type uint64;
           description "Total packet count for low-priority queue";
         }
         leaf total-bytes-high {
           type uint64;
           description "Total byte count for high-priority queue";
         }
         leaf total-bytes-low {
           type uint64;
           description "Total byte count for low-priority queue";
         }
         leaf total-pps-high {
           type uint32;
           description "Total packets per second count for high-priority queue";
         }
         leaf total-pps-low {
           type uint32;
           description "Total packets per second count for low-priority queue";
         }
         leaf total-bps-high {
           type uint64;
           description "Total bytes per second count for high-priority queue";
         }
         leaf total-bps-low {
           type uint64;
           description "Total bytes per second count for low-priority queue";
         }
       }
       container tx-statistics {
         description "Tx statistics";
         leaf tx-pkts-high {
           type uint64;
           description "Transmitted packet count for high-priority queue";
         }
         leaf tx-pkts-low {
           type uint64;
           description "Transmitted packet count for low-priority queue";
         }
         leaf tx-bytes-high {
           type uint64;
           description "Transmitted byte count for high-priority queue";
         }
         leaf tx-bytes-low {
           type uint64;
           description "Transmitted byte count for low-priority queue";
         }
         leaf tx-pps-high {
           type uint32;
           description "Transmitted packets per second count for high-priority queue";
         }
         leaf tx-pps-low {
           type uint32;
           description "Transmitted packets per second count for low-priority queue";
         }
         leaf tx-bps-high {
           type uint64;
           description "Transmitted bytes per second count for high-priority queue";
         }
         leaf tx-bps-low {
           type uint64;
           description "Transmitted bytes per second count for low-priority queue";
         }
       }
       container drop-statistics {
         description "Drop statistics";
         leaf drop-pkts-high {
           type uint64;
           description "Dropped packet count for high-priority queue";
         }
         leaf drop-pkts-low {
           type uint64;
           description "Dropped packet count for low-priority queue";
         }
         leaf drop-bytes-high {
           type uint64;
           description "Dropped byte count for high-priority queue";
         }
         leaf drop-bytes-low {
           type uint64;
           description "Dropped byte count for low-priority queue";
         }
         leaf drop-pps-high {
           type uint32;
           description "Dropped packets per second count for high-priority queue";
         }
         leaf drop-pps-low {
           type uint32;
           description "Dropped packets per second count for low-priority queue";
         }
         leaf drop-bps-high {
           type uint64;
           description "Dropped bytes per second count for high-priority queue";
         }
         leaf drop-bps-low {
           type uint64;
           description "Dropped bytes per second count for low-priority queue";
         }
       }
     }
   }
   grouping fabric-queue-detailed-information-block {
     list fpc-queue-detailed-information {
       description "Show detailed fabric queuing information for an FPC";
       leaf dest-fpc-index {
         type string;
         description "Destination FPC index";
       }
       leaf dest-pfe-index {
         type string;
         description "Destination pfe index";
       }
       leaf src-fpc-index {
         type string;
         description "Source FPC index";
       }
       leaf src-pfe-index {
         type string;
         description "Source pfe index";
       }
       container total-statistics {
         description "Total statistics";
         leaf total-pkts-high {
           type uint64;
           description "Total packet count for high-priority queue";
         }
         leaf total-pkts-low {
           type uint64;
           description "Total packet count for low-priority queue";
         }
         leaf total-bytes-high {
           type uint64;
           description "Total byte count for high-priority queue";
         }
         leaf total-bytes-low {
           type uint64;
           description "Total byte count for low-priority queue";
         }
         leaf total-pps-high {
           type uint32;
           description "Total packets per second count for high-priority queue";
         }
         leaf total-pps-low {
           type uint32;
           description "Total packets per second count for low-priority queue";
         }
         leaf total-bps-high {
           type uint64;
           description "Total bytes per second count for high-priority queue";
         }
         leaf total-bps-low {
           type uint64;
           description "Total bytes per second count for low-priority queue";
         }
       }
       container tx-statistics {
         description "Tx statistics";
         leaf tx-pkts-high {
           type uint64;
           description "Transmitted packet count for high-priority queue";
         }
         leaf tx-pkts-low {
           type uint64;
           description "Transmitted packet count for low-priority queue";
         }
         leaf tx-bytes-high {
           type uint64;
           description "Transmitted byte count for high-priority queue";
         }
         leaf tx-bytes-low {
           type uint64;
           description "Transmitted byte count for low-priority queue";
         }
         leaf tx-pps-high {
           type uint32;
           description "Transmitted packets per second count for high-priority queue";
         }
         leaf tx-pps-low {
           type uint32;
           description "Transmitted packets per second count for low-priority queue";
         }
         leaf tx-bps-high {
           type uint64;
           description "Transmitted bytes per second count for high-priority queue";
         }
         leaf tx-bps-low {
           type uint64;
           description "Transmitted bytes per second count for low-priority queue";
         }
       }
       container drop-statistics {
         description "Drop statistics";
         leaf drop-pkts-high {
           type uint64;
           description "Dropped packet count for high-priority queue";
         }
         leaf drop-pkts-low {
           type uint64;
           description "Dropped packet count for low-priority queue";
         }
         leaf drop-bytes-high {
           type uint64;
           description "Dropped byte count for high-priority queue";
         }
         leaf drop-bytes-low {
           type uint64;
           description "Dropped byte count for low-priority queue";
         }
         leaf drop-pps-high {
           type uint32;
           description "Dropped packets per second count for high-priority queue";
         }
         leaf drop-pps-low {
           type uint32;
           description "Dropped packets per second count for low-priority queue";
         }
         leaf drop-bps-high {
           type uint64;
           description "Dropped bytes per second count for high-priority queue";
         }
         leaf drop-bps-low {
           type uint64;
           description "Dropped bytes per second count for low-priority queue";
         }
       }
       container qdepth-statistics {
         description "Queue depth statistics";
         leaf qdepth-avg-high {
           type uint32;
           description "Average queue depth for high-priority queue";
         }
         leaf qdepth-avg-low {
           type uint32;
           description "Average queue depth for low-priority queue";
         }
         leaf qdepth-cur-high {
           type uint32;
           description "Current queue depth for high-priority queue";
         }
         leaf qdepth-cur-low {
           type uint32;
           description "Current queue depth for low-priority queue";
         }
         leaf qdepth-peak-high {
           type uint32;
           description "Peak queue depth for high-priority queue";
         }
         leaf qdepth-peak-low {
           type uint32;
           description "Peak queue depth for low-priority queue";
         }
         leaf qdepth-max-high {
           type uint32;
           description "Max queue depth for high-priority queue";
         }
         leaf qdepth-max-low {
           type uint32;
           description "Max queue depth for low-priority queue";
         }
       }
     }
   }
   grouping cos-fabric-scheduler-map-information-block {
     container fabric-scheduler-map {
       list fabric-scheduler {
         leaf fabric-scheduler-name {
           type string;
           description "Class-of-service scheduler name";
         }
         leaf fabric-scheduler-index {
           type uint32;
           description "Class of service scheduler index";
         }
         leaf fabric-scheduler-drop-profile-ln-index {
           type uint32;
           description "Class-of-service scheduler drop profile index low, non-TCP";
         }
         leaf fabric-scheduler-drop-profile-ln {
           type string;
           description "Class-of-service scheduler drop profile low, non-TCP";
         }
         leaf fabric-scheduler-drop-profile-lt-index {
           type uint32;
           description "Class-of-service scheduler drop profile index low, TCP";
         }
         leaf fabric-scheduler-drop-profile-lt {
           type string;
           description "Class-of-service scheduler drop profile low, TCP";
         }
         leaf fabric-scheduler-drop-profile-hn-index {
           type uint32;
           description "Class-of-service scheduler drop profile index high, non-TCP";
         }
         leaf fabric-scheduler-drop-profile-hn {
           type string;
           description "Class-of-service scheduler drop profile high, non-TCP";
         }
         leaf fabric-scheduler-drop-profile-ht-index {
           type uint32;
           description "Class-of-service scheduler drop profile index high, TCP";
         }
         leaf fabric-scheduler-drop-profile-ht {
           type string;
           description "Class-of-service scheduler drop profile high, TCP";
         }
         leaf fabric-scheduler-priority {
           type string;
         }
       }
     }
   }
   grouping cos-translation-table-map-information-block {
     list translation-table {
       description "Class-of-service code point translation table";
       leaf translation-table-name {
         type string;
         description "Class-of-service translation table name";
       }
       leaf translation-table-type {
         type string;
         description "Class-of-service translation table type";
       }
       leaf table-index {
         type uint32;
         description "Table index";
       }
       container translation-table-map {
         container translation-table-map-item {
           leaf from-code-point {
             type string;
             description "Class-of-service code point alias name or bits";
           }
           leaf to-code-point {
             type string;
             description "Class-of-service code point alias name or bits";
           }
         }
       }
       list translation-table-entry {
         leaf table-index {
           type uint32;
           description "Table index";
         }
         leaf from-code-point {
           type string;
           description "Class-of-service code point alias name or bits";
         }
         leaf to-code-point {
           type string;
           description "Class-of-service code point alias name or bits";
         }
       }
     }
   }
   grouping cos-congestion-notification-information-block {
     container cos-congestion-notification {
       leaf congestion-notification-name {
         type string;
         description "Class-of-service congestion-notification name";
       }
       leaf congestion-notification-id {
         type uint32;
         description "Class-of-service congestion-notification Index";
       }
       container congestion-notification-input {
         leaf congestion-notification-type {
           type string;
           description "Class-of-service congestion-notification type";
         }
         leaf pfc-cable-length {
           type uint32;
           description "Length of cable in meter";
         }
         container congestion-notification-pfc-account-map {
           container congestion-notification-pfc-account-map-item {
             leaf pfc-empty {
               type empty;
             }
             leaf pfc-account-name {
               type string;
               description "Pfc Account name";
             }
             leaf pfc-account-xon {
               type uint32;
               description "Pfc Xon threshold value";
             }
             leaf pfc-account-xoff {
               type uint32;
               description "Pfc Xoff threshold value";
             }
             list pfc-account-priority-list {
               leaf pfc-account-priority {
                 type uint32;
                 description "Pfc account priority";
               }
             }
           }
         }
         container congestion-notification-map {
           container congestion-notification-map-item {
             leaf pfc-priority {
               type string;
               description "PFC priority";
             }
             leaf pfc-enable-state {
               type string;
               description "PFC state for the priority";
             }
             leaf pfc-mru {
               type uint32;
               description "Maximum Rx Unit";
             }
             leaf pfc-account-name {
               type string;
               description "Pfc Account name";
             }
             leaf pfc-xon {
               type uint32;
               description "Pfc Xon value";
             }
           }
         }
       }
       container congestion-notification-output {
         leaf congestion-notification-type {
           type string;
           description "Class-of-service congestion-notification type";
         }
         container congestion-notification-output-map {
           container congestion-notification-output-map-item {
             leaf pfc-empty {
               type empty;
             }
             leaf pfc-priority {
               type string;
               description "PFC priority";
             }
             list pfc-flow-control-queue-list {
               leaf pfc-flow-control-queue {
                 type uint32;
                 description "Flow Control Queue";
               }
             }
           }
         }
       }
       container congestion-notification-pfc-watchdog {
         leaf pfc-wd-enabled {
           type string;
           description "Congestion notification profile - PFC watchdog";
         }
         leaf pfc-wd-action {
           type string;
           description "Congestion notification profile - PFC action";
         }
         leaf pfc-wd-poll-interval {
           type uint32;
           description "PFC watchdog poll intervals";
         }
         leaf pfc-wd-detection {
           type int32;
           description "PFC watchdog detection timer (milliseconds)";
         }
         leaf pfc-wd-recovery {
           type int32;
           description "PFC watchdog recovery timer (milliseconds)";
         }
       }
     }
   }
   grouping cos-adjustment-control-profile-information-block {
     list adjustment-control-profile {
       leaf adjustment-control-profile-name {
         type string;
         description "Class-of-service adjustment control profile name";
       }
       leaf adjustment-control-profile-application-name {
         type string;
         description "Class-of-service adjustment control profile application name";
       }
       leaf adjustment-control-profile-priority {
         type uint32;
         description "Class-of-service adjustment control profile application priority";
       }
       leaf adjustment-control-profile-algorithm {
         type string;
         description "Class-of-service adjustment control profile application algorithm";
       }
     }
   }
   grouping scheduler-hierarchy-information-block {
     container scheduler-hierarchy-header {
       leaf dummy {
         type string;
       }
     }
     container scheduler-hierarchy-terse-header {
       leaf dummy-terse {
         type string;
       }
     }
     list scheduler-hierarchy-node {
       leaf node-name {
         type string;
         description "Scheduler node name";
       }
       leaf shaping-rate {
         type uint64;
         description "Class-of-service shaping rate";
       }
       leaf node-type {
         type string;
         description "Scheduler node type";
       }
       leaf shaping-rate-priority-strict-high {
         type uint64;
         description "Class-of-service shaping rate for priority strict high";
       }
       leaf shaping-rate-priority-high {
         type uint64;
         description "Class-of-service shaping rate for priority high";
       }
       leaf shaping-rate-priority-medium {
         type uint64;
         description "Class-of-service shaping rate for priority medium";
       }
       leaf shaping-rate-priority-medium-low {
         type uint64;
         description "Class-of-service shaping rate for priority medium-low";
       }
       leaf shaping-rate-priority-low {
         type uint64;
         description "Class-of-service shaping rate for priority low";
       }
       leaf shaping-rate-excess-high {
         type uint64;
         description "Class-of-service shaping rate for excess high";
       }
       leaf shaping-rate-excess-medium-high {
         type uint64;
         description "Class-of-service shaping rate for excess medium-high";
       }
       leaf shaping-rate-excess-medium-low {
         type uint64;
         description "Class-of-service shaping rate for excess medium-low";
       }
       leaf shaping-rate-excess-low {
         type uint64;
         description "Class-of-service shaping rate for excess low";
       }
       leaf node-adjustment-mode {
         type string;
         description "Adjustment mode";
       }
       leaf node-adjustment-bytes {
         type int32;
         description "Adjustment byte count";
       }
       leaf guaranteed-rate {
         type uint64;
         description "Class-of-service guaranteed rate";
       }
       leaf weight-excess-rate-high {
         type uint32;
         description "Weight for excess-high priority traffic";
       }
       leaf weight-excess-rate-low {
         type uint32;
         description "Weight for excess-low priority traffic";
       }
       leaf weight-excess-rate-medium-high {
         type uint32;
         description "Weight for excess-medium-high priority traffic";
       }
       leaf weight-excess-rate-medium-low {
         type uint32;
         description "Weight for excess-medium-low priority traffic";
       }
       leaf rate-excess-high-promote-to-guaranteed {
         type string;
         description "Promotion rule to a guaranteed priority";
       }
       leaf rate-excess-low-promote-to-guaranteed {
         type string;
         description "Promotion rule to a guaranteed priority";
       }
       leaf rate-excess-medium-high-promote-to-guaranteed {
         type string;
         description "Promotion rule to a guaranteed priority";
       }
       leaf rate-excess-medium-low-promote-to-guaranteed {
         type string;
         description "Promotion rule to a guaranteed priority";
       }
       leaf oor-resource-state {
         type string;
         description "Scheduler hierarchy out-of-resource state";
       }
       leaf queue-guaranteed-priority {
         type string;
         description "Queue guaranteed priority";
       }
       leaf queue-excess-priority {
         type string;
         description "Queue excess priority";
       }
       leaf queue-weight {
         type uint32;
         description "Queue weight";
       }
       leaf queue-max-depth {
         type uint32;
         description "Max queue depth";
       }
       leaf queue-depth {
         type uint32;
         description "Instantaneous queue depth";
       }
       leaf time-average-queue-length {
         type uint32;
         description "Time average queue length";
       }
       leaf terse-output {
         type empty;
         description "Terse output";
       }
     }
   }
   grouping scheduler-resources-information-block {
     list scheduler-resources {
       leaf scheduler-resources-slot-num {
         type uint32;
         description "Slot number";
       }
       list scheduler-resources-pfe {
         leaf scheduler-resources-pfe-id {
           type uint32;
           description "Class of service PFE ID";
         }
         list scheduler-resources-sched {
           leaf scheduler-resources-sched-id {
             type uint32;
             description "Class of service Scheduler ID";
           }
           leaf scheduler-resources-l1-limit {
             type string;
             description "Class of service L1 nodes have reached limit";
           }
           leaf scheduler-resources-l1-used {
             type uint32;
             description "Class of service L1 Nodes Used";
           }
           leaf scheduler-resources-l1-total {
             type uint32;
             description "Class of service L1 Nodes Total";
           }
           leaf scheduler-resources-l1-time-pending {
             type uint32;
             description "Class of service L1 Nodes time waiting for resource";
           }
           leaf scheduler-resources-l2-limit {
             type string;
             description "Class of service L2 nodes have reached limit";
           }
           leaf scheduler-resources-l2-used {
             type uint32;
             description "Class of service L2 Nodes Used";
           }
           leaf scheduler-resources-l2-total {
             type uint32;
             description "Class of service L2 Nodes Total";
           }
           leaf scheduler-resources-l2-time-pending {
             type uint32;
             description "Class of service L2 Nodes time waiting for resource";
           }
           leaf scheduler-resources-l3-limit {
             type string;
             description "Class of service L3 nodes have reached limit";
           }
           leaf scheduler-resources-l3-used {
             type uint32;
             description "Class of service L3 Nodes Used";
           }
           leaf scheduler-resources-l3-total {
             type uint32;
             description "Class of service L3 Nodes Total";
           }
           leaf scheduler-resources-l3-time-pending {
             type uint32;
             description "Class of service L3 Nodes time waiting for resource";
           }
           leaf scheduler-resources-l4-limit {
             type string;
             description "Class of service L4 nodes have reached limit";
           }
           leaf scheduler-resources-l4-used {
             type uint32;
             description "Class of service L4 Nodes Used";
           }
           leaf scheduler-resources-l4-total {
             type uint32;
             description "Class of service L4 Nodes Total";
           }
           leaf scheduler-resources-l4-time-pending {
             type uint32;
             description "Class of service L4 Nodes time waiting for resource";
           }
           leaf scheduler-resources-q-limit {
             type string;
             description "Class of service Qs have reached limit";
           }
           leaf scheduler-resources-q-used {
             type uint32;
             description "Class of service Q Nodes Used";
           }
           leaf scheduler-resources-q-total {
             type uint32;
             description "Class of service Q Nodes Total";
           }
           leaf scheduler-resources-q-time-pending {
             type uint32;
             description "Class of service Q Nodes time waiting for resource";
           }
         }
       }
     }
   }
   grouping cos-client-information-block {
     list cos-client {
       description "Class-of-service Junos client information";
       leaf cos-client-info-internal-id {
         type uint32;
         description "Junos client internal identifier";
       }
       leaf cos-client-info-requests {
         type uint32;
         description "Number of requests from Junos client";
       }
       leaf cos-client-info-responses {
         type uint32;
         description "Number of responses to Junos client";
       }
       leaf cos-client-info-failures {
         type uint32;
         description "Number of failures while handling Junos client requests";
       }
       leaf cos-client-info-identifier {
         type string;
         description "Junos client identifier";
       }
       leaf cos-client-name {
         type string;
         description "Junos client name";
       }
       leaf cos-client-state {
         type string;
         description "Junos client state information";
       }
       leaf cos-client-internal-name {
         type string;
         description "Junos client internal name";
       }
       leaf cos-client-stats {
         type string;
         description "Junos client statistics";
       }
       leaf cos-client-failure-stats {
         type string;
         description "Junos client failure/error statistics";
       }
       leaf cos-client-validate-failures {
         type uint32;
         description "Junos client request validation failures";
       }
       leaf cos-client-ownership-failures {
         type uint32;
         description "Junos client ownership validation failures";
       }
       leaf cos-client-info-name {
         type string;
         description "CoS client name";
       }
       leaf cos-client-internal-id {
         type uint32;
         description "Junos client internal identifier";
       }
       leaf cos-client-requests {
         type uint64;
         description "Number of requests from Junos client";
       }
       leaf cos-client-responses {
         type uint64;
         description "Number of responses to Junos client";
       }
       leaf cos-client-failures {
         type uint64;
         description "Number of failures while handling Junos client requests";
       }
       leaf cos-client-identifier {
         type string;
         description "Junos client identifier";
       }
       leaf cos-client-status {
         type string;
         description "Junos client status";
       }
       leaf cos-client-connected-time {
         type string;
         description "Junos client time of connect";
       }
       leaf cos-client-reconnected-time {
         type string;
         description "Junos client time of reconnect";
       }
       leaf cos-client-disconnected-time {
         type string;
         description "Junos client time of disconnect";
       }
       leaf cos-client-message-type {
         type string;
         description "Junos client message type";
       }
       leaf cos-client-operation-type {
         type string;
         description "Junos client operation type";
       }
       leaf-list cos-bind-point-type {
         type string;
         description "Class-of-service bind point type";
       }
       leaf-list cos-bind-point-owner-type {
         type string;
         description "Class-of-service bind point owner type";
       }
       leaf-list cos-bind-point-owner-internal-id {
         type uint32;
         description "Junos client internal identifier";
       }
       leaf-list cos-bind-point-name {
         type string;
         description "Class-of-service bind point name";
       }
       leaf cos-bind-point-feature {
         type string;
         description "Class-of-service bind point feature name";
       }
       leaf cos-bind-point-feature-object-name {
         type string;
         description "Class-of-service bind point feature object name";
       }
     }
   }
   grouping cos-host-outbound-info-block {
     list cos-host-outbound-traffic-info {
       description "Class-of-service host-outbound-traffic information";
       leaf cos-host-outbound-traffic-protocol-name {
         type string;
         description "CoS host outbound traffic protocol name";
       }
       leaf cos-host-outbound-traffic-dscp {
         type string;
         description "CoS host outbound traffic dscp";
       }
       leaf cos-host-outbound-traffic-dot1p {
         type string;
         description "CoS host outbound traffic ieee 802.1p";
       }
       leaf cos-host-outbound-traffic-fc-id {
         type string;
         description "CoS host outbound traffic forwarding class id";
       }
       leaf cos-host-outbound-traffic-queue-id {
         type string;
         description "CoS host outbound traffic queue id";
       }
       leaf cos-host-outbound-traffic-restrict-queue-id {
         type string;
         description "CoS host outbound traffic restrict queue id";
       }
       leaf cos-host-outbound-traffic-override-firewall {
         type string;
         description "CoS host outbound traffic override firwall action";
       }
       leaf cos-host-outbound-traffic-rw-dot1p {
         type string;
         description "CoS host outbound traffic - use ieee 802.1p rewrite rules";
       }
     }
   }
   grouping cos-packet-buffer-usage-information-block {
     leaf total-buffer-egress-used {
       type string;
       description "Total Buffer Used at Egress in KB";
     }
     leaf total-buffer-egress-bytes {
       type string;
       description "Total Buffer at Egress in KB";
     }
     leaf total-buffer-egress-used-pkts {
       type string;
       description "Total Buffer Used at Egress in packets";
     }
     leaf total-buffer-egress-pkts {
       type string;
       description "Total Buffer at Egress in packets";
     }
     leaf dedicated-buffer-egress-used {
       type string;
       description "Dedicated Buffer Used at Egress in KB";
     }
     leaf dedicated-buffer-egress-bytes {
       type string;
       description "Dedicated Buffer at Egress in KB";
     }
     leaf dedicated-buffer-egress-used-pkts {
       type string;
       description "Dedicated Buffer Used at Egress in packets";
     }
     leaf dedicated-buffer-egress-pkts {
       type string;
       description "Dedicated Buffer at Egress in packets";
     }
     leaf shared-buffer-egress-used {
       type string;
       description "Shared Buffer Used at Egress in KB";
     }
     leaf shared-buffer-egress-bytes {
       type string;
       description "Shared Buffer at Egress in KB";
     }
     leaf shared-buffer-egress-used-pkts {
       type string;
       description "Shared Buffer Used at Egress in packets";
     }
     leaf shared-buffer-egress-pkts {
       type string;
       description "Shared Buffer at Egress in packets";
     }
   }
 }
