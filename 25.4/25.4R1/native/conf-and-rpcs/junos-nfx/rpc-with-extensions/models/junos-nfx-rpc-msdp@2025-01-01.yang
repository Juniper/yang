/*
 * Copyright (c) 2025 Juniper Networks, Inc.
 * All rights reserved.
 */
 module junos-nfx-rpc-msdp {
   namespace "http://yang.juniper.net/junos-nfx/rpc/msdp";

   prefix msdp;

   import junos-common-ddl-extensions {
     prefix junos;
     revision-date 2025-01-01;
   }

   import junos-common-types {
     prefix jt;
     revision-date 2025-01-01;
   }

   organization "Juniper Networks, Inc.";

   contact "yang-support@juniper.net";

   description "Junos RPC YANG module for msdp command(s)";

   revision 2025-01-01 {
     description "Junos: 25.4R1.12";
   }

   rpc get-msdp-information {
     description "Show Multicast Source Discovery Protocol information";
     junos:command "show msdp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf peer {
         description "IPv4 address and optional prefix length of MSDP peers";
         type jt:ipv4prefix;
       }
       leaf verbosity_level {
         junos:cli-feature "nokeyword";
         default "brief";
         type enumeration {
           enum "brief" {
             description "Display brief output (default)";
           }
           enum "detail" {
             description "Display detailed output";
           }
         }
       }
     }
     output {
       container msdp-peer-information {
         uses msdp-peer-information-block;
       }
     }
   }
   rpc get-msdp-statistics-information {
     description "Show MSDP statistics";
     junos:command "show msdp statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf peer {
         description "IPv4 address and optional prefix length of MSDP peers";
         type jt:ipv4addr;
       }
     }
     output {
       container msdp-statistics-information {
         uses msdp-statistics-information-block;
       }
     }
   }
   rpc get-msdp-source-information {
     description "Show multicast sources learned from MSDP";
     junos:command "show msdp source";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf source {
         description "IP address and optional prefix length of source";
         junos:cli-feature "nokeyword";
         type jt:ipv4addr;
       }
     }
     output {
       container msdp-source-information {
         uses msdp-source-information-block;
       }
     }
   }
   rpc get-msdp-source-active-information {
     description "Show the source-active (SA) cache";
     junos:command "show msdp source-active";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf group {
         description "Name of group";
         type string;
       }
       leaf source {
         description "Name of source";
         type string;
       }
       leaf peer {
         description "IPv4 address of peer";
         type jt:ipv4addr;
       }
       leaf local {
         description "Display SA cache entries originating at this router";
         type empty;
       }
       leaf originator {
         description "IPv4 address of peer that originated SA cache entries";
         type jt:ipv4addr;
       }
       leaf verbosity_level {
         junos:cli-feature "nokeyword";
         default "brief";
         type enumeration {
           enum "brief" {
             description "Display brief output (default)";
           }
           enum "detail" {
             description "Display detailed output";
           }
         }
       }
     }
     output {
       container msdp-source-active-information {
         uses msdp-source-active-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping msdp-peer-information-block {
     leaf msdp-no-peers {
       type empty;
     }
     list msdp-peer {
       leaf msdp-peer-address {
         type jt:ipaddr;
       }
       leaf msdp-local-address {
         type jt:ipaddr;
       }
       leaf msdp-state {
         type string;
       }
       leaf msdp-state-change {
         type string;
       }
       leaf msdp-group-name {
         type string;
       }
       leaf msdp-sa-accepted {
         type int32;
         description "Number of SAs accepted from peer";
       }
       leaf msdp-sa-received {
         type int32;
         description "Number of SAs received from peer";
       }
       leaf msdp-active-source-limit-exceeded {
         type int32;
       }
       leaf msdp-connect-retries {
         type int32;
       }
       leaf msdp-state-timeout {
         type int32;
       }
       leaf msdp-peer-timeout {
         type int32;
       }
       leaf msdp-active-source-limit-maximum {
         type uint32;
       }
       leaf msdp-active-source-limit-threshold {
         type uint32;
       }
       leaf msdp-active-source-limit-log-warning {
         type uint32;
       }
       leaf msdp-active-source-limit-log-interval {
         type uint32;
       }
       leaf msdp-socket-primary {
         type int32;
         description "MSDP Peer Socket on Primary";
       }
       leaf msdp-socket-secondary {
         type int32;
         description "MSDP Peer Socket on Secondary";
       }
       leaf msdp-socket-handler {
         type uint32;
         description "Socket Replication Handler";
       }
       leaf msdp-residual-inbound-bytes {
         type int32;
       }
       leaf msdp-residual-outbound-bytes {
         type int32;
       }
     }
   }
   grouping msdp-statistics-information-block {
     leaf msdp-no-peer {
       type jt:ipaddr;
     }
     list msdp-instance {
       leaf-list instance-name {
         type string;
       }
       leaf msdp-global-active-source-limit-exceeded {
         type int32;
       }
       leaf msdp-global-active-source-limit-maximum {
         type uint32;
       }
       leaf msdp-global-active-source-limit-threshold {
         type uint32;
       }
       leaf msdp-global-active-source-limit-log-warning {
         type uint32;
       }
       leaf msdp-global-active-source-limit-log-interval {
         type uint32;
       }
       list msdp-route {
         leaf multicast-group-address {
           type jt:ipaddr;
           description "Group address";
         }
         leaf multicast-source-address {
           type jt:ipaddr;
           description "Source address";
         }
         list msdp-route-peer {
           leaf msdp-peer-address {
             type jt:ipaddr;
           }
           leaf msdp-originator {
             type jt:ipaddr;
           }
           container msdp-route-peer-flags {
             leaf msdp-accept {
               type empty;
             }
             leaf msdp-reject {
               type empty;
             }
             leaf msdp-filtered {
               type empty;
             }
           }
         }
       }
       list msdp-source {
         leaf msdp-source-prefix {
           type jt:ipaddr;
         }
         leaf msdp-source-prefix-length {
           type uint32;
         }
         leaf msdp-source-type {
           type string;
         }
         leaf msdp-source-limit-maximum {
           type string;
         }
         leaf msdp-source-limit-threshold {
           type string;
         }
         leaf msdp-source-limit-exceeded {
           type int32;
         }
         leaf msdp-source-limit-log-warning {
           type string;
         }
         leaf msdp-source-limit-log-interval {
           type string;
         }
       }
       list msdp-peer-statistics {
         leaf msdp-peer-address {
           type jt:ipaddr;
         }
         leaf msdp-state-change-absolute {
           type string;
         }
         leaf msdp-state-change {
           type string;
         }
         leaf msdp-message-received-absolute {
           type string;
         }
         leaf msdp-message-received {
           type string;
         }
         leaf msdp-rpf-failures {
           type int32;
         }
         leaf msdp-remote-closes {
           type int32;
         }
         leaf msdp-peer-timeouts {
           type int32;
         }
         leaf msdp-sa-messages-sent {
           type int32;
         }
         leaf msdp-sa-messages-received {
           type int32;
         }
         leaf msdp-sa-requests-sent {
           type int32;
         }
         leaf msdp-sa-requests-received {
           type int32;
         }
         leaf msdp-sa-responses-sent {
           type int32;
         }
         leaf msdp-sa-responses-received {
           type int32;
         }
         leaf msdp-active-source-limit-exceeded {
           type int32;
         }
         leaf msdp-active-source-limit-maximum {
           type uint32;
         }
         leaf msdp-active-source-limit-threshold {
           type uint32;
         }
         leaf msdp-active-source-limit-log-warning {
           type uint32;
         }
         leaf msdp-active-source-limit-log-interval {
           type uint32;
         }
         leaf msdp-keepalives-sent {
           type int32;
         }
         leaf msdp-keepalives-received {
           type int32;
         }
         leaf msdp-unknowns-received {
           type int32;
         }
         leaf msdp-sa-zero-entry-received {
           type uint32;
         }
         leaf msdp-errors-received {
           type int32;
         }
       }
     }
   }
   grouping msdp-source-information-block {
     list msdp-instance {
       leaf-list instance-name {
         type string;
       }
       leaf msdp-no-source {
         type jt:ipaddr;
       }
       list msdp-route {
         leaf multicast-group-address {
           type jt:ipaddr;
           description "Group address";
         }
         leaf multicast-source-address {
           type jt:ipaddr;
           description "Source address";
         }
         list msdp-route-peer {
           leaf msdp-peer-address {
             type jt:ipaddr;
           }
           leaf msdp-originator {
             type jt:ipaddr;
           }
           container msdp-route-peer-flags {
             leaf msdp-accept {
               type empty;
             }
             leaf msdp-reject {
               type empty;
             }
             leaf msdp-filtered {
               type empty;
             }
           }
         }
       }
       list msdp-source {
         leaf msdp-source-prefix {
           type jt:ipaddr;
         }
         leaf msdp-source-prefix-length {
           type uint32;
         }
         leaf msdp-source-type {
           type string;
         }
         leaf msdp-source-limit-maximum {
           type string;
         }
         leaf msdp-source-limit-threshold {
           type string;
         }
         leaf msdp-source-limit-exceeded {
           type int32;
         }
         leaf msdp-source-limit-log-warning {
           type string;
         }
         leaf msdp-source-limit-log-interval {
           type string;
         }
       }
       list msdp-peer-statistics {
         leaf msdp-peer-address {
           type jt:ipaddr;
         }
         leaf msdp-state-change-absolute {
           type string;
         }
         leaf msdp-state-change {
           type string;
         }
         leaf msdp-message-received-absolute {
           type string;
         }
         leaf msdp-message-received {
           type string;
         }
         leaf msdp-rpf-failures {
           type int32;
         }
         leaf msdp-remote-closes {
           type int32;
         }
         leaf msdp-peer-timeouts {
           type int32;
         }
         leaf msdp-sa-messages-sent {
           type int32;
         }
         leaf msdp-sa-messages-received {
           type int32;
         }
         leaf msdp-sa-requests-sent {
           type int32;
         }
         leaf msdp-sa-requests-received {
           type int32;
         }
         leaf msdp-sa-responses-sent {
           type int32;
         }
         leaf msdp-sa-responses-received {
           type int32;
         }
         leaf msdp-active-source-limit-exceeded {
           type int32;
         }
         leaf msdp-active-source-limit-maximum {
           type uint32;
         }
         leaf msdp-active-source-limit-threshold {
           type uint32;
         }
         leaf msdp-active-source-limit-log-warning {
           type uint32;
         }
         leaf msdp-active-source-limit-log-interval {
           type uint32;
         }
         leaf msdp-keepalives-sent {
           type int32;
         }
         leaf msdp-keepalives-received {
           type int32;
         }
         leaf msdp-unknowns-received {
           type int32;
         }
         leaf msdp-sa-zero-entry-received {
           type uint32;
         }
         leaf msdp-errors-received {
           type int32;
         }
       }
     }
   }
   grouping msdp-source-active-information-block {
     list msdp-instance {
       leaf-list instance-name {
         type string;
       }
       leaf msdp-no-routes {
         type jt:ipaddr;
       }
       leaf msdp-global-active-source-limit-exceeded {
         type int32;
       }
       leaf msdp-global-active-source-limit-maximum {
         type uint32;
       }
       leaf msdp-global-active-source-limit-threshold {
         type uint32;
       }
       leaf msdp-global-active-source-limit-log-warning {
         type uint32;
       }
       leaf msdp-global-active-source-limit-log-interval {
         type uint32;
       }
       list msdp-route {
         leaf multicast-group-address {
           type jt:ipaddr;
           description "Group address";
         }
         leaf multicast-source-address {
           type jt:ipaddr;
           description "Source address";
         }
         list msdp-route-peer {
           leaf msdp-peer-address {
             type jt:ipaddr;
           }
           leaf msdp-originator {
             type jt:ipaddr;
           }
           container msdp-route-peer-flags {
             leaf msdp-accept {
               type empty;
             }
             leaf msdp-reject {
               type empty;
             }
             leaf msdp-filtered {
               type empty;
             }
           }
         }
       }
       list msdp-source {
         leaf msdp-source-prefix {
           type jt:ipaddr;
         }
         leaf msdp-source-prefix-length {
           type uint32;
         }
         leaf msdp-source-type {
           type string;
         }
         leaf msdp-source-limit-maximum {
           type string;
         }
         leaf msdp-source-limit-threshold {
           type string;
         }
         leaf msdp-source-limit-exceeded {
           type int32;
         }
         leaf msdp-source-limit-log-warning {
           type string;
         }
         leaf msdp-source-limit-log-interval {
           type string;
         }
       }
       list msdp-peer-statistics {
         leaf msdp-peer-address {
           type jt:ipaddr;
         }
         leaf msdp-state-change-absolute {
           type string;
         }
         leaf msdp-state-change {
           type string;
         }
         leaf msdp-message-received-absolute {
           type string;
         }
         leaf msdp-message-received {
           type string;
         }
         leaf msdp-rpf-failures {
           type int32;
         }
         leaf msdp-remote-closes {
           type int32;
         }
         leaf msdp-peer-timeouts {
           type int32;
         }
         leaf msdp-sa-messages-sent {
           type int32;
         }
         leaf msdp-sa-messages-received {
           type int32;
         }
         leaf msdp-sa-requests-sent {
           type int32;
         }
         leaf msdp-sa-requests-received {
           type int32;
         }
         leaf msdp-sa-responses-sent {
           type int32;
         }
         leaf msdp-sa-responses-received {
           type int32;
         }
         leaf msdp-active-source-limit-exceeded {
           type int32;
         }
         leaf msdp-active-source-limit-maximum {
           type uint32;
         }
         leaf msdp-active-source-limit-threshold {
           type uint32;
         }
         leaf msdp-active-source-limit-log-warning {
           type uint32;
         }
         leaf msdp-active-source-limit-log-interval {
           type uint32;
         }
         leaf msdp-keepalives-sent {
           type int32;
         }
         leaf msdp-keepalives-received {
           type int32;
         }
         leaf msdp-unknowns-received {
           type int32;
         }
         leaf msdp-sa-zero-entry-received {
           type uint32;
         }
         leaf msdp-errors-received {
           type int32;
         }
       }
     }
   }
 }
