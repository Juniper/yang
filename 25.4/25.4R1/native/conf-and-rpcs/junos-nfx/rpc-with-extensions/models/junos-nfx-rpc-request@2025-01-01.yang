/*
 * Copyright (c) 2025 Juniper Networks, Inc.
 * All rights reserved.
 */
 module junos-nfx-rpc-request {
   namespace "http://yang.juniper.net/junos-nfx/rpc/request";

   prefix request;

   import junos-common-ddl-extensions {
     prefix junos;
     revision-date 2025-01-01;
   }

   import junos-common-types {
     prefix jt;
     revision-date 2025-01-01;
   }

   organization "Juniper Networks, Inc.";

   contact "yang-support@juniper.net";

   description "Junos RPC YANG module for request command(s)";

   revision 2025-01-01 {
     description "Junos: 25.4R1.12";
   }

   rpc resize-configuraion-database {
     description "Resize the configuration database";
     junos:command "request system configuration database resize";
     input {
       uses command-forwarding;
       leaf force {
         description "Resize the configuration database even if modified";
         type empty;
       }
     }
     output {
       choice output_c {
         case output-tag {
           leaf output {
             type string;
           }
         }
         case multichassis-tag {
           anyxml multi-routing-engine-results;
         }
       }
     }
   }
   rpc request-save-rescue-configuration {
     description "Save committed configuration as rescue configuration";
     junos:command "request system configuration rescue save";
     output {
       container rescue-management-results {
         uses rescue-management-results-block;
       }
     }
   }
   rpc request-delete-rescue-configuration {
     description "Delete the rescue configuration";
     junos:command "request system configuration rescue delete";
     output {
       container rescue-management-results {
         uses rescue-management-results-block;
       }
     }
   }
   rpc request-commit-server-cleanup {
     description "Commit queue clean up operations";
     junos:command "request system commit server queue cleanup";
     input {
       choice queue-selector {
         case id {
           leaf id {
             description "Clean up queue id";
             type union {
               type uint32;
               type string {
                 pattern "<.*>|$.*";
               }
             }
           }
         }
         case job-status {
           leaf job-status {
             description "Clean up all entries with specified status";
             type enumeration {
               enum "error" {
                 description "Remove jobs that had errors";
               }
               enum "pending" {
                 description "Remove jobs that are pending";
               }
               enum "success" {
                 description "Remove jobs that succeeded";
               }
             }
           }
         }
       }
     }
     output {
       container commit-server-delete-results {
         uses commit-server-delete-results-block;
       }
     }
   }
   rpc request-commit-server-pause {
     description "Pause the commit server";
     junos:command "request system commit server pause";
     output {
       container commit-server-operation {
         uses commit-server-operation-block;
       }
     }
   }
   rpc request-commit-server-start {
     description "Start the commit server";
     junos:command "request system commit server start";
     output {
       container commit-server-operation {
         uses commit-server-operation-block;
       }
     }
   }
   rpc request-delta-exporter-initialize {
     description "Initialize delta exporter database";
     junos:command "request system commit delta-exporter initialize";
     output {
       choice output_c {
         case output-tag {
           leaf output {
             type string;
           }
         }
         case multichassis-tag {
           anyxml multi-routing-engine-results;
         }
       }
     }
   }
   rpc request-yang-add {
     description "Add YANG module(s) and action/translation script(s)";
     junos:command "request system yang add";
     input {
       leaf package {
         description "Unique ID for future op - delete/update";
         type string;
         mandatory true;
       }
       leaf-list module {
         ordered-by user;
         description "YANG module(s) path";
         type jt:filename;
       }
       leaf-list action-script {
         ordered-by user;
         description "Action script path";
         type jt:filename;
       }
       leaf-list translation-script {
         ordered-by user;
         description "Translation script path";
         type jt:filename;
       }
       leaf-list deviation-module {
         ordered-by user;
         description "Deviation module path";
         type jt:filename;
       }
       leaf proxy-xml {
         description "XML proxy YANG module(s)";
         type empty;
       }
       leaf snmp {
         description "Add custom MIB in YANG format";
         type empty;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-delete {
     description "Remove YANG package";
     junos:command "request system yang delete";
     input {
       leaf package {
         description "ID to be removed";
         junos:cli-feature "nokeyword";
         type string;
         mandatory true;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-enable {
     description "Enable YANG package to JUNOS translation";
     junos:command "request system yang enable";
     input {
       leaf package {
         description "ID";
         junos:cli-feature "nokeyword";
         type string;
         mandatory true;
       }
     }
     output {
       choice output_c {
         case output-tag {
           leaf output {
             type string;
           }
         }
         case multichassis-tag {
           anyxml multi-routing-engine-results;
         }
       }
     }
   }
   rpc request-yang-disable {
     description "Disable YANG package to JUNOS translation";
     junos:command "request system yang disable";
     input {
       leaf package {
         description "ID";
         junos:cli-feature "nokeyword";
         type string;
         mandatory true;
       }
     }
     output {
       choice output_c {
         case output-tag {
           leaf output {
             type string;
           }
         }
         case multichassis-tag {
           anyxml multi-routing-engine-results;
         }
       }
     }
   }
   rpc request-yang-validate {
     description "Validate YANG module(s) and action/translation script(s)";
     junos:command "request system yang validate";
     input {
       leaf-list module {
         ordered-by user;
         description "Name of the YANG module to be validated";
         type jt:filename;
       }
       leaf-list translation-script {
         ordered-by user;
         description "Name of the translation-script to be validated";
         type jt:filename;
       }
       leaf-list action-script {
         ordered-by user;
         description "Name of the action-script to be validated";
         type jt:filename;
       }
       leaf proxy-xml {
         description "XML proxy YANG module";
         type empty;
       }
       leaf snmp {
         description "Validate custom MIB in YANG format";
         type empty;
       }
     }
     output {
       choice output_c {
         case output-tag {
           leaf output {
             type string;
           }
         }
         case multichassis-tag {
           anyxml multi-routing-engine-results;
         }
       }
     }
   }
   rpc request-yang-update {
     description "Update YANG module(s) and action/translation script(s)";
     junos:command "request system yang update";
     input {
       leaf package {
         description "ID";
         junos:cli-feature "nokeyword";
         type string;
         mandatory true;
       }
       leaf-list module {
         ordered-by user;
         description "YANG module(s) path";
         type jt:filename;
       }
       leaf-list translation-script {
         ordered-by user;
         description "Translation script path";
         type jt:filename;
       }
       leaf-list deviation-module {
         ordered-by user;
         description "Deviation module path";
         type jt:filename;
       }
       leaf-list action-script {
         ordered-by user;
         description "Action script path";
         type jt:filename;
       }
       leaf proxy-xml {
         description "XML proxy YANG module(s)";
         type empty;
       }
       leaf snmp {
         description "Update custom MIBs in YANG format";
         type empty;
       }
     }
     output {
       choice output_c {
         case output-tag {
           leaf output {
             type string;
           }
         }
         case multichassis-tag {
           anyxml multi-routing-engine-results;
         }
       }
     }
   }
   rpc request-logout-user {
     description "Forcibly end user's CLI login session";
     junos:command "request system logout";
     input {
       uses command-forwarding;
       leaf pid {
         description "Management process ID for user";
         type union {
           type uint32;
           type string {
             pattern "<.*>|$.*";
           }
         }
       }
       leaf all {
         description "Logout all sessions owned by user";
         type empty;
       }
       leaf user {
         description "Name of user";
         type string {
           junos:posix-pattern "^[[:alnum:]_]{1,}[.]{0,1}[[:alnum:]_-]{0,}[.]{0,1}[[:alnum:]_-]{0,}$";
           junos:pattern-message "Must contain characters (alphanumerics, underscores or hyphens) beginning with an alphanumeric or an underscore character.";
         }
       }
       leaf terminal {
         description "Terminal user is logged in to";
         type string {
           junos:posix-pattern "[a-z][0-9a-z]";
           junos:pattern-message "Must start with a letter followed by alphanumeric character";
         }
       }
     }
     output {
       container logout-user {
         uses logout-user-block;
       }
     }
   }
   rpc request-json-configuration-conversion {
     description "Convert the given JSON configuration file as per Junos";
     junos:command "request system convert-json-configuration";
     input {
       leaf filename {
         description "Path to the input JSON configuration file";
         junos:cli-feature "nokeyword";
         type jt:filename;
         mandatory true;
       }
       leaf output-filename {
         description "Path to the output file";
         type string {
           junos:posix-pattern "![/ %]";
           junos:pattern-message "Must not contain \'/\', % or a space";
         }
         mandatory true;
       }
       leaf origin-schema {
         description "Specify the Yang schema origin";
         default "juniper";
         type string;
       }
     }
     output {
       choice output_c {
         case output-tag {
           leaf output {
             type string;
           }
         }
         case multichassis-tag {
           anyxml multi-routing-engine-results;
         }
       }
     }
   }
   rpc reload-event-scripts {
     description "Reload all existing event-scripts";
     junos:command "request system scripts event-scripts reload";
   }
   rpc request-scripts-package-add {
     description "Add or upgrade jais package";
     junos:command "request system scripts add";
     input {
       leaf no-copy {
         description "Don't save copy of jais package file";
         type empty;
       }
       leaf unlink {
         description "Remove the package after successful installation";
         type empty;
       }
       leaf package-name {
         description "URL or pathname of package";
         junos:cli-feature "nokeyword";
         type jt:filename;
         mandatory true;
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case master {
           leaf master {
             description "Run command on master";
             type empty;
           }
         }
         case backup {
           leaf backup {
             description "Run command on backup";
             type empty;
           }
         }
       }
     }
     output {
       choice output_c {
         case output-tag {
           leaf output {
             type string;
           }
         }
         case multichassis-tag {
           anyxml multi-routing-engine-results;
         }
       }
     }
   }
   rpc request-scripts-package-delete {
     description "Remove jais package";
     junos:command "request system scripts delete";
     input {
       uses command-forwarding;
     }
     output {
       choice output_c {
         case output-tag {
           leaf output {
             type string;
           }
         }
         case multichassis-tag {
           anyxml multi-routing-engine-results;
         }
       }
     }
   }
   rpc request-scripts-package-rollback {
     description "Attempt to roll back to last jais package";
     junos:command "request system scripts rollback";
     input {
       uses command-forwarding;
     }
     output {
       choice output_c {
         case output-tag {
           leaf output {
             type string;
           }
         }
         case multichassis-tag {
           anyxml multi-routing-engine-results;
         }
       }
     }
   }
   rpc request-script-refresh-from {
     description "Refresh script from a given base URL";
     junos:command "request system scripts refresh-from";
     input {
       leaf type {
         junos:cli-feature "nokeyword";
         type enumeration {
           enum "commit" {
             description "Refresh commit script from a given base URL";
           }
           enum "op" {
             description "Refresh op script from a given base URL";
           }
           enum "event" {
             description "Refresh event script from a given base URL";
           }
           enum "snmp" {
             description "Refresh snmp script from a given base URL";
           }
           enum "extension-service" {
             description "Refresh extension-services app from a given base URL";
           }
         }
         mandatory true;
       }
       leaf file {
         description "Local script file name";
         type string {
           junos:posix-pattern "!/";
           junos:pattern-message "File name cannot contain a \'/\'";
         }
         mandatory true;
       }
       leaf url {
         description "URL from where the content will be retrieved";
         type string;
         mandatory true;
       }
       leaf routing-instance {
         description "Specify the routing-instance name";
         type string;
       }
       leaf cert-file {
         description "Specify the ca certificate file name";
         type string;
       }
       leaf sync {
         description "Refresh script and synchronize with other RE";
         type empty;
       }
     }
     output {
       choice output_c {
         case output-tag {
           leaf output {
             type string;
           }
         }
         case multichassis-tag {
           anyxml multi-routing-engine-results;
         }
       }
     }
   }
   rpc request-scripts-synchronize {
     description "Push the scripts to other RE";
     junos:command "request system scripts synchronize";
     input {
       leaf type {
         junos:cli-feature "nokeyword";
         type enumeration {
           enum "commit" {
             description "Push commit script to other RE";
           }
           enum "op" {
             description "Push op script to other RE";
           }
           enum "event" {
             description "Push event script to other RE";
           }
           enum "snmp" {
             description "Push snmp script to other RE";
           }
           enum "jet" {
             description "Push jet app to other RE";
           }
           enum "lib" {
             description "Push lib script to other RE";
           }
           enum "all" {
             description "Push all the scripts to other RE";
           }
         }
         mandatory true;
       }
       leaf file {
         description "Local script file name";
         type string;
       }
       leaf newer-than {
         description "Push script to other RE if newer than this time (YYYY-MM-DD.HH:MM:SS)";
         type jt:time;
       }
     }
     output {
       choice output_c {
         case output-tag {
           leaf output {
             type string;
           }
         }
         case multichassis-tag {
           anyxml multi-routing-engine-results;
         }
       }
     }
   }
   rpc request-package-add {
     description "Add extension or upgrade package";
     junos:command "request system software add";
     input {
       leaf force {
         description "Force addition of package (ignore warnings)";
         type empty;
       }
       leaf host {
         description "Force host is to do an in-service application in-service kexec warm restart";
         type empty;
       }
       leaf reboot {
         description "Reboot system after adding package";
         type empty;
       }
       choice firmware-option {
         case update-firmware {
           leaf update-firmware {
             description "Synchronize device to firmware versions in the package";
             type empty;
           }
         }
       }
       leaf force-host {
         description "Force addition of host os package (ignore version check)";
         type empty;
       }
       leaf on-primary {
         description "Install image on primary partition while booted on secondary partition";
         type empty;
       }
       leaf no-auto-reboot {
         description "Do not reboot system automatically after adding package";
         type empty;
       }
       leaf no-copy {
         description "Don't save copies of package files";
         type empty;
       }
       leaf dualroot {
         description "Install Dual-Root image for Zeroization";
         type empty;
       }
       choice validate_choice {
         case no-validate {
           leaf no-validate {
             description "Don't check compatibility with current configuration";
             type empty;
           }
         }
         case validate {
           leaf validate {
             description "Check compatibility with current configuration";
             type empty;
           }
         }
         case validate-on-host {
           leaf validate-on-host {
             description "Remote host or user@host for configuration validation";
             type string;
           }
         }
         case validate-on-routing-engine {
           leaf validate-on-routing-engine {
             description "Routing engine for configuration validation";
             type string;
           }
         }
       }
       leaf partition {
         description "Format and re-partition the media before installation";
         status deprecated;
         type empty;
       }
       choice re-choice {
         case re0 {
           leaf re0 {
             description "Install package on RE0";
             type empty;
           }
         }
         case re1 {
           leaf re1 {
             description "Install package on RE1";
             type empty;
           }
         }
         case both-routing-engines {
           leaf both-routing-engines {
             description "Simultaneous upgrade on both the RE's";
             type empty;
           }
         }
       }
       choice chassis {
         case scc {
           leaf scc {
             description "Install package on SCC";
             status deprecated;
             type empty;
           }
         }
         case lcc {
           leaf lcc {
             description "Install package on an LCC";
             status deprecated;
             type union {
               type string {
                 pattern "<.*>|$.*";
               }
               type uint32;
             }
           }
         }
         case sfc {
           leaf sfc {
             description "Install package on SFC";
             status deprecated;
             type empty;
           }
         }
         case member {
           leaf member {
             description "Install package on member";
             status deprecated;
             type union {
               type string {
                 pattern "<.*>|$.*";
               }
               type uint32;
             }
           }
         }
         case dont-forward {
           leaf dont-forward {
             type empty;
           }
         }
         case service-node {
           leaf service-node {
             description "Install package on Service Node";
             status deprecated;
             type union {
               type string {
                 pattern "<.*>|$.*";
               }
               type uint32 {
                 range "0 .. 1";
               }
             }
           }
         }
         case upgrade-group {
           leaf upgrade-group {
             description "Satellite upgrade group name";
             status deprecated;
             type string;
           }
         }
         case satellite {
           leaf satellite {
             description "FPC slot of satellite system";
             status deprecated;
             type union {
               type int32;
               type string {
                 pattern "<.*>|$.*";
               }
             }
           }
         }
         case device-alias {
           leaf device-alias {
             description "Device alias of satellite system";
             status deprecated;
             type string;
           }
         }
       }
       leaf issu-internal {
         description "Internally executed by mgd, to allow software adds during issu";
         type empty;
       }
       leaf routing-instance {
         description "Specify the routing-instance name";
         type string;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
         case version {
           leaf version {
             description "Version of satellite package";
             status deprecated;
             type string;
           }
         }
       }
       leaf virtual-machine-package {
         description "Add virtual-machine package";
         type empty;
       }
     }
     output {
       choice output_c {
         case output-tag {
           leaf output {
             type string;
           }
         }
         case multichassis-tag {
           anyxml multi-routing-engine-results;
         }
       }
     }
   }
   rpc request-package-latest-status {
     description "Status of package installation";
     junos:command "request system software status";
     output {
       container package-status {
         uses package-status-block;
       }
     }
   }
   rpc abort-in-service-upgrade {
     description "Abort in-service software upgrade";
     junos:command "request system software abort in-service-upgrade";
     output {
       choice output_c {
         case output-tag {
           leaf output {
             type string;
           }
         }
         case multichassis-tag {
           anyxml multi-routing-engine-results;
         }
       }
     }
   }
   rpc request-package-in-service-upgrade {
     description "In-service software upgrade";
     junos:command "request system software in-service-upgrade";
     input {
       leaf reboot {
         description "Reboot system after adding package";
         type empty;
       }
       leaf handle-incompatible-config {
         description "Automatically handle incompatible configurations";
         type empty;
       }
       choice package-options {
         case set {
           leaf-list set {
             ordered-by user;
             description "List of URLs or pathnames corresponding to packages for ISSU";
             type jt:filename;
           }
         }
         case package-name {
           leaf package-name {
             description "URL or pathname of package";
             junos:cli-feature "nokeyword";
             type jt:filename;
           }
         }
       }
       leaf no-old-master-upgrade {
         description "Don't upgrade the old master after switchover";
         type empty;
       }
       leaf verbose {
         description "Enable detailed output";
         type empty;
       }
       leaf no-copy {
         description "Don't save copies of package files";
         type empty;
       }
       leaf unlink {
         description "Remove the package after successful installation";
         type empty;
       }
       leaf no-sync {
         description "No state or session sync from master to backup";
         type empty;
       }
       leaf no-validate {
         description "Don't check compatibility with current configuration";
         type empty;
       }
       leaf no-tcp-syn-check {
         description "Disable TCP SYN check on secondary node, Custom time in seconds (0..14400, 0 - default)";
         default "0";
         type union {
           type string {
             pattern "<.*>|$.*";
           }
           type uint32 {
             range "0 .. 14400";
           }
         }
       }
       choice issu_internal {
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-in-service-upgrade-status {
     description "In-Service software upgrade status";
     junos:command "request system software in-service-upgrade status";
     output {
       leaf issu-status {
         type string;
         description "Show issu status";
       }
     }
   }
   rpc request-in-service-upgrade-pause {
     description "In-Service software upgrade pause";
     junos:command "request system software in-service-upgrade pause";
     input {
       leaf before-issu-state-validate {
         description "Pause ISSU before ISSU_STATE_VALIDATE";
         type empty;
       }
       leaf before-issu-state-slave-re-prepare {
         description "Pause ISSU before ISSU_STATE_SLAVE_RE_PREPARE";
         type empty;
       }
       leaf after-issu-state-slave-re-prepare-done {
         description "Pause ISSU after ISSU_STATE_SLAVE_RE_PREPARE_DONE";
         type empty;
       }
       leaf after-issu-state-switchover-done {
         description "Pause ISSU after ISSU_STATE_SWITCHOVER_DONE";
         type empty;
       }
       leaf before-issu-state-old-master-upgrade {
         description "Pause ISSU before ISSU_STATE_OLD_MASTER_UPGRADE";
         type empty;
       }
     }
     output {
       leaf issu-pause {
         type string;
         description "Pause ISSU";
       }
     }
   }
   rpc request-in-service-upgrade-resume {
     description "In-Service software upgrade resume";
     junos:command "request system software in-service-upgrade resume";
     input {
       leaf before-issu-state-validate {
         description "Resume ISSU before ISSU_STATE_VALIDATE";
         type empty;
       }
       leaf before-issu-state-slave-re-prepare {
         description "Resume ISSU before ISSU_STATE_SLAVE_RE_PREPARE";
         type empty;
       }
       leaf after-issu-state-slave-re-prepare-done {
         description "Resume ISSU after ISSU_STATE_SLAVE_RE_PREPARE_DONE";
         type empty;
       }
       leaf after-issu-state-switchover-done {
         description "Resume ISSU after ISSU_STATE_SWITCHOVER_DONE";
         type empty;
       }
       leaf before-issu-state-old-master-upgrade {
         description "Resume ISSU before ISSU_STATE_OLD_MASTER_UPGRADE";
         type empty;
       }
       leaf all-states {
         description "Resume/Cancel the pause request for all the states";
         type empty;
       }
     }
     output {
       leaf issu-resume {
         type string;
         description "Resume ISSU";
       }
     }
   }
   rpc request-package-nonstop-upgrade {
     description "Nonstop software upgrade";
     junos:command "request system software nonstop-upgrade";
     input {
       choice firmware-option {
         case update-firmware {
           leaf update-firmware {
             description "Synchronize device to firmware versions in the package";
             type empty;
           }
         }
       }
       leaf force-host {
         description "Force addition of host os package (ignore version check)";
         type empty;
       }
       leaf no-auto-recovery {
         description "Will not recover in case of NSSU failure";
         type empty;
       }
       leaf reboot {
         description "Reboot system after adding package";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf no-old-master-upgrade {
         description "Don't upgrade the old master after switchover";
         type empty;
       }
       leaf no-copy {
         description "Don't save copies of package files";
         status deprecated;
         type empty;
       }
       leaf unlink {
         description "Remove the package after successful installation";
         status deprecated;
         type empty;
       }
       leaf no-validate {
         description "Don't check compatibility with current configuration";
         type empty;
       }
     }
     output {
       choice output_c {
         case output-tag {
           leaf output {
             type string;
           }
         }
         case multichassis-tag {
           anyxml multi-routing-engine-results;
         }
       }
     }
   }
   rpc request-package-delete {
     description "Remove extension or upgrade package";
     junos:command "request system software delete";
     input {
       leaf archived {
         description "Removing of all archived software versions except current and rollback";
         type empty;
       }
       leaf force {
         description "Force removal of package (ignore warnings)";
         type empty;
       }
       leaf virtual-machine-package {
         description "Remove virtual-machine package";
         type empty;
       }
       choice package-options {
         case set {
           leaf-list set {
             ordered-by user;
             description "List of package name";
             type string;
           }
         }
         case package-name {
           leaf package-name {
             description "Name of package";
             junos:cli-feature "nokeyword";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
       choice re-choice {
         case re0 {
           leaf re0 {
             description "Delete package on RE0";
             type empty;
           }
         }
         case re1 {
           leaf re1 {
             description "Delete package on RE1";
             type empty;
           }
         }
       }
       choice chassis {
         case scc {
           leaf scc {
             description "Delete package on SCC";
             type empty;
           }
         }
         case lcc {
           leaf lcc {
             description "Delete package on an LCC";
             type union {
               type string {
                 pattern "<.*>|$.*";
               }
               type uint32 {
                 range "0 .. 3";
               }
             }
           }
         }
         case sfc {
           leaf sfc {
             description "Delete package on SFC";
             type empty;
           }
         }
         case member {
           leaf member {
             description "Delete package on VC Member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-package-rollback {
     description "Attempt to roll back to previous set of packages";
     junos:command "request system software rollback";
     input {
       uses command-forwarding;
       leaf reboot {
         description "Reboot system after rollback";
         type empty;
       }
       choice satellite-arg {
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
     }
     output {
       choice output_c {
         case output-tag {
           leaf output {
             type string;
           }
         }
         case multichassis-tag {
           anyxml multi-routing-engine-results;
         }
       }
     }
   }
   rpc request-package-validate {
     description "Verify package compatibility with current configuration";
     junos:command "request system software validate";
     input {
       leaf-list upgrade-with-config {
         ordered-by user;
         description "Additional configs ('text/xml' format) to be validated";
         type jt:filename;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       choice chassis {
         case scc {
           leaf scc {
             description "Validate package on SCC";
             type empty;
           }
         }
         case lcc {
           leaf lcc {
             description "Validate package on an LCC";
             type union {
               type string {
                 pattern "<.*>|$.*";
               }
               type uint32;
             }
           }
         }
         case sfc {
           leaf sfc {
             description "Validate package on SFC";
             type empty;
           }
         }
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc check-in-service-upgrade {
     description "Check in-service software upgrade";
     junos:command "request system software validate in-service-upgrade";
     input {
       choice package-options {
         case set {
           leaf-list set {
             ordered-by user;
             description "List of URLs or pathnames corresponding to packages for ISSU";
             type jt:filename;
           }
         }
         case package-name {
           leaf package-name {
             description "URL or pathname of package";
             junos:cli-feature "nokeyword";
             type jt:filename;
           }
         }
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-package-delete-backup {
     description "Delete old system software packages";
     status deprecated;
     junos:command "request system software delete-backup";
     output {
       choice output_c {
         case output-tag {
           leaf output {
             type string;
           }
         }
         case multichassis-tag {
           anyxml multi-routing-engine-results;
         }
       }
     }
   }
   rpc request-license-add {
     description "Add license keys from file, local or from server";
     junos:command "request system license add";
     input {
       leaf filename {
         description "Filename (URL, local, remote, or floppy)";
         junos:cli-feature "nokeyword";
         type string;
       }
       leaf key-data {
         description "License key data";
         type string;
       }
     }
     output {
       container add-license-results {
         uses add-license-results-block;
       }
     }
   }
   rpc request-license-delete {
     description "Delete license keys";
     junos:command "request system license delete";
     input {
       choice delete-choice {
         case all {
           leaf all {
             description "Delete all license keys";
             type empty;
           }
         }
         case license-identifier {
           leaf license-identifier {
             description "Identifier of installed license key";
             junos:cli-feature "nokeyword";
             type string;
           }
         }
         case license-identifier-list {
           leaf-list license-identifier-list {
             ordered-by user;
             description "Identifier of installed license key";
             type string;
           }
         }
       }
     }
     output {
       choice output_c {
         case output-tag {
           leaf output {
             type string;
           }
         }
         case multichassis-tag {
           anyxml multi-routing-engine-results;
         }
       }
     }
   }
   rpc request-license-save {
     description "Save license keys to file, local or to server";
     junos:command "request system license save";
     input {
       leaf filename {
         description "Filename (URL, local, remote, or floppy)";
         junos:cli-feature "nokeyword";
         type string;
         mandatory true;
       }
     }
     output {
       choice output_c {
         case output-tag {
           leaf output {
             type string;
           }
         }
         case multichassis-tag {
           anyxml multi-routing-engine-results;
         }
       }
     }
   }
   rpc request-license-update {
     description "Start autoupdate license keys from LMS servers";
     junos:command "request system license update";
     input {
       leaf trial {
         description "Start autoupdate trial license keys from LMS servers";
         status deprecated;
         type empty;
       }
     }
     output {
       container inform {
         uses inform-block;
       }
     }
   }
   rpc license-revoke-licenses {
     description "Revoke licenses in the Authorization key";
     status deprecated;
     junos:command "request system license revoke-licenses";
     input {
       leaf filename {
         description "Filename (URL, local, remote, or floppy)";
         junos:cli-feature "nokeyword";
         type string;
         mandatory true;
       }
     }
     output {
       choice output_c {
         case output-tag {
           leaf output {
             type string;
           }
         }
         case multichassis-tag {
           anyxml multi-routing-engine-results;
         }
       }
     }
   }
   rpc enable-unified-services-chassis-mode {
     description "Enable unified services chassis mode";
     junos:command "request system enable unified-services";
     output {
       choice output_c {
         case output-tag {
           leaf output {
             type string;
           }
         }
         case multichassis-tag {
           anyxml multi-routing-engine-results;
         }
       }
     }
   }
   rpc disable-unified-services-chassis-mode {
     description "Disable unified services chassis mode";
     junos:command "request system disable unified-services";
     output {
       choice output_c {
         case output-tag {
           leaf output {
             type string;
           }
         }
         case multichassis-tag {
           anyxml multi-routing-engine-results;
         }
       }
     }
   }
   rpc fips-selftest {
     description "Execute FIPS known answer tests (KATs)";
     junos:command "request system fips self-test";
     output {
       choice output_c {
         case output-tag {
           leaf output {
             type string;
           }
         }
         case multichassis-tag {
           anyxml multi-routing-engine-results;
         }
       }
     }
   }
   rpc request-system-erase {
     description "Secure erase SATA drives";
     junos:command "request system erase";
   }
   rpc request-personality-file-generate {
     description "Generate the personality-file tarball for the device";
     junos:command "request system personality-file generate";
     input {
       leaf personality-file-create {
         description "Url containing the remote server alongwith the name of the tarball";
         type string;
         mandatory true;
       }
     }
     output {
       choice output_c {
         case output-tag {
           leaf output {
             type string;
           }
         }
         case multichassis-tag {
           anyxml multi-routing-engine-results;
         }
       }
     }
   }
   rpc request-personality-file-retrieve {
     description "Retrieve the personality-file tarball of the device";
     junos:command "request system personality-file retrieve";
     input {
       leaf personality-file-retrieve {
         description "Url containing the remote server alongwith the name of the tarball";
         type string;
         mandatory true;
       }
       leaf retrieve-location {
         description "Path on the local device where the personality-file will be retrieved";
         type string;
         mandatory true;
       }
     }
     output {
       choice output_c {
         case output-tag {
           leaf output {
             type string;
           }
         }
         case multichassis-tag {
           anyxml multi-routing-engine-results;
         }
       }
     }
   }
   rpc transfer-control {
     description "Control transfers of core and log files";
     junos:command "request system diagnostics transfer-control";
     input {
       leaf operation {
         description "Transfer control operation";
         type enumeration {
           enum "abort" {
             description "Abort a transfer";
           }
           enum "pause" {
             description "Pause a transfer";
           }
           enum "restart" {
             description "Restart a transfer";
           }
         }
         mandatory true;
       }
       choice arg-type {
         case component {
           leaf component {
             description "Name of the component (uuid or serial number or all)";
             type string;
           }
         }
         case transfer-id {
           leaf transfer-id {
             description "Transfer identifier";
             type union {
               type int32;
               type string {
                 pattern "<.*>|$.*";
               }
             }
           }
         }
       }
     }
     output {
       container transfer-control-diagnostics {
         uses transfer-control-diagnostics-block;
       }
     }
   }
   rpc request-log {
     description "Create an archive of all system logs";
     junos:command "request system diagnostics log-archive";
     input {
       leaf component {
         description "Name of the component (uuid or serial number or all)";
         type string;
       }
     }
     output {
       container system-logfiles {
         uses system-logfiles-block;
       }
     }
   }
   rpc request-system-storage-cleanup {
     description "Clean up temporary files and rotate logs";
     junos:command "request system storage cleanup";
     input {
       uses command-forwarding;
       leaf subsystem {
         type string;
       }
       leaf dry-run {
         description "Only list the cleanup candidates, do not remove them";
         type empty;
       }
       leaf no-confirm {
         description "Do not ask for confirmation";
         type empty;
       }
     }
     output {
       container system-storage-cleanup-information {
         uses system-storage-cleanup-information-block;
       }
     }
   }
   rpc remove-qfabric-repository-contents {
     description "Remove contents from debug repositories of qfabric";
     junos:command "request system storage cleanup qfabric";
     input {
       leaf staging-area {
         description "Remove contents of staging area";
         type empty;
       }
       leaf repository {
         description "Specify type of repository for display";
         default "core";
         type enumeration {
           enum "core" {
             description "Remove 'core' repository";
           }
           enum "log" {
             description "Remove 'log' repository";
           }
         }
       }
       leaf name-tag {
         description "Remove all debug file(s) matching name-tag";
         type string;
       }
       leaf prune {
         description "Prune specified repository";
         type empty;
       }
       leaf dry-run {
         description "Only list cleanup candidates, donot remove them";
         type empty;
       }
       leaf component {
         description "Name of the component (uuid or serial number or all)";
         type string;
         mandatory true;
       }
     }
     output {
       container system-storage-cleanup-information {
         uses system-storage-cleanup-information-block;
       }
     }
   }
   rpc request-system-storage-cleanup-satellite {
     description "Clean up temporary and core files on satellite device";
     junos:command "request system storage cleanup satellite";
     input {
       leaf fpc-slot {
         description "Satellite slot number";
         junos:cli-feature "nokeyword";
         type union {
           type string {
             pattern "<.*>|$.*";
           }
           type uint32 {
             range "65 .. 254";
           }
         }
       }
       leaf device-alias {
         description "Device alias";
         type string;
       }
       leaf dry-run {
         description "Only list the cleanup candidates, do not remove them";
         type empty;
       }
     }
     output {
       choice output_c {
         case output-tag {
           leaf output {
             type string;
           }
         }
         case multichassis-tag {
           anyxml multi-routing-engine-results;
         }
       }
     }
   }
   rpc request-system-storage-expand-user {
     description "Manage size of user disk";
     junos:command "request system storage user-disk";
     input {
       leaf operation {
         description "Expand user disk or revert to default";
         junos:cli-feature "nokeyword";
         type enumeration {
           enum "expand" {
             description "Expand user disk to maximum available size";
           }
           enum "restore" {
             description "Restore user disk to default setting";
           }
         }
         mandatory true;
       }
     }
     output {
       choice output_c {
         case output-tag {
           leaf output {
             type string;
           }
         }
         case multichassis-tag {
           anyxml multi-routing-engine-results;
         }
       }
     }
   }
   rpc request-boot-media {
     description "Setup permanent boot media for subsequent reboots";
     junos:command "request system boot-media";
     input {
       leaf media {
         description "Media to be setup as boot device";
         junos:cli-feature "nokeyword";
         type enumeration {
           enum "primary" {
             description "Boot from primary Junos partition";
           }
           enum "alternate" {
             description "Boot from alternate Junos partition";
           }
           enum "external" {
             description "Boot from external USB device";
           }
         }
         mandatory true;
       }
     }
     output {
       choice output_c {
         case output-tag {
           leaf output {
             type string;
           }
         }
         case multichassis-tag {
           anyxml multi-routing-engine-results;
         }
       }
     }
   }
   rpc request-boot-console {
     description "Switch boot-console port";
     junos:command "request system boot-console";
     input {
       uses command-forwarding;
       leaf port {
         description "Choice of port";
         junos:cli-feature "nokeyword";
         type enumeration {
           enum "console" {
             description "Set Console port as boot console";
           }
           enum "auxiliary" {
             description "Set Auxiliary port as boot console";
           }
         }
         mandatory true;
       }
     }
     output {
       choice output_c {
         case output-tag {
           leaf output {
             type string;
           }
         }
         case multichassis-tag {
           anyxml multi-routing-engine-results;
         }
       }
     }
   }
   rpc request-reboot {
     description "Reboot the system";
     junos:command "request system reboot";
     input {
       uses command-forwarding;
       leaf fast-boot {
         description "Enable fast reboot";
         status deprecated;
         type empty;
       }
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       container request-reboot-results {
         uses request-reboot-results-block;
       }
     }
   }
   rpc request-reboot-in-service {
     description "Reboot with minimal traffic disruption";
     junos:command "request system reboot in-service";
     output {
       choice output_c {
         case output-tag {
           leaf output {
             type string;
           }
         }
         case multichassis-tag {
           anyxml multi-routing-engine-results;
         }
       }
     }
   }
   rpc request-system-logs-copy {
     description "Copy the logs from Host/FPC to RE";
     junos:command "request system logs";
     input {
       leaf from {
         description "From argument";
         type enumeration {
           enum "host" {
             description "Fetch all the logs from the host";
           }
           enum "fpc" {
             description "Fetch all the logs from a given FPC slot";
           }
           enum "all" {
             description "Fetch all the logs from the host and the FPC's";
           }
         }
         mandatory true;
       }
       leaf slot {
         description "From fpc slot number for U8/16";
         junos:cli-feature "nokeyword";
         type union {
           type string {
             pattern "<.*>|$.*";
           }
           type uint32;
         }
       }
     }
     output {
       choice output_c {
         case output-tag {
           leaf output {
             type string;
           }
         }
         case multichassis-tag {
           anyxml multi-routing-engine-results;
         }
       }
     }
   }
   rpc request-halt {
     description "Halt the system";
     junos:command "request system halt";
     input {
       uses command-forwarding;
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
         case at {
           leaf at {
             description "Time at which to perform the operation in hh::mm 24 hrs format";
             default "now";
             type string;
           }
         }
         case in {
           leaf in {
             description "Number of minutes to delay before operation";
             default "now";
             type string;
           }
         }
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-power-off {
     description "Power off the software on RE";
     junos:command "request system power-off";
     input {
       uses command-forwarding;
       leaf media {
         junos:cli-feature "nokeyword";
         type enumeration {
           enum "oam" {
             description "Boot off OAM volume";
           }
           enum "junos" {
             description "Boot off Junos volume";
           }
           enum "network" {
             description "Network boot via PXE";
           }
           enum "usb" {
             description "Boot off USB device";
           }
         }
       }
       choice time-arg-choice {
         case at {
           leaf at {
             description "Time at which to perform the operation in hh::mm 24 hrs format";
             default "now";
             type string;
           }
         }
         case in {
           leaf in {
             description "Number of minutes to delay before operation";
             default "now";
             type string;
           }
         }
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-process-terminate {
     description "Terminate the process";
     junos:command "request system process terminate";
     input {
       leaf subsystem {
         type string;
       }
       leaf process-id {
         description "Process ID";
         junos:cli-feature "nokeyword";
         type union {
           type string {
             pattern "<.*>|$.*";
           }
           type uint32 {
             range "1 .. 99999";
           }
         }
         mandatory true;
       }
     }
     output {
       choice output_c {
         case output-tag {
           leaf output {
             type string;
           }
         }
         case multichassis-tag {
           anyxml multi-routing-engine-results;
         }
       }
     }
   }
   rpc request-jdm-system-zeroize {
     description "Erase all data, including configuration and log files";
     junos:command "request system zeroize";
     input {
       leaf media {
         description "Overwrite media";
         type empty;
       }
       leaf ztp-option {
         description "Zeroize with ztp-mode options";
         type enumeration {
           enum "secure-enable" {
             description "Secure Enable";
           }
           enum "secure-disable" {
             description "Secure Disable";
           }
         }
       }
       leaf local {
         description "Zeroize just this Routing Engine";
         type empty;
       }
       leaf to-fips {
         description "Zeroize and switch device to FIPS mode";
         type empty;
       }
     }
     output {
       choice output_c {
         case output-tag {
           leaf output {
             type string;
           }
         }
         case multichassis-tag {
           anyxml multi-routing-engine-results;
         }
       }
     }
   }
   rpc request-system-zeroize-vc {
     description "Virtual-chassis zeroize options";
     junos:command "request system zeroize virtual-chassis";
     input {
       uses command-forwarding;
       leaf media {
         description "Overwrite media";
         type empty;
       }
     }
     output {
       leaf system-zeroize-status {
         type string;
         description "Status of zeroize operation";
       }
     }
   }
   rpc request-snapshot {
     description "Create a normal Junos or a recovery snapshot";
     junos:command "request system snapshot";
     input {
       uses command-forwarding;
       leaf snapshot-name {
         description "Snapshot name";
         type string;
       }
       leaf configuration {
         junos:cli-feature "nokeyword";
         default "configuration";
         type enumeration {
           enum "configuration" {
             description "Store device configuration in snapshot";
           }
           enum "no-configuration" {
             description "Do not store device configuration in snapshot";
           }
         }
       }
       leaf force {
         description "Force snapshot operation";
         type empty;
       }
       leaf recovery {
         description "Create a recovery snapshot";
         type empty;
       }
       leaf delete {
         description "Delete an existing snapshot";
         type string;
       }
       leaf load {
         description "Load a given snapshot and activate it upon reboot";
         type string;
       }
       leaf partition {
         description "Partition the media";
         type empty;
       }
       leaf as-primary {
         description "Setup snapshot to be used in the primary boot device";
         type empty;
       }
       leaf swap-size {
         description "Size of the swap partition";
         type string;
       }
       leaf config-size {
         description "Size of the config partition";
         type string;
       }
       leaf root-size {
         description "Size of the root partition";
         type string;
       }
       leaf data-size {
         description "Size of the data partition";
         type string;
       }
       leaf slice {
         description "Write snapshot to specified partition";
         status deprecated;
         type enumeration {
           enum "alternate" {
             description "Write snapshot to alternate partition";
             status deprecated;
           }
         }
       }
       leaf media {
         description "Media to snapshot to";
         default "compact-flash";
         type enumeration {
           enum "removable-compact-flash" {
             description "Write snapshot to removable compact flash";
           }
           enum "compact-flash" {
             description "Write snapshot to compact flash";
           }
           enum "usb" {
             description "Write snapshot to device connected to USB port";
           }
           enum "usb0" {
             description "Write snapshot to device connected to USB0 port";
           }
           enum "usb1" {
             description "Write snapshot to device connected to USB1 port";
           }
           enum "hard-disk" {
             description "Write snapshot to hard disk";
           }
           enum "internal" {
             description "Write snapshot to internal flash";
           }
           enum "external" {
             description "Write snapshot to external storage device";
           }
         }
       }
     }
     output {
       container snapshot-information {
         uses snapshot-information-block;
       }
     }
   }
   rpc request-system-firmware-reload-fpc {
     description "Reload FPC ROM monitor";
     junos:command "request system firmware reload fpc";
     input {
       leaf slot {
         description "FPC slot number";
         type union {
           type string {
             pattern "<.*>|$.*";
           }
           type uint32;
         }
         mandatory true;
       }
       choice which-arg {
         case wanio-fpga {
           leaf wanio-fpga {
             description "Reload wanio-fpga firmware";
             type empty;
           }
         }
         case i2cs-fpga {
           leaf i2cs-fpga {
             description "Reload i2cs-fpga firmware";
             type empty;
           }
         }
         case boot-cpld {
           leaf boot-cpld {
             description "Reload boot-cpld firmware";
             type empty;
           }
         }
       }
     }
     output {
       container system-firmware-information {
         uses system-firmware-information-block;
       }
     }
   }
   rpc request-system-firmware-reload-sib {
     description "Reload SIB firmware";
     junos:command "request system firmware reload sib";
     input {
       leaf slot {
         description "SIB slot number";
         type union {
           type string {
             pattern "<.*>|$.*";
           }
           type uint32;
         }
         mandatory true;
       }
     }
     output {
       container system-firmware-information {
         uses system-firmware-information-block;
       }
     }
   }
   rpc request-system-firmware-upgrade-jnpr-optics-fw {
     description "Upgrade optics firmware";
     junos:command "request system firmware optics update";
     input {
       leaf part-number {
         description "Enter juniper or vendor optic part number";
         type string;
       }
       leaf fpc-slot {
         description "Slot number of FPC";
         type union {
           type string {
             pattern "<.*>|$.*";
           }
           type uint32;
         }
       }
       leaf pic-slot {
         description "PIC slot number";
         type union {
           type string {
             pattern "<.*>|$.*";
           }
           type uint32;
         }
       }
       leaf port {
         description "Enter Port number";
         type union {
           type string {
             pattern "<.*>|$.*";
           }
           type uint32;
         }
       }
       leaf firmware-path {
         description "Enter firmware path";
         type string;
       }
       leaf password {
         description "Password to unlock firmware download";
         type union {
           type string {
             pattern "<.*>|$.*";
           }
           type uint32 {
             range "0 .. 2147483647";
           }
         }
       }
     }
     output {
       choice output_c {
         case output-tag {
           leaf output {
             type string;
           }
         }
         case multichassis-tag {
           anyxml multi-routing-engine-results;
         }
       }
     }
   }
   rpc request-system-firmware-optics-switch {
     description "Firmware switch optics";
     junos:command "request system firmware optics switch";
     input {
       leaf fpc-slot {
         description "Slot number of FPC";
         type union {
           type string {
             pattern "<.*>|$.*";
           }
           type uint32;
         }
         mandatory true;
       }
       leaf pic-slot {
         description "Slot number of FPC";
         type union {
           type string {
             pattern "<.*>|$.*";
           }
           type uint32;
         }
         mandatory true;
       }
       leaf port {
         description "Slot number of FPC";
         type union {
           type string {
             pattern "<.*>|$.*";
           }
           type uint32;
         }
         mandatory true;
       }
       leaf password {
         description "Password to unlock firmware download";
         type union {
           type string {
             pattern "<.*>|$.*";
           }
           type uint32 {
             range "0 .. 2147483647";
           }
         }
       }
     }
     output {
       choice output_c {
         case output-tag {
           leaf output {
             type string;
           }
         }
         case multichassis-tag {
           anyxml multi-routing-engine-results;
         }
       }
     }
   }
   rpc request-jfw-cpld-upgrade {
     description "Upgrade CPLD firmware";
     junos:command "request system firmware upgrade jfirmware cpld";
     input {
       leaf cpld-type {
         description "CPLD type: RE, MAIN, FAN";
         type string;
       }
       leaf file {
         description "Jfirmware package file";
         type string;
       }
     }
     output {
       choice output_c {
         case output-tag {
           leaf output {
             type string;
           }
         }
         case multichassis-tag {
           anyxml multi-routing-engine-results;
         }
       }
     }
   }
   rpc request-jfw-cpld-mainboard-upgrade {
     description "Upgrade mainboard CPLD firmware";
     junos:command "request system firmware upgrade jfirmware cpld main";
     input {
       leaf file {
         description "Jfirmware package file";
         type string;
       }
     }
   }
   rpc request-jfw-main-board-upgrade-status {
     description "Show MAIN board upgrade status";
     junos:command "request system firmware upgrade jfirmware cpld main progress";
   }
   rpc request-jfw-cpld-fanboard-upgrade {
     description "Upgrade fanboard CPLD firmware";
     junos:command "request system firmware upgrade jfirmware cpld fan";
     input {
       uses command-forwarding;
       leaf file {
         description "Jfirmware package file";
         type string;
       }
     }
   }
   rpc request-jfw-cpld-fanboard-upgrade-status {
     description "Show fanboard CPLD upgrade status";
     junos:command "request system firmware upgrade jfirmware cpld fan progress";
     input {
       uses command-forwarding;
     }
   }
   rpc request-jfw-cpld-sys-upgrade {
     description "Upgrade Sys CPLD firmware";
     junos:command "request system firmware upgrade jfirmware cpld sys";
     input {
       uses command-forwarding;
       leaf file {
         description "Jfirmware package file";
         type string;
       }
     }
   }
   rpc request-jfw-sys-cpld-upgrade-status {
     description "Show Sys cpld upgrade status";
     junos:command "request system firmware upgrade jfirmware cpld sys progress";
     input {
       uses command-forwarding;
     }
   }
   rpc request-jfw-cpld-cpuboard-upgrade {
     description "Upgrade CPU board CPLD firmware";
     junos:command "request system firmware upgrade jfirmware cpld cpu";
     input {
       uses command-forwarding;
       leaf file {
         description "Jfirmware package file";
         type string;
       }
     }
   }
   rpc request-jfw-cpu-cpld-upgrade-status {
     description "Show CPU cpld upgrade status";
     junos:command "request system firmware upgrade jfirmware cpld cpu progress";
     input {
       uses command-forwarding;
     }
   }
   rpc request-jfw-cpld-port-upgrade {
     description "Upgrade port CPLD firmware";
     junos:command "request system firmware upgrade jfirmware cpld port-cpld";
     input {
       uses command-forwarding;
     }
   }
   rpc request-jfw-port-cpld-upgrade-status {
     description "Show port cpld upgrade status";
     junos:command "request system firmware upgrade jfirmware cpld port-cpld progress";
     input {
       uses command-forwarding;
     }
   }
   rpc request-jfw-mmc-upgrade {
     description "Upgrade MMC firmware";
     junos:command "request system firmware upgrade jfirmware mmc";
     input {
       uses command-forwarding;
     }
   }
   rpc request-jfw-mmc-upgrade-status {
     description "Show MMC upgrade status";
     junos:command "request system firmware upgrade jfirmware mmc progress";
     input {
       uses command-forwarding;
     }
   }
   rpc request-jfw-eusb-upgrade {
     description "Upgrade eusb firmware";
     junos:command "request system firmware upgrade jfirmware eusb";
   }
   rpc request-jfw-eusb-upgrade-status {
     description "Show eusb upgrade status";
     junos:command "request system firmware upgrade jfirmware eusb progress";
   }
   rpc request-jfw-uboot-upgrade {
     description "Upgrade uboot binary";
     junos:command "request system firmware upgrade jfirmware uboot";
     input {
       uses command-forwarding;
     }
   }
   rpc request-jfw-uboot-upgrade-status {
     description "Show uboot upgrade status";
     junos:command "request system firmware upgrade jfirmware uboot progress";
     input {
       uses command-forwarding;
     }
   }
   rpc request-jfw-nic-i350-upgrade {
     description "Upgrade Builtin i350 NIC firmware";
     junos:command "request system firmware upgrade jfirmware nic i350";
     input {
       leaf file {
         description "Jfirmware package file";
         type string;
       }
     }
     output {
       choice output_c {
         case output-tag {
           leaf output {
             type string;
           }
         }
         case multichassis-tag {
           anyxml multi-routing-engine-results;
         }
       }
     }
   }
   rpc request-jfirmware-nic-i210-upgrade {
     description "Upgrade Builtin i210 NIC firmware";
     junos:command "request system firmware upgrade jfirmware nic i210";
     input {
       leaf file {
         description "Jfirmware package file";
         type string;
       }
     }
     output {
       choice output_c {
         case output-tag {
           leaf output {
             type string;
           }
         }
         case multichassis-tag {
           anyxml multi-routing-engine-results;
         }
       }
     }
   }
   rpc request-jfw-nic-x552-upgrade {
     description "Upgrade Builtin x552 NIC firmware";
     junos:command "request system firmware upgrade jfirmware nic x552";
     input {
       leaf file {
         description "Jfirmware package file";
         type string;
       }
     }
   }
   rpc request-jfw-nic-x722-upgrade {
     description "Upgrade Builtin x722 NIC firmware";
     junos:command "request system firmware upgrade jfirmware nic x722";
     input {
       leaf file {
         description "Jfirmware package file";
         type string;
       }
     }
   }
   rpc request-jfw-nic-x722-upgrade-status {
     description "Show NIC upgrade status";
     junos:command "request system firmware upgrade jfirmware nic x722 progress";
   }
   rpc request-jfw-nic-x553-upgrade {
     description "Upgrade Builtin x553 NIC firmware";
     junos:command "request system firmware upgrade jfirmware nic x553";
     input {
       leaf file {
         description "Jfirmware package file";
         type string;
       }
     }
   }
   rpc request-jfw-nic-i82599-1-upgrade {
     description "Upgrade Builtin i82599_1 NIC firmware";
     junos:command "request system firmware upgrade jfirmware nic i82599-1";
     input {
       leaf file {
         description "Jfirmware package file";
         type string;
       }
     }
   }
   rpc request-jfw-nic-i82599-2-upgrade {
     description "Upgrade Builtin i82599_2 NIC firmware";
     junos:command "request system firmware upgrade jfirmware nic i82599-2";
     input {
       leaf file {
         description "Jfirmware package file";
         type string;
       }
     }
   }
   rpc request-jfw-em-i350-copper-upgrade {
     description "Upgrade Expansion Module i350 NIC Copper firmware";
     junos:command "request system firmware upgrade jfirmware em i350 copper";
     input {
       leaf file {
         description "Jfirmware package file";
         type string;
       }
     }
   }
   rpc request-jfw-em-i350-sfp-upgrade {
     description "Upgrade Expansion Module i350 NIC SFP firmware";
     junos:command "request system firmware upgrade jfirmware em i350 sfp";
     input {
       leaf file {
         description "Jfirmware package file";
         type string;
       }
     }
   }
   rpc request-jfw-bios-upgrade {
     description "Upgrade BIOS firmware";
     junos:command "request system firmware upgrade jfirmware bios";
     input {
       uses command-forwarding;
       leaf disk {
         description "1, 2";
         type string;
       }
       leaf file {
         description "Jfirmware package file";
         type string;
       }
     }
     output {
       choice output_c {
         case output-tag {
           leaf output {
             type string;
           }
         }
         case multichassis-tag {
           anyxml multi-routing-engine-results;
         }
       }
     }
   }
   rpc request-jfw-bios-upgrade-status {
     description "Show BIOS upgrade status";
     junos:command "request system firmware upgrade jfirmware bios progress";
     input {
       uses command-forwarding;
     }
   }
   rpc request-jfw-psu-upgrade {
     description "Upgrade psu firmware";
     junos:command "request system firmware upgrade jfirmware psu";
     input {
       leaf file {
         description "Jfirmware package file";
         type string;
       }
     }
     output {
       choice output_c {
         case output-tag {
           leaf output {
             type string;
           }
         }
         case multichassis-tag {
           anyxml multi-routing-engine-results;
         }
       }
     }
   }
   rpc request-jfw-psu-upgrade-status {
     description "Show PSU upgrade status";
     junos:command "request system firmware upgrade jfirmware psu progress";
   }
   rpc request-jfirmware-hv-psu-upgrade {
     description "Upgrade HV PSU firmware";
     junos:command "request system firmware upgrade jfirmware hv-psu";
     input {
       leaf file {
         description "Jfirmware package file";
         type string;
       }
     }
     output {
       choice output_c {
         case output-tag {
           leaf output {
             type string;
           }
         }
         case multichassis-tag {
           anyxml multi-routing-engine-results;
         }
       }
     }
   }
   rpc request-jfirmware-hv-psu-upgrade-status {
     description "Show HV PSU upgrade status";
     junos:command "request system firmware upgrade jfirmware hv-psu progress";
     output {
       choice output_c {
         case output-tag {
           leaf output {
             type string;
           }
         }
         case multichassis-tag {
           anyxml multi-routing-engine-results;
         }
       }
     }
   }
   rpc request-jfw-ssd-upgrade {
     description "Upgrade SSD firmware";
     junos:command "request system firmware upgrade jfirmware ssd";
     input {
       leaf disk {
         description "1, 2";
         type string;
       }
       leaf file {
         description "Jfirmware package file";
         type string;
       }
     }
     output {
       choice output_c {
         case output-tag {
           leaf output {
             type string;
           }
         }
         case multichassis-tag {
           anyxml multi-routing-engine-results;
         }
       }
     }
   }
   rpc get-jfw-tpm-upgrade {
     description "Upgrade TPM firmware";
     junos:command "request system firmware upgrade jfirmware tpm";
     output {
       choice output_c {
         case output-tag {
           leaf output {
             type string;
           }
         }
         case multichassis-tag {
           anyxml multi-routing-engine-results;
         }
       }
     }
   }
   rpc request-jfw-ltc-upgrade {
     description "Upgrade LTC firmware";
     junos:command "request system firmware upgrade jfirmware ltc";
     output {
       choice output_c {
         case output-tag {
           leaf output {
             type string;
           }
         }
         case multichassis-tag {
           anyxml multi-routing-engine-results;
         }
       }
     }
   }
   rpc request-jfw-poe-upgrade {
     description "Upgrade POE firmware";
     junos:command "request system firmware upgrade jfirmware poe";
     input {
       uses command-forwarding;
       leaf fpc-slot {
         description "FPC slot";
         type string;
         mandatory true;
       }
       leaf poe-firmware-type {
         description "POE_FIRMWARE_TYPE";
         junos:cli-feature "nokeyword";
         type enumeration {
           enum "poe-at-firmware" {
             description "IEEE 802.3at PoE Firmware Support";
           }
           enum "poe-bt-firmware" {
             description "IEEE 802.3bt PoE Firmware Support";
           }
         }
       }
     }
     output {
       choice output_c {
         case output-tag {
           leaf output {
             type string;
           }
         }
         case multichassis-tag {
           anyxml multi-routing-engine-results;
         }
       }
     }
   }
   rpc request-jfw-bcm-pcie-upgrade {
     description "Upgrade BCM PCIe firmware";
     junos:command "request system firmware upgrade jfirmware bcmpcie";
     input {
       leaf file {
         description "Jfirmware package file";
         type string;
       }
     }
     output {
       choice output_c {
         case output-tag {
           leaf output {
             type string;
           }
         }
         case multichassis-tag {
           anyxml multi-routing-engine-results;
         }
       }
     }
   }
   rpc request-jfirmware-pmic-upgrade {
     description "Upgrade PMIC firmware";
     junos:command "request system firmware upgrade jfirmware pmic";
     input {
       leaf file {
         description "Jfirmware package file";
         type string;
       }
     }
     output {
       choice output_c {
         case output-tag {
           leaf output {
             type string;
           }
         }
         case multichassis-tag {
           anyxml multi-routing-engine-results;
         }
       }
     }
   }
   rpc request-jfw-pmic-fpga-upgrade-status {
     description "Show PMIC Upgrade status";
     junos:command "request system firmware upgrade jfirmware pmic progress";
     output {
       choice output_c {
         case output-tag {
           leaf output {
             type string;
           }
         }
         case multichassis-tag {
           anyxml multi-routing-engine-results;
         }
       }
     }
   }
   rpc request-jfw-re-fpga-upgrade {
     description "Upgrade RE FPGA";
     junos:command "request system firmware upgrade jfirmware fpga re";
     input {
       uses command-forwarding;
       leaf file {
         description "Jfirmware package file";
         type string;
       }
     }
   }
   rpc request-jfw-re-fpga-upgrade-status {
     description "Show RE FPGA Upgrade status";
     junos:command "request system firmware upgrade jfirmware fpga re progress";
     input {
       uses command-forwarding;
     }
   }
   rpc request-jfw-tmc-fpga-upgrade {
     description "Upgrade Mainboard TMC FPGA";
     junos:command "request system firmware upgrade jfirmware fpga tmc";
     input {
       leaf file {
         description "Jfirmware package file";
         type string;
       }
     }
   }
   rpc request-jfw-tmc-fpga-upgrade-status {
     description "Show TMC Upgrade status";
     junos:command "request system firmware upgrade jfirmware fpga tmc progress";
   }
   rpc request-jfw-main-fpga-upgrade {
     description "Upgrade Mainboard FPGA";
     junos:command "request system firmware upgrade jfirmware fpga main-board";
     input {
       uses command-forwarding;
     }
   }
   rpc request-jfw-main-fpga-upgrade-status {
     description "Show main board Upgrade status";
     junos:command "request system firmware upgrade jfirmware fpga main-board progress";
     input {
       uses command-forwarding;
     }
   }
   rpc request-jfw-power-cpld-upgrade {
     description "Upgrade Power CPLD";
     junos:command "request system firmware upgrade jfirmware fpga powercpld";
     input {
       leaf file {
         description "Jfirmware package file";
         type string;
       }
     }
   }
   rpc request-jfw-powercpld-upgrade-status {
     description "Show Powercpld Upgrade status";
     junos:command "request system firmware upgrade jfirmware fpga powercpld progress";
   }
   rpc request-jfirmware-fanboard-fpga-upgrade {
     description "Upgrade Fanboard FPGA";
     junos:command "request system firmware upgrade jfirmware fpga fan";
     input {
       leaf file {
         description "Jfirmware package file";
         type string;
       }
     }
     output {
       choice output_c {
         case output-tag {
           leaf output {
             type string;
           }
         }
         case multichassis-tag {
           anyxml multi-routing-engine-results;
         }
       }
     }
   }
   rpc request-jfirmware-fanboard-fpga-upgrade-status {
     description "Show Fanboard FPGA Upgrade status";
     junos:command "request system firmware upgrade jfirmware fpga fan progress";
     output {
       choice output_c {
         case output-tag {
           leaf output {
             type string;
           }
         }
         case multichassis-tag {
           anyxml multi-routing-engine-results;
         }
       }
     }
   }
   rpc request-jfw-optics-sfp-upgrade {
     description "Upgrade Optics FPGA/CPLD";
     junos:command "request system firmware upgrade jfirmware fpga sfp";
     input {
       leaf file {
         description "Jfirmware package file";
         type string;
       }
     }
   }
   rpc request-jfw-optics-sfp-upgrade-status {
     description "Show SFP Upgrade status";
     junos:command "request system firmware upgrade jfirmware fpga sfp progress";
   }
   rpc request-jfw-optics-qsfp-upgrade {
     description "Upgrade Optics FPGA/CPLD";
     junos:command "request system firmware upgrade jfirmware fpga qsfp";
     input {
       leaf file {
         description "Jfirmware package file";
         type string;
       }
     }
   }
   rpc request-jfw-optics-qsfp-upgrade-status {
     description "Show QSFP Upgrade status";
     junos:command "request system firmware upgrade jfirmware fpga qsfp progress";
   }
   rpc request-jfw-bmc-upgrade {
     description "Upgrade BMC firmware";
     junos:command "request system firmware upgrade jfirmware bmc";
     input {
       leaf file {
         description "Jfirmware package file";
         type string;
       }
     }
     output {
       choice output_c {
         case output-tag {
           leaf output {
             type string;
           }
         }
         case multichassis-tag {
           anyxml multi-routing-engine-results;
         }
       }
     }
   }
   rpc request-jfw-bmc-upgrade-status {
     description "Show BMC Upgrade status";
     junos:command "request system firmware upgrade jfirmware bmc progress";
     output {
       choice output_c {
         case output-tag {
           leaf output {
             type string;
           }
         }
         case multichassis-tag {
           anyxml multi-routing-engine-results;
         }
       }
     }
   }
   rpc request-jfw-allfw-upgrade {
     description "Upgrade all firmwares applicable in Jfirmware package";
     junos:command "request system firmware upgrade jfirmware allfw";
     input {
       uses command-forwarding;
       leaf file {
         description "Jfirmware package file";
         type string;
       }
     }
     output {
       choice output_c {
         case output-tag {
           leaf output {
             type string;
           }
         }
         case multichassis-tag {
           anyxml multi-routing-engine-results;
         }
       }
     }
   }
   rpc request-jfw-allfw-upgrade-status {
     description "Show all firmware upgrade status";
     junos:command "request system firmware upgrade jfirmware allfw progress";
     input {
       uses command-forwarding;
     }
   }
   rpc request-scb-fpga-upgrade {
     description "Upgrade SCB FPGA ";
     junos:command "request system firmware upgrade fpga scb";
     input {
       leaf file {
         description "FPGA file name";
         type string;
       }
     }
   }
   rpc request-system-cb-fpga-upgrade {
     description "Upgrade Control Board Controller FPGA ";
     junos:command "request system firmware upgrade fpga cb";
   }
   rpc request-re-fpga-upgrade {
     description "Upgrade RE FPGA ";
     junos:command "request system firmware upgrade fpga re";
   }
   rpc request-fpd-fpga-upgrade {
     description "Upgrade Front Panel Display FPGA ";
     junos:command "request system firmware upgrade fpga fpd";
   }
   rpc request-ftc-fpga-upgrade {
     description "Upgrade Fan Tray Controller FPGA ";
     junos:command "request system firmware upgrade fpga ftc";
     input {
       leaf slot {
         description "FTC slot number";
         type union {
           type string {
             pattern "<.*>|$.*";
           }
           type uint32;
         }
       }
     }
   }
   rpc request-sib-fpga-upgrade {
     description "Upgrade Switching Interface Board FPGA";
     junos:command "request system firmware upgrade fpga sib";
     input {
       leaf slot {
         description "SIB slot number";
         type union {
           type string {
             pattern "<.*>|$.*";
           }
           type uint32;
         }
       }
     }
   }
   rpc request-fpc-fpga-upgrade {
     description "Upgrade Line Card FPGAs";
     junos:command "request system firmware upgrade fpga fpc";
     input {
       uses command-forwarding;
       leaf slot {
         description "FPC slot number";
         type union {
           type string {
             pattern "<.*>|$.*";
           }
           type uint32;
         }
       }
       leaf file {
         description "FPGA file name";
         type string;
       }
     }
   }
   rpc request-pem-firmware-upgrade {
     description "Upgrade CHASSIS PEM FW";
     junos:command "request system firmware upgrade pem";
     input {
       leaf slot {
         description "PEM slot number";
         type union {
           type string {
             pattern "<.*>|$.*";
           }
           type uint32;
         }
       }
       leaf mcu {
         description "MCU inside PEM";
         type enumeration {
           enum "primary" {
             description "Primary MCU";
           }
           enum "secondary" {
             description "Secondary MCU";
           }
         }
         mandatory true;
       }
     }
     output {
       container system-firmware-information {
         uses system-firmware-information-block;
       }
     }
   }
   rpc request-mic-firmware-upgrade {
     description "Upgrade MIC Firmware";
     junos:command "request system firmware upgrade mic";
     input {
       leaf mic-slot {
         description "MIC slot number";
         type union {
           type string {
             pattern "<.*>|$.*";
           }
           type uint32;
         }
       }
       leaf fpc-slot {
         description "FPC slot number";
         type union {
           type string {
             pattern "<.*>|$.*";
           }
           type uint32;
         }
       }
       leaf tag {
         description "MIC firmware tag";
         type union {
           type uint32;
           type string {
             pattern "<.*>|$.*";
           }
         }
       }
     }
     output {
       container system-firmware-information {
         uses system-firmware-information-block;
       }
     }
   }
   rpc request-fpc-eth-switch-upgrade {
     description "Upgrade Line Card ETH-SWITCH";
     junos:command "request system firmware upgrade eth-switch fpc";
     input {
       leaf slot {
         description "FPC slot number";
         type union {
           type string {
             pattern "<.*>|$.*";
           }
           type uint32;
         }
         mandatory true;
       }
     }
   }
   rpc request-ftc-firmware-upgrade {
     description "Upgrade FTC firmware";
     junos:command "request system firmware upgrade ftc";
     input {
       leaf slot {
         description "FTC slot number";
         type union {
           type string {
             pattern "<.*>|$.*";
           }
           type uint32;
         }
         mandatory true;
       }
     }
     output {
       container system-firmware-information {
         uses system-firmware-information-block;
       }
     }
   }
   rpc request-ftc-fpga-firmware-upgrade {
     description "Upgrade FTC FPGA firmware";
     junos:command "request system firmware upgrade fan";
     input {
       leaf slot {
         description "FAN slot number";
         type union {
           type string {
             pattern "<.*>|$.*";
           }
           type uint32;
         }
         mandatory true;
       }
     }
     output {
       container system-firmware-information {
         uses system-firmware-information-block;
       }
     }
   }
   rpc request-bitscpld-firmware-upgrade {
     description "Upgrade BITSCPLD programmable on SPMC Mezz board";
     junos:command "request system firmware upgrade re bitscpld";
     output {
       container system-firmware-information {
         uses system-firmware-information-block;
       }
     }
   }
   rpc request-cb-fpga-upgrade {
     description "Upgrade baseboard FPGA";
     junos:command "request system firmware upgrade cb";
     input {
       choice which-arg {
         case fpga {
           leaf fpga {
             description "Upgrade baseboard FPGA";
             type empty;
           }
         }
         case port-fpga {
           leaf port-fpga {
             description "Upgrade baseboard PORT FPGA";
             type empty;
           }
         }
         case port {
           leaf port {
             description "Upgrade baseboard port";
             type empty;
           }
         }
         case tic-fpga {
           leaf tic-fpga {
             description "Upgrade TIC FPGA";
             type empty;
           }
         }
         case optics {
           leaf optics {
             description "Upgrade Optics CPLD";
             type enumeration {
               enum "cpld0" {
                 description "Optics CPLD0";
               }
               enum "cpld1" {
                 description "Optics CPLD1";
               }
             }
           }
         }
         case fancpld {
           leaf fancpld {
             description "Upgrade fan board CPLD";
             type empty;
           }
         }
         case pciesw {
           leaf pciesw {
             description "Upgrade CB PCIe SW Firmware";
             type empty;
           }
         }
         case i2cs-fpga {
           leaf i2cs-fpga {
             description "Upgrade CB I2CS FPGA";
             type empty;
           }
         }
         case gnss {
           leaf gnss {
             description "Upgrade GNSS Firmware";
             type empty;
           }
         }
         case idtpll {
           leaf idtpll {
             description "Upgrade IDTPLL Firmware";
             type empty;
           }
         }
         case bits-fpga {
           leaf bits-fpga {
             description "Upgrade BITS FPGA firmware";
             type empty;
           }
         }
         case cg0 {
           leaf cg0 {
             description "Upgrade Clock Gen Firmware";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       container system-firmware-information {
         uses system-firmware-information-block;
       }
     }
   }
   rpc request-i2c-fpga-upgrade {
     description "I2C FPGA Upgrade";
     junos:command "request system firmware upgrade cb i2c";
   }
   rpc request-system-firmware-upgrade-sfb {
     description "Upgrade SFB firmware";
     junos:command "request system firmware upgrade sfb";
     input {
       leaf slot {
         description "SFB slot number";
         type union {
           type string {
             pattern "<.*>|$.*";
           }
           type uint32;
         }
         mandatory true;
       }
       leaf tag {
         description "Firmware tag number";
         type union {
           type string {
             pattern "<.*>|$.*";
           }
           type uint32 {
             range "0 .. 1";
           }
         }
         mandatory true;
       }
     }
     output {
       container system-firmware-information {
         uses system-firmware-information-block;
       }
     }
   }
   rpc request-pem-firmware-downgrade {
     description "Upgrade CHASSIS PEM FW";
     junos:command "request system firmware downgrade pem";
     input {
       leaf slot {
         description "PEM slot number";
         type union {
           type string {
             pattern "<.*>|$.*";
           }
           type uint32;
         }
       }
     }
     output {
       container system-firmware-information {
         uses system-firmware-information-block;
       }
     }
   }
   rpc request-bitscpld-firmware-downgrade {
     description "Upgrade BITSCPLD programmable on SPMC Mezz board";
     junos:command "request system firmware downgrade re bitscpld";
     output {
       container system-firmware-information {
         uses system-firmware-information-block;
       }
     }
   }
   rpc request-cb-fpga-downgrade {
     description "Upgrade baseboard FPGA";
     junos:command "request system firmware downgrade cb";
     input {
       choice which-arg {
         case fpga {
           leaf fpga {
             description "Upgrade baseboard FPGA";
             type empty;
           }
         }
         case port {
           leaf port {
             description "Upgrade baseboard port";
             type empty;
           }
         }
         case tic-fpga {
           leaf tic-fpga {
             description "Upgrade TIC FPGA";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       container system-firmware-information {
         uses system-firmware-information-block;
       }
     }
   }
   rpc request-i2c-fpga-downgrade {
     description "I2C FPGA Upgrade";
     junos:command "request system firmware downgrade cb i2c";
   }
   rpc request-system-firmware-downgrade-sfb {
     description "Downgrade SFB firmware";
     junos:command "request system firmware downgrade sfb";
     input {
       leaf slot {
         description "SFB slot number";
         type union {
           type string {
             pattern "<.*>|$.*";
           }
           type uint32;
         }
         mandatory true;
       }
       leaf tag {
         description "Firmware tag number";
         type union {
           type string {
             pattern "<.*>|$.*";
           }
           type uint32 {
             range "0 .. 1";
           }
         }
         mandatory true;
       }
     }
     output {
       container system-firmware-information {
         uses system-firmware-information-block;
       }
     }
   }
   rpc request-power-on-other-re {
     description "Power on the system";
     junos:command "request system power-on";
     input {
       uses command-forwarding;
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc request-system-debug-info {
     description "Collect debug information of the system";
     junos:command "request system debug-info";
     input {
       leaf mode {
         description "Debug Collector mode";
         type string;
       }
       leaf since {
         description "Log duration. Supported format: yyyy-mm-dd or #d (ex: 2d) or #h (ex: 5h)";
         type string;
       }
       leaf noninteractive {
         description "To skip any user interaction";
         type empty;
       }
       leaf outdir {
         description "Specify the output directory";
         type string;
       }
     }
     output {
       choice output_c {
         case output-tag {
           leaf output {
             type string;
           }
         }
         case multichassis-tag {
           anyxml multi-routing-engine-results;
         }
       }
     }
   }
   rpc renew-dhcp-client {
     description "Request DHCP client renew";
     junos:command "request system services dhcp renew";
     input {
       leaf interface-name {
         description "Interface name of DHCP client";
         junos:cli-feature "nokeyword";
         type string;
         mandatory true;
       }
     }
     output {
       choice output_c {
         case output-tag {
           leaf output {
             type string;
           }
         }
         case multichassis-tag {
           anyxml multi-routing-engine-results;
         }
       }
     }
   }
   rpc release-dhcp-client {
     description "Request DHCP client release";
     junos:command "request system services dhcp release";
     input {
       leaf interface-name {
         description "Interface name of DHCP client";
         junos:cli-feature "nokeyword";
         type string;
         mandatory true;
       }
     }
     output {
       choice output_c {
         case output-tag {
           leaf output {
             type string;
           }
         }
         case multichassis-tag {
           anyxml multi-routing-engine-results;
         }
       }
     }
   }
   rpc request-system-download-clear {
     description "Clear records of completed and aborted downloads";
     junos:command "request system download clear";
     output {
       container download-information {
         uses download-information-block;
       }
     }
   }
   rpc request-system-download-start {
     description "Start a new download";
     junos:command "request system download start";
     input {
       leaf url {
         description "URL of file";
         junos:cli-feature "nokeyword";
         type string;
         mandatory true;
       }
       leaf max-rate {
         description "Maximum bandwidth for the download";
         type string {
           junos:posix-pattern "^[1-9][0-9]{0,8}([kKmM])?$";
           junos:pattern-message "Up to 9 digits with optional k or m suffix";
         }
       }
       leaf save-as {
         description "Rename file when saving to local file system";
         type string;
       }
       leaf login {
         description "Login credentials (username:password)";
         type string;
       }
       leaf identity-file {
         description "Identity file for sftp pubic key authentication";
         type string;
       }
       leaf passphrase {
         description "Passphrase used to protect identity key pair";
         type string;
       }
       leaf delay {
         description "Delay the start of the download";
         units "hours";
         type union {
           type string {
             pattern "<.*>|$.*";
           }
           type int32 {
             range "1 .. 48";
           }
         }
       }
     }
     output {
       container download-information {
         uses download-information-block;
       }
     }
   }
   rpc request-system-download-pause {
     description "Pause an active download";
     junos:command "request system download pause";
     input {
       leaf download-id {
         description "ID of the download to be paused";
         junos:cli-feature "nokeyword";
         type union {
           type uint16;
           type string {
             pattern "<.*>|$.*";
           }
         }
         mandatory true;
       }
     }
     output {
       container download-information {
         uses download-information-block;
       }
     }
   }
   rpc request-system-download-resume {
     description "Resume a paused download";
     junos:command "request system download resume";
     input {
       leaf download-id {
         description "ID of the download to be resumed";
         junos:cli-feature "nokeyword";
         type union {
           type uint16;
           type string {
             pattern "<.*>|$.*";
           }
         }
         mandatory true;
       }
       leaf max-rate {
         description "Maximum bandwidth for the download";
         type string;
       }
     }
     output {
       container download-information {
         uses download-information-block;
       }
     }
   }
   rpc request-system-download-abort {
     description "Abort a download and delete the local file";
     junos:command "request system download abort";
     input {
       leaf download-id {
         description "ID of the download to be aborted";
         junos:cli-feature "nokeyword";
         type union {
           type uint16;
           type string {
             pattern "<.*>|$.*";
           }
         }
         mandatory true;
       }
     }
     output {
       container download-information {
         uses download-information-block;
       }
     }
   }
   rpc request-system-autorecovery {
     description "Manage autorecovery information";
     junos:command "request system autorecovery";
     input {
       uses command-forwarding;
     }
     output {
       container autorecovery {
         uses autorecovery-block;
       }
     }
   }
   rpc request-system-autorecovery-state-save {
     description "Save autorecovery state";
     junos:command "request system autorecovery state save";
     output {
       container autorecovery {
         uses autorecovery-block;
       }
     }
   }
   rpc request-system-autorecovery-state-recover {
     description "Check for problems and recover state if needed";
     junos:command "request system autorecovery state recover";
     output {
       container autorecovery {
         uses autorecovery-block;
       }
     }
   }
   rpc request-system-autorecovery-state-clear {
     description "Delete previously saved autorecovery state";
     junos:command "request system autorecovery state clear";
     output {
       container autorecovery {
         uses autorecovery-block;
       }
     }
   }
   rpc request-system-malware-quick-scan {
     description "Scan process files";
     junos:command "request system malware-scan quick-scan";
     input {
       leaf-list pids {
         ordered-by user;
         description "Processes IDs to scan";
         type union {
           type uint32;
           type string {
             pattern "<.*>|$.*";
           }
         }
       }
       leaf clean-action {
         description "Action to handle suspected malware";
         type enumeration {
           enum "clean" {
             description "Kill processes and delete files";
           }
           enum "warn" {
             description "Do not kill process or delete file";
           }
         }
       }
       leaf test {
         description "Scan for example test malware";
         status deprecated;
         type empty;
       }
     }
     output {
       container jmrt-scan-result {
         uses jmrt-scan-result-block;
       }
     }
   }
   rpc request-system-malware-veriexec-check {
     description "Check whether Verified Exec is running";
     status deprecated;
     junos:command "request system malware-scan veriexec-check";
     output {
       container jmrt-veriexec-check {
         uses jmrt-veriexec-check-block;
       }
     }
   }
   rpc request-system-malware-integrity-check {
     description "Check whether integrity mechanism is running";
     junos:command "request system malware-scan integrity-check";
     output {
       container jmrt-integrity-check {
         uses jmrt-integrity-check-block;
       }
     }
   }
   rpc request-system-malware-fake-malware {
     description "Run example malware";
     junos:command "request system malware-scan run-fake-malware";
     output {
       container jmrt-fake-malware {
         uses jmrt-fake-malware-block;
       }
     }
   }
   rpc request-system-malware-list-fake-malware {
     description "List running example malware processes";
     junos:command "request system malware-scan list-fake-malware";
     output {
       container jmrt-list-fake-malware {
         uses jmrt-list-fake-malware-block;
       }
     }
   }
   rpc request-system-routing-pitrace {
     description "Routing protocol daemon";
     junos:command "request system pixel-tracing routing";
     output {
       choice output_c {
         case output-tag {
           leaf output {
             type string;
           }
         }
         case multichassis-tag {
           anyxml multi-routing-engine-results;
         }
       }
     }
   }
   rpc request-system-routing-pitrace-flush {
     description "Flush pitrace";
     junos:command "request system pixel-tracing routing flush";
     output {
       choice output_c {
         case output-tag {
           leaf output {
             type string;
           }
         }
         case multichassis-tag {
           anyxml multi-routing-engine-results;
         }
       }
     }
   }
   rpc request-system-routing-pitrace-enable {
     description "Enable pitrace";
     junos:command "request system pixel-tracing routing enable";
     output {
       choice output_c {
         case output-tag {
           leaf output {
             type string;
           }
         }
         case multichassis-tag {
           anyxml multi-routing-engine-results;
         }
       }
     }
   }
   rpc request-system-routing-pitrace-disable {
     description "Disable pitrace";
     junos:command "request system pixel-tracing routing disable";
     output {
       choice output_c {
         case output-tag {
           leaf output {
             type string;
           }
         }
         case multichassis-tag {
           anyxml multi-routing-engine-results;
         }
       }
     }
   }
   rpc get-ethernet-switching-status-evpn-vlan {
     description "Show vlans status";
     junos:command "request system evpn forwarding vlans";
     input {
       leaf no-confirm {
         description "Do not ask for confirmation";
         type empty;
       }
       leaf instance {
         description "Routing instance";
         type string;
       }
       leaf vlan {
         description "VLAN name";
         type string;
       }
       leaf verbosity {
         junos:cli-feature "nokeyword";
         type enumeration {
           enum "detail" {
             description "Display detailed output";
           }
           enum "format" {
             description "Display formated output";
           }
         }
       }
       leaf module {
         description "Module name";
         type enumeration {
           enum "mac-table" {
             description "MAC module";
           }
           enum "mac-ip-table" {
             description "MAC IP module";
           }
         }
       }
     }
     output {
       container system-evpn {
         uses system-evpn-block;
       }
     }
   }
   rpc get-ethernet-switching-status-hash-vlan {
     description "Show vlans status";
     junos:command "request system evpn hash-values vlans";
     input {
       leaf no-confirm {
         description "Do not ask for confirmation";
         type empty;
       }
       leaf instance {
         description "Routing instance";
         type string;
       }
       leaf vlan {
         description "VLAN name";
         type string;
       }
     }
     output {
       container system-evpn {
         uses system-evpn-block;
       }
     }
   }
   rpc request-security-uefi-revoke {
     description "Revoke platform UEFI keys";
     junos:command "request security uefi revoke";
     input {
       leaf cmd {
         junos:cli-feature "nokeyword";
         type string;
         mandatory true;
       }
     }
     output {
       choice output_c {
         case output-tag {
           leaf output {
             type string;
           }
         }
         case multichassis-tag {
           anyxml multi-routing-engine-results;
         }
       }
     }
   }
   rpc request-security-bios-upgrade {
     description "Upgrade BIOS from the location";
     junos:command "request security bios-upgrade";
     input {
       leaf package-name {
         description "URL or path name of package";
         junos:cli-feature "nokeyword";
         type jt:filename;
       }
       leaf re-slot {
         description "RE slot number";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc generate-pki-key-pair {
     description "Generate RSA, DSA or ECDSA private and public key pair";
     junos:command "request security pki generate-key-pair";
     input {
       uses command-forwarding;
       choice daemon-select {
         case logical-system {
         }
       }
       choice id-type {
         case certificate-id {
           leaf certificate-id {
             description "Certificate identifier";
             type string {
               length "1 .. 32";
               junos:posix-pattern "![/ %.]";
               junos:pattern-message "Must not contain \'/\', %, \'.\' or a space";
             }
           }
         }
         case acme-key-id {
           leaf acme-key-id {
             description "Acme account key identifier";
             type string {
               length "1 .. 32";
               junos:posix-pattern "![/ %.]";
               junos:pattern-message "Must not contain \'/\', %, \'.\' or a space";
             }
           }
         }
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption";
           }
           enum "dsa" {
             description "DSA encryption";
           }
           enum "ecdsa" {
             description "ECDSA encryption";
           }
         }
       }
     }
     output {
       container cert-key-pair {
         uses cert-key-pair-block;
       }
     }
   }
   rpc generate-pki-certificate-request {
     description "Generate the certificate request in PKCS-10 format";
     junos:command "request security pki generate-certificate-request";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
       }
       leaf email {
         description "Email address";
         type string;
       }
     }
     output {
       choice output_c {
         case output-tag {
           leaf output {
             type string;
           }
         }
         case multichassis-tag {
           anyxml multi-routing-engine-results;
         }
       }
     }
   }
   rpc load-pki-ca-certificate {
     description "Load the certificate onto the routing platform";
     junos:command "request security pki ca-certificate load";
     input {
       uses command-forwarding;
       leaf ca-profile {
         description "Certificate authority profile";
         type string {
           length "1 .. 32";
           junos:posix-pattern "![/%. ]";
           junos:pattern-message "Must not contain \'/\', %, \'.\' or a space";
         }
         mandatory true;
       }
       choice daemon-select {
         case logical-system {
         }
       }
       leaf filename {
         description "File pathname containing certificate to load";
         type string;
         mandatory true;
       }
     }
     output {
       container cert-ca-load-status {
         uses cert-ca-load-status-block;
       }
     }
   }
   rpc request-security-pki-ca-profile-group {
     description "Perform operations on group of Certificate-authority(CA) certificates";
     junos:command "request security pki ca-certificate ca-profile-group";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
   }
   rpc request-default-trusted-ca-certs {
     description "Perform actions on default trusted ca certificates";
     junos:command "request security pki ca-certificate ca-profile-group default-trusted-ca-certs";
     input {
       uses command-forwarding;
     }
     output {
       choice output_c {
         case output-tag {
           leaf output {
             type string;
           }
         }
         case multichassis-tag {
           anyxml multi-routing-engine-results;
         }
       }
     }
   }
   rpc request-default-trusted-ca-certs-download {
     description "Download default trusted CA certs from a CDN server";
     junos:command "request security pki ca-certificate ca-profile-group default-trusted-ca-certs download";
     input {
       uses command-forwarding;
     }
     output {
       container default-trusted-ca-certs-download {
         uses default-trusted-ca-certs-download-block;
       }
     }
   }
   rpc request-default-trusted-ca-certs-download-cs {
     description "Check connectivity to CDN server to download default trusted CA certs";
     junos:command "request security pki ca-certificate ca-profile-group default-trusted-ca-certs download check-server";
     input {
       uses command-forwarding;
     }
     output {
       container default-trusted-ca-certs-download-cs {
         uses default-trusted-ca-certs-download-cs-block;
       }
     }
   }
   rpc request-default-trusted-ca-certs-download-status {
     description "Check current status of default trusted CA certs downloaded from CDN server";
     junos:command "request security pki ca-certificate ca-profile-group default-trusted-ca-certs download status";
     input {
       uses command-forwarding;
     }
     output {
       container default-trusted-ca-certs-download-status {
         uses default-trusted-ca-certs-download-status-block;
       }
     }
   }
   rpc request-security-pki-ca-profile-group-load {
     description "Load the certificate group onto the routing platform";
     junos:command "request security pki ca-certificate ca-profile-group load";
     input {
       uses command-forwarding;
       choice daemon-select {
         case logical-system {
         }
       }
       leaf ca-group-name {
         description "CA group identifier";
         type string {
           length "1 .. 24";
           junos:posix-pattern "![/ %]";
           junos:pattern-message "Must not contain \'/\', % or a space";
         }
         mandatory true;
       }
       leaf filename {
         description "File pathname containing certificate to load";
         type string;
         mandatory true;
       }
     }
   }
   rpc verify-pki-ca-certificate {
     description "Verify the certificate";
     junos:command "request security pki ca-certificate verify";
     input {
       uses command-forwarding;
       choice daemon-select {
         case logical-system {
         }
       }
       leaf ca-profile {
         description "Certificate authority profile";
         type string {
           length "1 .. 32";
           junos:posix-pattern "![/%. ]";
           junos:pattern-message "Must not contain \'/\', %, \'.\' or a space";
         }
         mandatory true;
       }
     }
     output {
       choice output_c {
         case output-tag {
           leaf output {
             type string;
           }
         }
         case multichassis-tag {
           anyxml multi-routing-engine-results;
         }
       }
     }
   }
   rpc request-security-local-certificate-enroll {
     description "Enroll router certificate with CA online";
     junos:command "request security pki local-certificate enroll";
     input {
       uses command-forwarding;
       leaf certificate-id {
         description "Certificate identifier";
         status deprecated;
         type string {
           length "1 .. 32";
           junos:posix-pattern "![/%. ]";
           junos:pattern-message "Must not contain \'/\', %, \'.\' or a space";
         }
         mandatory true;
       }
       leaf ca-profile {
         description "Certificate authority profile";
         status deprecated;
         type string {
           length "1 .. 32";
           junos:posix-pattern "![/%. ]";
           junos:pattern-message "Must not contain \'/\', %, \'.\' or a space";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
       choice daemon-select {
         case logical-system {
         }
       }
       leaf domain-name {
         description "Fully qualified domain name";
         status deprecated;
         type string;
       }
       leaf email {
         description "Email address";
         status deprecated;
         type string;
       }
     }
   }
   rpc request-security-local-certificate-enroll-cmpv2 {
     description "Enroll certificate using CMPv2 protocol";
     junos:command "request security pki local-certificate enroll cmpv2";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
           junos:posix-pattern "![/%. ]";
           junos:pattern-message "Must not contain \'/\', %, \'.\' or a space";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
   }
   rpc request-security-local-certificate-enroll-acme {
     description "Enroll certificate using ACME protocol";
     junos:command "request security pki local-certificate enroll acme";
     input {
       uses command-forwarding;
       choice daemon-select {
         case logical-system {
         }
       }
       leaf acme-key-id {
         description "ACME account key identifier";
         type string {
           length "1 .. 32";
           junos:posix-pattern "![/%. ]";
           junos:pattern-message "Must not contain \'/\', %, \'.\' or a space";
         }
         mandatory true;
       }
       leaf certificate-id {
         description "Certificate identifier";
         type string {
           length "1 .. 32";
           junos:posix-pattern "![/%. ]";
           junos:pattern-message "Must not contain \'/\', %, \'.\' or a space";
         }
         mandatory true;
       }
       leaf letsencrypt-enrollment {
         description "Whether the enrollment server is Let's Encrypt or not";
         type enumeration {
           enum "yes" {
             description "Certificate enrollment using Let's Encrypt";
           }
           enum "no" {
             description "Certificate enrollment using other server";
           }
         }
         mandatory true;
       }
       leaf terms-of-service {
         description "Service agreement of Let's Encrypt (https://letsencrypt.org/repository)";
         type enumeration {
           enum "agree" {
             description "Agreed to terms of service";
           }
           enum "disagree" {
             description "Disagree to terms of service";
           }
         }
       }
       leaf domain-names {
         description "Fully qualified domain names for subject-alt-name separated by comma. Maximum limit is 5";
         type string {
           junos:posix-pattern "![_ ]";
           junos:pattern-message "Must not contain \'_\' or space";
         }
         mandatory true;
       }
       leaf email {
         description "Email address";
         type string;
         mandatory true;
       }
       leaf ca-profile {
         description "Certificate authority profile";
         type string {
           length "1 .. 32";
           junos:posix-pattern "![/%. ]";
           junos:pattern-message "Must not contain \'/\', %, \'.\' or a space";
         }
         mandatory true;
       }
     }
   }
   rpc request-security-local-certificate-enroll-scep {
     description "Enroll end-entity certificate using SCEP protocol";
     junos:command "request security pki local-certificate enroll scep";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
         mandatory true;
       }
       leaf challenge-password {
         description "Password used by CA for enrollment and revocation";
         type string;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
     }
   }
   rpc request-security-local-certificate-re-enroll {
     description "Re-enroll router certificate with CA online";
     junos:command "request security pki local-certificate re-enroll";
     input {
       uses command-forwarding;
     }
   }
   rpc request-security-local-cert-re-enroll-acme {
     description "Enroll certificate using ACME protocol";
     junos:command "request security pki local-certificate re-enroll acme";
     input {
       uses command-forwarding;
       choice daemon-select {
         case logical-system {
         }
       }
       leaf acme-key-id {
         description "ACME account key identifier";
         type string {
           length "1 .. 32";
           junos:posix-pattern "![/%. ]";
           junos:pattern-message "Must not contain \'/\', %, \'.\' or a space";
         }
         mandatory true;
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
   }
   rpc request-security-local-cert-re-enroll-cmpv2 {
     description "Enroll certificate using CMPv2 protocol";
     junos:command "request security pki local-certificate re-enroll cmpv2";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
   }
   rpc request-security-local-cert-re-enroll-scep {
     description "Enroll end-entity certificate using SCEP protocol";
     junos:command "request security pki local-certificate re-enroll scep";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf challenge-password {
         description "Password used by CA for enrollment and revocation";
         type string;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
   }
   rpc request-security-local-certificate-export {
     description "Export Certificate";
     junos:command "request security pki local-certificate export";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
   }
   rpc load-pki-local-certificate {
     description "Load the certificate onto the routing platform";
     junos:command "request security pki local-certificate load";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       container cert-load-status {
         uses cert-load-status-block;
       }
     }
   }
   rpc verify-pki-local-certificate {
     description "Verify the certificate";
     junos:command "request security pki local-certificate verify";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
     }
     output {
       choice output_c {
         case output-tag {
           leaf output {
             type string;
           }
         }
         case multichassis-tag {
           anyxml multi-routing-engine-results;
         }
       }
     }
   }
   rpc generate-pki-self-signed-local-certificate {
     description "Generate a self-signed certificate";
     junos:command "request security pki local-certificate generate-self-signed";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
         mandatory true;
       }
       leaf ip-address {
         description "Static IP address of the device";
         type jt:ipaddr;
       }
       leaf ipv6-address {
         description "Static IPV6 address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
     output {
       choice output_c {
         case output-tag {
           leaf output {
             type string;
           }
         }
         case multichassis-tag {
           anyxml multi-routing-engine-results;
         }
       }
     }
   }
   rpc request-security-cloud-certificate-download {
     description "Download cloud certificate using resource name";
     junos:command "request security pki cloud-certificate download";
     input {
       uses command-forwarding;
       choice daemon-select {
         case logical-system {
         }
       }
       leaf certificate-profile {
         description "Certificate profile name";
         type string {
           length "1 .. 32";
           junos:posix-pattern "![/%. ]";
           junos:pattern-message "Must not contain \'/\', \'%\', \'.\' or a space";
         }
         mandatory true;
       }
       leaf save-to {
         description "Options to save key/cert only in-memory option";
         default "memory";
         type enumeration {
           enum "memory" {
             description "Save in memory only";
           }
         }
       }
     }
   }
   rpc request-security-key-pair-export {
     description "Export Keypair in PEM format";
     junos:command "request security pki key-pair export";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier for keypair";
         type string {
           length "1 .. 32";
           junos:posix-pattern "![/%. ]";
           junos:pattern-message "Must not contain \'/\', %, \'.\' or a space";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
   }
   rpc load-pki-crl {
     description "Load the CRL onto the routing platform";
     junos:command "request security pki crl load";
     input {
       uses command-forwarding;
       choice daemon-select {
         case logical-system {
         }
       }
       leaf ca-profile {
         description "Certificate authority profile";
         type string {
           length "1 .. 32";
           junos:posix-pattern "![/%. ]";
           junos:pattern-message "Must not contain \'/\', %, \'.\' or a space";
         }
         mandatory true;
       }
       leaf filename {
         description "Pathname of file containing CRL to load";
         type string;
         mandatory true;
       }
     }
     output {
       choice output_c {
         case output-tag {
           leaf output {
             type string;
           }
         }
         case multichassis-tag {
           anyxml multi-routing-engine-results;
         }
       }
     }
   }
   rpc request-security-pki-file-sync {
     description "Perform PKI file-sync with MN-HA remote node";
     junos:command "request security pki sync-from-peer";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
   }
   rpc node-local-generate-key-pair {
     description "Generate RSA, DSA or ECDSA private and public key pair";
     junos:command "request security pki node-local generate-key-pair";
     input {
       uses command-forwarding;
       choice daemon-select {
         case logical-system {
         }
       }
       leaf certificate-id {
         description "Certificate identifier";
         type string {
           length "1 .. 32";
           junos:posix-pattern "![/ %.]";
           junos:pattern-message "Must not contain \'/\', %, \'.\' or a space";
         }
         mandatory true;
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption (Key-Size: 512/1024/2048/4096 bits";
           }
           enum "dsa" {
             description "DSA encryption (Key-Size: 1024/2048/4096 bits)";
           }
           enum "ecdsa" {
             description "ECDSA encryption (Key-Size: 256/384/521 bits)";
           }
         }
       }
     }
     output {
       container cert-key-pair {
         uses cert-key-pair-block;
       }
     }
   }
   rpc node-local-generate-csr {
     description "Generate the certificate request in PKCS-10 format";
     junos:command "request security pki node-local generate-certificate-request";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name for subject-alt-name";
         type string;
       }
       leaf email {
         description "Email address";
         type string;
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
     }
   }
   rpc node-local-local-certificate-enroll {
     description "Enroll router certificate with CA online";
     junos:command "request security pki node-local local-certificate enroll";
     input {
       uses command-forwarding;
       leaf certificate-id {
         description "Certificate identifier";
         status deprecated;
         type string {
           length "1 .. 32";
           junos:posix-pattern "![/%. ]";
           junos:pattern-message "Must not contain \'/\', %, \'.\' or a space";
         }
         mandatory true;
       }
       leaf domain-name {
         description "Fully qualified domain name for subject-alt-name";
         status deprecated;
         type string;
       }
       leaf email {
         description "Email address";
         status deprecated;
         type string;
       }
       leaf ca-profile {
         description "Certificate authority profile";
         status deprecated;
         type string {
           length "1 .. 32";
           junos:posix-pattern "![/%. ]";
           junos:pattern-message "Must not contain \'/\', %, \'.\' or a space";
         }
         mandatory true;
       }
       leaf challenge-password {
         description "Password used by CA for enrollment and revocation";
         status deprecated;
         type string;
         mandatory true;
       }
       leaf scep-encryption-algorithm {
         description "Encrypion algorithm used for SCEP-PKCS7";
         status deprecated;
         type enumeration {
           enum "des" {
             description "DES Encryption";
             status deprecated;
           }
           enum "des3" {
             description "DES-3 Encryption (default)";
             status deprecated;
           }
         }
       }
       leaf scep-digest-algorithm {
         description "Hash algorithm used for SCEP-PKCS7";
         status deprecated;
         type enumeration {
           enum "md5" {
             description "MD-5 digest";
             status deprecated;
           }
           enum "sha1" {
             description "SHA-1 digest (default)";
             status deprecated;
           }
         }
       }
       leaf ip-address {
         description "Static IP address of the device";
         status deprecated;
         type jt:ipaddr;
       }
       leaf ipv6-address {
         description "Static IPv6 address of the device for subject-alt-name";
         status deprecated;
         type jt:ipv6addr;
       }
       leaf subject {
         description "DC=<Domain component>,CN=<Common-Name>,OU=<Organizational-Unit-name>,O=<Organization-name>,SN=<Serial-Number>,L=<Locality>,ST=<state>,C=<Country>";
         status deprecated;
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         status deprecated;
         type enumeration {
           enum "sha-1" {
             description "SHA-1 digests (default value)";
             status deprecated;
           }
           enum "sha-256" {
             description "SHA-256 digests";
             status deprecated;
           }
         }
       }
     }
   }
   rpc node-local-local-certificate-enroll-cmpv2 {
     description "Enroll certificate using CMPv2 protocol";
     junos:command "request security pki node-local local-certificate enroll cmpv2";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
           junos:posix-pattern "![/%. ]";
           junos:pattern-message "Must not contain \'/\', %, \'.\' or a space";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
   }
   rpc node-local-local-certificate-enroll-scep {
     description "Enroll end-entity certificate using SCEP protocol";
     junos:command "request security pki node-local local-certificate enroll scep";
     input {
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
         mandatory true;
       }
       leaf challenge-password {
         description "Password used by CA for enrollment and revocation";
         type string;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
     }
   }
   rpc load-node-local-local-certificate {
     description "Load the certificate onto the routing platform";
     junos:command "request security pki node-local local-certificate load";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       container cert-load-status {
         uses cert-load-status-block;
       }
     }
   }
   rpc verify-pki-node-local-local-certificate {
     description "Verify the certificate";
     junos:command "request security pki node-local local-certificate verify";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
     }
   }
   rpc generate-node-local-self-signed-certificate {
     description "Generate a self-signed certificate";
     junos:command "request security pki node-local local-certificate generate-self-signed";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf domain-name {
         description "Fully qualified domain name";
         type string;
         mandatory true;
       }
       leaf ip-address {
         description "Static IP address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
   }
   rpc node-local-local-certificate-re-enroll {
     description "Re-enroll router certificate with CA online";
     junos:command "request security pki node-local local-certificate re-enroll";
     input {
       uses command-forwarding;
     }
   }
   rpc node-local-local-cert-re-enroll-cmpv2 {
     description "Enroll certificate using CMPv2 protocol";
     junos:command "request security pki node-local local-certificate re-enroll cmpv2";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf re-generate-keypair {
         description "Generate new keypair for re-enrollment";
         type empty;
       }
     }
   }
   rpc node-local-local-cert-re-enroll-scep {
     description "Enroll end-entity certificate using SCEP protocol";
     junos:command "request security pki node-local local-certificate re-enroll scep";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain \'/\', %, \'.\' or a space";
         }
         mandatory true;
       }
       leaf ca-profile {
         description "Certificate authority profile";
         type string {
           length "1 .. 32";
           junos:posix-pattern "![/%. ]";
           junos:pattern-message "Must not contain \'/\', %, \'.\' or a space";
         }
       }
       leaf challenge-password {
         description "Password used by CA for enrollment and revocation";
         type string;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
   }
   rpc node-local-local-certificate-export {
     description "Export Certificate";
     junos:command "request security pki node-local local-certificate export";
     input {
       uses command-forwarding;
       choice daemon-select {
         case logical-system {
         }
       }
       leaf certificate-id {
         description "Certificate identifier";
         type string {
           length "1 .. 32";
           junos:posix-pattern "![/%. ]";
           junos:pattern-message "Must not contain \'/\', %, \'.\' or a space";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
   }
   rpc node-local-key-pair-export {
     description "Export Keypair in PEM format";
     junos:command "request security pki node-local key-pair export";
     input {
       uses command-forwarding;
       choice daemon-select {
         case logical-system {
         }
       }
       leaf certificate-id {
         description "Certificate identifier for keypair";
         type string {
           length "1 .. 32";
           junos:posix-pattern "![/%. ]";
           junos:pattern-message "Must not contain \'/\', %, \'.\' or a space";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
   }
   rpc request-security-pki-ca-profile-group-status {
     description "Status of CA certs in default CA profile group";
     junos:command "request security pki ca-profile-group-status";
     input {
       uses command-forwarding;
       choice daemon-select {
         case logical-system {
         }
       }
       leaf ca-group-name {
         description "CA group identifier";
         type string {
           length "1 .. 24";
           junos:posix-pattern "![/ %]";
           junos:pattern-message "Must not contain \'/\', % or a space";
         }
         mandatory true;
       }
     }
     output {
       container ca-profile-group-cert-status {
         uses ca-profile-group-cert-status-block;
       }
     }
   }
   rpc verify-integrity-status {
     description "Check the integrity of PKI files (in CC mode)";
     junos:command "request security pki verify-integrity-status";
     input {
       uses command-forwarding;
       choice daemon-select {
         case logical-system {
         }
       }
     }
     output {
       container verify-integrity-status {
         uses verify-integrity-status-block;
       }
     }
   }
   rpc request-pki-debug-memory-profile {
     description "Enable or disable memory profile";
     junos:command "request security pki debug-memory-profile";
     input {
       leaf profile-state {
         junos:cli-feature "nokeyword";
         type enumeration {
           enum "enable" {
             description "Enable PKI memory profiling";
           }
           enum "disable" {
             description "Disable PKI memory profiling";
           }
           enum "dump" {
             description "Dump PKI memory profile debug info";
           }
         }
         mandatory true;
       }
     }
     output {
       choice output_c {
         case output-tag {
           leaf output {
             type string;
           }
         }
         case multichassis-tag {
           anyxml multi-routing-engine-results;
         }
       }
     }
   }
   rpc generate-ssh-key-pair {
     description "Generate SSH key pair identity";
     junos:command "request security ssh key-pair-identity generate";
     input {
       leaf identity-name {
         description "Identity name";
         junos:cli-feature "nokeyword";
         type string {
           junos:posix-pattern "^[[:alnum:]_-]+$";
           junos:pattern-message "Must be a string of letters, numbers, dashes or underscores";
         }
         mandatory true;
       }
       leaf passphrase {
         description "Generate SSH identity with passphrase";
         type string {
           junos:posix-pattern "^[[:alnum:]_-]{6,30}$";
           junos:pattern-message "Must be a string of letters, numbers, dashes or underscores, at least 6 characters and no more than 30 characters";
         }
       }
     }
     output {
       choice output_c {
         case output-tag {
           leaf output {
             type string;
           }
         }
         case multichassis-tag {
           anyxml multi-routing-engine-results;
         }
       }
     }
   }
   rpc get-enable-ike-debug {
     description "Enable ike debug";
     junos:command "request security ike debug-enable";
     input {
       uses command-forwarding;
       leaf remote {
         description "Remote ip address";
         type jt:ipaddr;
         mandatory true;
       }
     }
     output {
       choice output_c {
         case output-tag {
           leaf output {
             type string;
           }
         }
         case multichassis-tag {
           anyxml multi-routing-engine-results;
         }
       }
     }
   }
   rpc get-disable-ike-debug {
     description "Disable ike debug";
     junos:command "request security ike debug-disable";
     input {
       uses command-forwarding;
     }
     output {
       choice output_c {
         case output-tag {
           leaf output {
             type string;
           }
         }
         case multichassis-tag {
           anyxml multi-routing-engine-results;
         }
       }
     }
   }
   rpc get-enable-ike-event-logs {
     description "Enable ike event logs";
     junos:command "request security ike debug-enable-event-logs";
     input {
       uses command-forwarding;
     }
     output {
       choice output_c {
         case output-tag {
           leaf output {
             type string;
           }
         }
         case multichassis-tag {
           anyxml multi-routing-engine-results;
         }
       }
     }
   }
   rpc get-disable-ike-event-logs {
     description "Disable ike event logs";
     junos:command "request security ike debug-disable-event-logs";
     input {
       uses command-forwarding;
     }
     output {
       choice output_c {
         case output-tag {
           leaf output {
             type string;
           }
         }
         case multichassis-tag {
           anyxml multi-routing-engine-results;
         }
       }
     }
   }
   rpc request-ike-debug-memory-profile {
     description "Enable or disable memory profile";
     junos:command "request security ike debug-memory-profile";
     input {
       leaf profile-state {
         junos:cli-feature "nokeyword";
         type enumeration {
           enum "enable" {
             description "Enable IKE memory profiling";
           }
           enum "disable" {
             description "Disable IKE memory profiling";
           }
           enum "dump" {
             description "Dump IKE memory profile debug info";
           }
         }
         mandatory true;
       }
     }
     output {
       choice output_c {
         case output-tag {
           leaf output {
             type string;
           }
         }
         case multichassis-tag {
           anyxml multi-routing-engine-results;
         }
       }
     }
   }
   rpc request-re-distribution-vpn {
     description "Re-distribute tunnel(s)";
     junos:command "request security re-distribution ipsec-vpn";
     input {
       leaf gateway-name {
         description "Gateway name";
         type string {
           length "1 .. 32";
         }
         mandatory true;
       }
       leaf fpc {
         description "FPC slot number";
         type union {
           type string {
             pattern "<.*>|$.*";
           }
           type uint32 {
             range "0 .. 63";
           }
         }
         mandatory true;
       }
       leaf pic {
         description "PIC slot number";
         type union {
           type string {
             pattern "<.*>|$.*";
           }
           type uint32 {
             range "0 .. 3";
           }
         }
         mandatory true;
       }
       leaf thread-id {
         description "Thread-id";
         type union {
           type string {
             pattern "<.*>|$.*";
           }
           type uint32 {
             range "1 .. 27";
           }
         }
       }
       leaf remote-id {
         description "Remote-ike-id of the peer";
         type string {
           length "1 .. 256";
         }
       }
     }
     output {
       choice output_c {
         case output-tag {
           leaf output {
             type string;
           }
         }
         case multichassis-tag {
           anyxml multi-routing-engine-results;
         }
       }
     }
   }
   rpc request-internal-security-association-refresh {
     description "Refresh internal security association";
     junos:command "request security internal-security-association refresh";
     input {
       uses command-forwarding;
     }
     output {
       choice output_c {
         case output-tag {
           leaf output {
             type string;
           }
         }
         case multichassis-tag {
           anyxml multi-routing-engine-results;
         }
       }
     }
   }
   rpc request-idp-policy-load {
     description "Load a compiled policy";
     junos:command "request security idp load";
     input {
       uses command-forwarding;
       leaf policy {
         description "Compiled policy file name";
         type string;
       }
       leaf no-ai {
         description "Application identification flag";
         type empty;
       }
       leaf detector {
         description "Detector file name";
         type string;
       }
     }
     output {
       container request-idp-policy-load {
         uses request-idp-policy-load-block;
       }
     }
   }
   rpc request-idp-storage-cleanup {
     description "Delete non-essential idp files for freeing up disk space";
     junos:command "request security idp storage-cleanup";
     input {
       uses command-forwarding;
       choice cleanup-choice {
         case cache-files {
           leaf cache-files {
             description "Deletes DFA cache files used for optimizing idp policy compilation";
             type empty;
           }
         }
         case downloaded-files {
           leaf downloaded-files {
             description "Deletes downloaded security-package files (doesn't affect installed database)";
             type empty;
           }
         }
         case packet-capture {
           leaf packet-capture {
             description "Deletes attack pcap files stored locally";
             type empty;
           }
         }
       }
     }
     output {
       container request-idp-storage-cleanup {
         uses request-idp-storage-cleanup-block;
       }
     }
   }
   rpc request-idp-security-package-install {
     description "Update attack database, active policy, detector with new package";
     junos:command "request security idp security-package install";
     input {
       uses command-forwarding;
       choice re-selector-idpd {
         case re0 {
         }
         case re1 {
         }
       }
       choice install-choice {
         case update-attack-database-only {
           leaf update-attack-database-only {
             description "Don't update/push active policy or detector to data plane";
             type empty;
           }
         }
         case policy-templates {
           leaf policy-templates {
             description "Update previously installed policy-templates with newly downloaded ones";
             type empty;
           }
         }
         case precompiled-policy {
           leaf precompiled-policy {
             description "Update dataplane 'Recommended' policy and detector for it with newly downloaded ones";
             type empty;
           }
         }
         case older-detector {
           leaf older-detector {
             description "Update dataplane with older detector";
             type empty;
           }
         }
         case status {
           leaf status {
             description "Retrieve the status of security package load operation";
             type empty;
           }
         }
         case policy-template-result {
           leaf policy-template-result {
             description "Status of policy templates operation";
             type empty;
           }
         }
       }
     }
     output {
       container secpack-update-status {
         uses secpack-update-status-block;
       }
     }
   }
   rpc request-idp-security-package-download {
     description "Download security package (Package includes detector and deltas for attack table)";
     junos:command "request security idp security-package download";
     input {
       uses command-forwarding;
       choice re-selector-idpd {
         case re0 {
         }
         case re1 {
         }
       }
       choice download-choice {
         case full-update {
           leaf full-update {
             description "Download package with complete attack table";
             type empty;
           }
         }
         case package-option {
           leaf package-option {
             junos:cli-feature "nokeyword";
             type enumeration {
               enum "check-server" {
                 description "Retrieve version information for latest package on server";
               }
               enum "policy-templates" {
                 description "Download policy templates";
               }
               enum "precompiled-policy" {
                 description "Download pre-compiled 'Recommended' policy and detector for it";
               }
             }
           }
         }
         case minor-only {
           leaf minor-only {
             description "Download minor-only security package";
             type empty;
           }
         }
         case status {
           leaf status {
             description "Retrieve the status of security package download operation";
             type empty;
           }
         }
         case policy-template-file {
           leaf policy-template-file {
             description "Current status of policy template file";
             type empty;
           }
         }
         case policy-template-result {
           leaf policy-template-result {
             description "Status of policy templates operation";
             type empty;
           }
         }
       }
     }
     output {
       container secpack-download-status {
         uses secpack-download-status-block;
       }
     }
   }
   rpc request-idp-security-package-download-version {
     description "Version of package to download";
     junos:command "request security idp security-package download version";
     input {
       uses command-forwarding;
       choice re-selector-idpd {
         case re0 {
         }
         case re1 {
         }
       }
       leaf version-value {
         description "Version number";
         junos:cli-feature "nokeyword";
         type union {
           type uint32;
           type string {
             pattern "<.*>|$.*";
           }
         }
         mandatory true;
       }
       leaf full-update {
         description "Download package with complete attack table";
         type empty;
       }
     }
     output {
       container secpack-download-status {
         uses secpack-download-status-block;
       }
     }
   }
   rpc request-idp-security-package-offline-download {
     description "Unzip the security package and copy the xml files";
     junos:command "request security idp security-package offline-download";
     input {
       uses command-forwarding;
       choice re-selector-idpd {
         case re0 {
         }
         case re1 {
         }
       }
       choice offline-download-choice {
         case package-path {
           leaf package-path {
             description "Package path of the zipped security package ";
             type string {
               junos:posix-pattern "![*]";
               junos:pattern-message "File name can\'t contain \'*\'. Use TAB for filename completion";
             }
           }
         }
         case status {
           leaf status {
             description "Retrieve the status of offline package download operation";
             type empty;
           }
         }
       }
     }
     output {
       container offline-download-status {
         uses offline-download-status-block;
       }
     }
   }
   rpc request-idp-security-package-rollback {
     description "Rollback attack database, active policy, detector";
     junos:command "request security idp security-package rollback";
     input {
       uses command-forwarding;
       choice re-selector-idpd {
         case re0 {
         }
         case re1 {
         }
       }
       choice rollback-choice {
         case status {
           leaf status {
             description "Retrieve the status of package rollback operation";
             type empty;
           }
         }
       }
     }
   }
   rpc get-idp-attack-rule-information {
     description "Analyze the PCAP traffic and display the context generated";
     junos:command "request security idp pcap-analysis";
     input {
       uses command-forwarding;
       leaf pcap-file {
         description "Pcap file";
         junos:cli-feature "nokeyword";
         type jt:filename;
         mandatory true;
       }
       leaf from-zone {
         description "Select the policy information matching the given source zone";
         type string;
         mandatory true;
       }
       leaf to-zone {
         description "Select the policy information matching the given destination zone";
         type string;
         mandatory true;
       }
       leaf logging-level {
         description "Brief status / Detail logging of ongoing pcap-analysis";
         junos:cli-feature "nokeyword";
         type enumeration {
           enum "brief" {
             description "Brief status of ongoing pcap-analysis";
           }
           enum "detail" {
             description "Detail logging of ongoing pcap-analysis";
           }
         }
       }
       leaf packets {
         description "Insert only first n packets from pcap for pcap-analysis";
         type union {
           type uint32;
           type string {
             pattern "<.*>|$.*";
           }
         }
       }
       choice lsys {
         case logical-system {
         }
         case root-logical-system {
           leaf root-logical-system {
             description "Root logical-system (default)";
             type empty;
           }
         }
         case tenant {
         }
       }
     }
     output {
       container idp-attack-rule-information {
         uses idp-attack-rule-information-block;
       }
     }
   }
   rpc request-idp-dmi-to-pcap {
     description "Convert the IDP attack capture to pcap format";
     junos:command "request security idp dmi-to-pcap";
     input {
       uses command-forwarding;
       leaf pcap-file {
         description "Complete path of the pcap file";
         junos:cli-feature "nokeyword";
         type jt:filename;
         mandatory true;
       }
       choice lsys {
         case logical-system {
         }
         case root-logical-system {
           leaf root-logical-system {
             description "Root logical-system (default)";
             type empty;
           }
         }
         case tenant {
         }
       }
     }
     output {
       container idp-dmi-to-pcap {
         uses idp-dmi-to-pcap-block;
       }
     }
   }
   rpc request-idp-ssl-key-add {
     description "Add SSL key and server";
     junos:command "request security idp ssl-inspection key add";
     input {
       uses command-forwarding;
       leaf key-name {
         description "Key name";
         junos:cli-feature "nokeyword";
         type string {
           length "1 .. 31";
         }
         mandatory true;
       }
       leaf file {
         description "Key file";
         type jt:filename;
       }
       leaf password {
         description "Password used to encrypt private key";
         type string {
           length "1 .. 31";
         }
       }
       leaf tcp-port {
         description "Server TCP port";
         type union {
           type string {
             pattern "<.*>|$.*";
           }
           type uint16 {
             range "1 .. 65535";
           }
         }
       }
     }
   }
   rpc request-idp-ssl-key-delete {
     description "Delete SSL keys and servers";
     junos:command "request security idp ssl-inspection key delete";
     input {
       uses command-forwarding;
       leaf key-name {
         description "Key name";
         junos:cli-feature "nokeyword";
         type string {
           length "1 .. 31";
         }
       }
       leaf tcp-port {
         description "Server TCP port";
         type union {
           type string {
             pattern "<.*>|$.*";
           }
           type uint16 {
             range "1 .. 65535";
           }
         }
       }
     }
     output {
       container request-idp-ssl-key-delete {
         uses request-idp-ssl-key-delete-block;
       }
     }
   }
   rpc jist-conversion-information {
     description "JIST conversion of snort rules to Juniper Signatures";
     junos:command "request security idp jist-conversion";
     input {
       uses command-forwarding;
       choice re-selector-idpd {
         case re0 {
         }
         case re1 {
         }
       }
       leaf input-file {
         description "Snort rules file";
         type string;
         mandatory true;
       }
       leaf output-file {
         description "Redirect converted attacks-set commands to this file";
         type string;
       }
     }
     output {
       container jist-conversion-information {
         uses jist-conversion-information-block;
       }
     }
   }
   rpc request-eedebug-capture-start {
     description "Start datapath debug packet capture";
     junos:command "request security datapath-debug capture start";
     output {
       container request-eedebug-capture-start-result {
         uses request-eedebug-capture-start-result-block;
       }
     }
   }
   rpc request-eedebug-capture-stop {
     description "Stop datapath debug packet capture";
     junos:command "request security datapath-debug capture stop";
     output {
       container request-eedebug-capture-stop-result {
         uses request-eedebug-capture-stop-result-block;
       }
     }
   }
   rpc request-key-manager-profile-config {
     description "Get the config for configured key profile";
     junos:command "request security key-manager profiles get profile-config";
     input {
       leaf profile-name {
         description "Name of the configured key profile";
         type string {
           length "1 .. 32";
         }
         mandatory true;
       }
     }
     output {
       container key-manager-profiles-get-info {
         uses key-manager-profiles-get-info-block;
       }
     }
   }
   rpc request-key-manager-profile-status {
     description "Get the status for configured key profile";
     junos:command "request security key-manager profiles get profile-status";
     input {
       leaf profile-name {
         description "Name of the configured key profile";
         type string {
           length "1 .. 32";
         }
         mandatory true;
       }
       leaf peer-sae-id {
         description "Specify peer sae id";
         type string {
           length "1 .. 250";
         }
       }
     }
     output {
       container key-manager-profiles-get-info {
         uses key-manager-profiles-get-info-block;
       }
     }
   }
   rpc request-key-manager-profile-keys {
     description "Get the key(s) for configured key profile";
     junos:command "request security key-manager profiles get profile-keys";
     input {
       leaf profile-name {
         description "Name of the configured key profile";
         type string {
           length "1 .. 32";
         }
         mandatory true;
       }
       leaf-list peer-sae-id {
         ordered-by user;
         description "Specify peer sae id";
         type string {
           length "1 .. 250";
         }
         max-elements 20;
       }
       leaf key-count {
         description "Specify the number of keys";
         type union {
           type string {
             pattern "<.*>|$.*";
           }
           type uint32 {
             range "1 .. 20";
           }
         }
       }
       leaf key-size {
         description "Specify the size of key(s) in bits";
         type union {
           type string {
             pattern "<.*>|$.*";
           }
           type uint32 {
             range "256 .. 4096";
           }
         }
       }
     }
     output {
       container key-manager-profiles-get-info {
         uses key-manager-profiles-get-info-block;
       }
     }
   }
   rpc request-key-manager-profile-keys-with-id {
     description "Get the key(s) for given key-id(s) for configured key profile";
     junos:command "request security key-manager profiles get profile-keys-with-id";
     input {
       leaf profile-name {
         description "Name of the configured key profile";
         type string {
           length "1 .. 32";
         }
         mandatory true;
       }
       leaf peer-sae-id {
         description "Specify peer sae id";
         type string {
           length "1 .. 250";
         }
       }
       leaf-list key-id {
         ordered-by user;
         description "Specify key id";
         type string {
           length "1 .. 512";
         }
         max-elements 20;
       }
     }
     output {
       container key-manager-profiles-get-info {
         uses key-manager-profiles-get-info-block;
       }
     }
   }
   rpc request-anti-virus-update-avira-update {
     description "Update avira-engine pattern";
     junos:command "request security utm anti-virus avira-engine pattern-update";
     input {
       uses command-forwarding;
     }
   }
   rpc request-anti-virus-update-avira-local {
     description "Update pattern from local folder";
     junos:command "request security utm anti-virus avira-engine pattern-local-update";
     input {
       uses command-forwarding;
       leaf path {
         description "Pattern update from local folder";
         junos:cli-feature "nokeyword";
         type string;
         mandatory true;
       }
     }
   }
   rpc request-anti-virus-update-avira-reload {
     description "Reload avira-engine pattern";
     junos:command "request security utm anti-virus avira-engine pattern-reload";
     input {
       uses command-forwarding;
     }
   }
   rpc request-anti-virus-update-avira-delete {
     description "Delete avira-engine pattern";
     junos:command "request security utm anti-virus avira-engine pattern-delete";
     input {
       uses command-forwarding;
     }
   }
   rpc request-custom-object-url-feed-update {
     description "Request update for url-feed";
     junos:command "request security utm custom-objects url-feed update";
     input {
       uses command-forwarding;
       leaf feed-name {
         description "Name of url-feed";
         junos:cli-feature "nokeyword";
         type string;
         mandatory true;
       }
       leaf force {
         description "Forcefully update url-feed";
         type empty;
       }
       choice lsys {
         case logical-system {
         }
         case root-logical-system {
           leaf root-logical-system {
             description "Root logical-system (default)";
             type empty;
           }
         }
         case tenant {
         }
       }
     }
     output {
       container feed-update {
         uses feed-update-block;
       }
     }
   }
   rpc request-migrate-ng {
     description "Migration to NG-Juniper";
     junos:command "request security utm web-filtering category migrate-to-ng-juniper";
     input {
       uses command-forwarding;
     }
     output {
       container migrate-ng {
         uses migrate-ng-block;
       }
     }
   }
   rpc request-category-download {
     description "Download predefined-category and predefined-filter package from server";
     junos:command "request security utm web-filtering category download";
     input {
       uses command-forwarding;
       leaf version {
         description "Version number";
         status deprecated;
         type union {
           type uint32;
           type string {
             pattern "<.*>|$.*";
           }
         }
       }
       leaf rollback {
         description "Download Backup Category Package";
         type empty;
       }
     }
     output {
       container category-updater {
         uses category-updater-block;
       }
     }
   }
   rpc request-category-download-install {
     description "Download and install predefined-category and predefined-filter package from server";
     junos:command "request security utm web-filtering category download-install";
     input {
       uses command-forwarding;
       leaf version {
         description "Version number";
         status deprecated;
         type union {
           type uint32;
           type string {
             pattern "<.*>|$.*";
           }
         }
       }
       leaf rollback {
         description "Download Backup Category Package";
         type empty;
       }
     }
     output {
       container category-updater {
         uses category-updater-block;
       }
     }
   }
   rpc request-category-install {
     description "Install predefined-category and predefined-filter to system";
     junos:command "request security utm web-filtering category install";
     input {
       uses command-forwarding;
     }
     output {
       container category-updater {
         uses category-updater-block;
       }
     }
   }
   rpc request-category-uninstall {
     description "Rollback to system default predefined-category";
     junos:command "request security utm web-filtering category uninstall";
     input {
       uses command-forwarding;
     }
   }
   rpc request-ewf-cache-preload-download {
     description "Downloads and installs URL feed from remote server";
     junos:command "request security utm web-filtering cache-preload download";
     input {
       uses command-forwarding;
       leaf feed-type {
         description "Choose type of the URL feed";
         junos:cli-feature "nokeyword";
         type enumeration {
           enum "abs-urls-feed" {
             description "List of absolute URLs with categories";
           }
           enum "server-names-feed" {
             description "List of server names with categories";
           }
         }
         mandatory true;
       }
       leaf feed-url {
         description "Link to the URL feed package on remote server";
         type string;
       }
     }
   }
   rpc request-ewf-cache-preload-load-active {
     description "Downloads categorized URL feed and preloads cache";
     junos:command "request security utm web-filtering cache-preload load-active";
     input {
       uses command-forwarding;
       leaf load-active-opts {
         description "Options to load-active request";
         junos:cli-feature "nokeyword";
         type enumeration {
           enum "abs-urls-feed" {
             description "List of absolute URLs with categories";
           }
           enum "server-names-feed" {
             description "List of server names with categories";
           }
         }
         mandatory true;
       }
     }
   }
   rpc request-ewf-cache-preload-load-active-local {
     description "Preloads cache by using available URL feed in the system";
     junos:command "request security utm web-filtering cache-preload load-active-local";
     input {
       uses command-forwarding;
       leaf load-active-local-opts {
         description "Options to load-active-local request";
         junos:cli-feature "nokeyword";
         type enumeration {
           enum "abs-urls-feed" {
             description "List of absolute URLs with categories";
           }
           enum "server-names-feed" {
             description "List of server names with categories";
           }
         }
         mandatory true;
       }
     }
   }
   rpc request-custom-page-file-reload {
     description "Reload custom-page file";
     junos:command "request security utm web-filtering custom-page reload";
     input {
       uses command-forwarding;
     }
   }
   rpc request-ng-recategorize {
     description "URL for which category needs to be updated";
     junos:command "request security utm web-filtering recategorize url";
     input {
       leaf recategorize-url {
         description "URL for which category needs to be updated";
         junos:cli-feature "nokeyword";
         type string {
           length "1 .. 249";
         }
         mandatory true;
       }
       leaf category-name {
         description "Requested category name for the URL";
         type string {
           length "1 .. 249";
         }
       }
       leaf status {
         description "Status of the recategorization URL requested";
         type empty;
       }
     }
     output {
       container ng-recategorize {
         uses ng-recategorize-block;
       }
     }
   }
   rpc request-ng-categorize {
     description "URL for which category needs to be updated";
     junos:command "request security utm web-filtering categorize url";
     input {
       leaf categorize-url {
         description "URL for which category needs to be updated";
         junos:cli-feature "nokeyword";
         type string {
           length "1 .. 249";
         }
         mandatory true;
       }
       leaf category-name {
         description "Requested category name for the URL";
         type string {
           length "1 .. 249";
         }
       }
     }
     output {
       container ng-categorize {
         uses ng-categorize-block;
       }
     }
   }
   rpc request-security-dynamic-address-update {
     description "Start a round of update";
     junos:command "request security dynamic-address update";
     input {
       uses command-forwarding;
       leaf address-name {
         description "Dynamic address name";
         type string {
           length "1 .. 63";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case multichassis-tag {
           anyxml multi-routing-engine-results;
         }
       }
     }
   }
   rpc check-security-policies {
     description "Check the security policies";
     junos:command "request security policies check";
     input {
       uses command-forwarding;
       leaf from-zone {
         description "Check the policies from this zone";
         type string;
       }
       leaf to-zone {
         description "Check the policies to this zone";
         type string;
       }
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc check-global-policies {
     description "Check global policies";
     junos:command "request security policies check global";
     input {
       uses command-forwarding;
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc recover-security-policy {
     description "Recover the security policies";
     junos:command "request security policies resync";
     input {
       uses command-forwarding;
       leaf from-zone {
         description "Recover the policies from this zone";
         type string;
       }
       leaf to-zone {
         description "Recover the policies to this zone";
         type string;
       }
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc recover-global-policies {
     description "Recover global policies";
     junos:command "request security policies resync global";
     input {
       uses command-forwarding;
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-userfw-local-auth-table-add {
     junos:command "request security user-identification local-authentication-table add";
     input {
       uses command-forwarding;
       leaf user-name {
         description "Add user name to local authentication table";
         type string {
           length "1 .. 64";
         }
         mandatory true;
       }
       leaf ip-address {
         description "Add ip-address to local authentication table";
         type jt:ipaddr;
         mandatory true;
       }
       leaf-list roles {
         ordered-by user;
         description "Add role name to local authentication table";
         type string {
           length "1 .. 63";
         }
       }
     }
   }
   rpc request-userfw-local-auth-table-delete-ip {
     description "Delete local user authentication table entry by ip-address";
     junos:command "request security user-identification local-authentication-table delete ip-address";
     input {
       uses command-forwarding;
       leaf ip-address {
         description "IP address";
         junos:cli-feature "nokeyword";
         type jt:ipaddr;
         mandatory true;
       }
     }
     output {
       choice output_c {
         case output-tag {
           leaf output {
             type string;
           }
         }
         case multichassis-tag {
           anyxml multi-routing-engine-results;
         }
       }
     }
   }
   rpc request-userfw-local-auth-table-delete-user {
     description "Delete local user authentication table entry by user name";
     junos:command "request security user-identification local-authentication-table delete user";
     input {
       uses command-forwarding;
       leaf user-name {
         description "User name";
         junos:cli-feature "nokeyword";
         type string {
           length "1 .. 64";
         }
         mandatory true;
       }
     }
     output {
       choice output_c {
         case output-tag {
           leaf output {
             type string;
           }
         }
         case multichassis-tag {
           anyxml multi-routing-engine-results;
         }
       }
     }
   }
   rpc revert-redundancy-interface-to-primary {
     description "Revert redundancy interface to its primary";
     junos:command "request interface revert";
     input {
       leaf interface-name {
         description "Name of interface";
         junos:cli-feature "nokeyword";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc switch-redundancy-interface-to-secondary {
     description "Switch redundancy interface over to its secondary";
     junos:command "request interface switchover";
     input {
       leaf interface-name {
         description "Name of interface";
         junos:cli-feature "nokeyword";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-switch-anchor {
     description "Manually switch the anchoring device.";
     junos:command "request interface switch-anchor";
     input {
       leaf anchoring-device-name {
         description "Anchoring PFE or FPC name.";
         junos:cli-feature "nokeyword";
         type string {
           junos:posix-pattern "^((pfe-)|(fpc-))";
           junos:pattern-message "Invalid anchoring interface or FPC name.";
         }
       }
     }
     output {
       choice output_c {
         case output-tag {
           leaf output {
             type string;
           }
         }
         case multichassis-tag {
           anyxml multi-routing-engine-results;
         }
       }
     }
   }
   rpc request-intf-modem-reset {
     description "Reset the modem device";
     junos:command "request interface modem reset";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc request-load-balancing-revert {
     description "Revert load-balancing member interface";
     junos:command "request interface load-balancing revert";
     input {
       leaf interface-name {
         description "Name of member-interface";
         junos:cli-feature "nokeyword";
         type union {
           type jt:interface-wildcard;
           type string {
             pattern "<.*>|$.*";
           }
         }
         mandatory true;
       }
     }
   }
   rpc request-load-balancing-switchover {
     description "Switch load-balancing member interface to backup";
     junos:command "request interface load-balancing switchover";
     input {
       leaf interface-name {
         description "Name of member interface";
         junos:cli-feature "nokeyword";
         type union {
           type jt:interface-wildcard;
           type string {
             pattern "<.*>|$.*";
           }
         }
         mandatory true;
       }
       leaf force {
         description "Force a active member switchover";
         type empty;
       }
     }
     output {
       leaf rdd-action-result {
         type string;
       }
     }
   }
   rpc request-interface-mcae-switchover {
     description "Request MC-AE mastership switchover";
     junos:command "request interface mc-ae switchover";
     input {
       leaf mcae-id {
         description "MC-AE id";
         type union {
           type uint16;
           type string {
             pattern "<.*>|$.*";
           }
         }
         mandatory true;
       }
     }
   }
   rpc request-interface-mcae-switchover-immediate {
     description "Request MC-AE mastership switchover immediate";
     junos:command "request interface mc-ae switchover immediate";
     input {
       leaf mcae-id {
         description "MC-AE id";
         type union {
           type uint16;
           type string {
             pattern "<.*>|$.*";
           }
         }
         mandatory true;
       }
     }
   }
   rpc request-interface-link-degade-recover {
     description "Perform manual link recovery";
     junos:command "request interface link-degrade-recover";
     input {
       leaf interface-name {
         description "Name of interface";
         junos:cli-feature "nokeyword";
         type union {
           type jt:interface-device;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-interface-optics-reset {
     description "Perform manual optics-reset";
     junos:command "request interface optics-reset";
     input {
       leaf transceiver-name {
         description "Transceiver name";
         junos:cli-feature "nokeyword";
         type string {
           junos:posix-pattern "^(xcvr|et)-[0-9]+/[0-9]+/[0-9]+$|et-[0-9]+/[0-9]+/[0-9]+:[0-9]+$";
           junos:pattern-message "Only transceiver name supported (xcvr-<fpc slot>/<pic slot>/<port number>)";
         }
         mandatory true;
       }
     }
     output {
       choice output_c {
         case output-tag {
           leaf output {
             type string;
           }
         }
         case multichassis-tag {
           anyxml multi-routing-engine-results;
         }
       }
     }
   }
   rpc request-bounce-interface {
     description "Bounce the port";
     junos:command "request interface bounce";
     input {
       leaf interface-name {
         description "Name of the interface";
         junos:cli-feature "nokeyword";
         type string;
         mandatory true;
       }
       leaf op {
         junos:cli-feature "nokeyword";
         type enumeration {
           enum "remote-only" {
             description "Bounce only the remote end";
           }
         }
       }
       leaf interval {
         description "Interval (in secs) between DOWN and UP";
         type union {
           type string {
             pattern "<.*>|$.*";
           }
           type uint32 {
             range "1 .. 30";
           }
         }
       }
     }
     output {
       container bounce-interface {
         uses bounce-interface-block;
       }
     }
   }
   rpc request-interface-bounce-poe {
     description "Bounce PoE on the given interface";
     junos:command "request interface bounce poe";
     input {
       leaf interface-name {
         description "Name of interface";
         junos:cli-feature "nokeyword";
         type union {
           type jt:interface-device;
           type string {
             pattern "<.*>|$.*";
           }
         }
         mandatory true;
       }
       leaf interval {
         description "Interval (in seconds) between PoE DOWN and UP";
         type union {
           type string {
             pattern "<.*>|$.*";
           }
           type uint32 {
             range "1 .. 60";
           }
         }
       }
     }
     output {
       choice output_c {
         case output-tag {
           leaf output {
             type string;
           }
         }
         case multichassis-tag {
           anyxml multi-routing-engine-results;
         }
       }
     }
   }
   rpc request-rebalance-interface {
     description "Request rebalance of interfaces on the interface";
     junos:command "request interface rebalance";
     input {
       leaf interface-name {
         description "Name of the interface";
         junos:cli-feature "nokeyword";
         type string;
         mandatory true;
       }
     }
     output {
       container rebalance-interface {
         uses rebalance-interface-block;
       }
     }
   }
   rpc extension-service-start {
     description "Start JET application";
     junos:command "request extension-service start";
     input {
       leaf invoke-debugger {
         description "Invoke extension-service in debugger mode";
         type enumeration {
           enum "cli" {
             description "Invoke debugger in cli";
           }
         }
       }
       leaf application-name {
         description "Application name";
         junos:cli-feature "nokeyword";
         type jt:filename;
         mandatory true;
       }
     }
     output {
       choice output_c {
         case output-tag {
           leaf output {
             type string;
           }
         }
         case multichassis-tag {
           anyxml multi-routing-engine-results;
         }
       }
     }
   }
   rpc extension-service-stop {
     description "Stop JET application";
     junos:command "request extension-service stop";
     input {
       leaf application-name {
         description "Application name";
         junos:cli-feature "nokeyword";
         type jt:filename;
         mandatory true;
       }
     }
     output {
       choice output_c {
         case output-tag {
           leaf output {
             type string;
           }
         }
         case multichassis-tag {
           anyxml multi-routing-engine-results;
         }
       }
     }
   }
   rpc extension-service-restart {
     description "Restart JET application";
     junos:command "request extension-service restart";
     input {
       leaf application-name {
         description "Application name";
         junos:cli-feature "nokeyword";
         type jt:filename;
         mandatory true;
       }
     }
     output {
       choice output_c {
         case output-tag {
           leaf output {
             type string;
           }
         }
         case multichassis-tag {
           anyxml multi-routing-engine-results;
         }
       }
     }
   }
   rpc extension-service-daemonize-restart {
     description "Restart daemonize JET application";
     junos:command "request extension-service restart-daemonize-app";
     input {
       leaf application-name {
         description "Application name";
         junos:cli-feature "nokeyword";
         type jt:filename;
         mandatory true;
       }
     }
     output {
       container extension-service-daemonize-restart-status {
         uses extension-service-daemonize-restart-status-block;
       }
     }
   }
   rpc get-csds-information {
     description "Perform one-way key exchange to host";
     junos:command "request csds authenticate-host";
     input {
       leaf csds-instance-id {
         description "CSDS Instance ID";
         type union {
           type int32;
           type string {
             pattern "<.*>|$.*";
           }
         }
       }
     }
     output {
       choice output_c {
         case output-tag {
           leaf output {
             type string;
           }
         }
         case multichassis-tag {
           anyxml multi-routing-engine-results;
         }
       }
     }
   }
   rpc request-csds-jdm-package-add {
     description "Install fresh JDM package or upgrade package";
     junos:command "request csds jdm add";
     input {
       leaf csds-instance-id {
         description "CSDS host Instance ID";
         type union {
           type int32;
           type string {
             pattern "<.*>|$.*";
           }
         }
         mandatory true;
       }
       leaf image {
         description "JDM package name";
         type jt:filename;
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-jdm-package-delete {
     description "Remove currently installed JDM package";
     junos:command "request csds jdm delete";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-vsrx-package-add {
     description "Add VSRX package to JDM";
     junos:command "request csds add-vsrx";
     input {
       leaf csds-instance-id {
         description "CSDS Instance ID";
         type union {
           type int32;
           type string {
             pattern "<.*>|$.*";
           }
         }
         mandatory true;
       }
       leaf image {
         description "VSRX package name";
         type jt:filename;
         mandatory true;
       }
     }
     output {
       choice output_c {
         case output-tag {
           leaf output {
             type string;
           }
         }
         case multichassis-tag {
           anyxml multi-routing-engine-results;
         }
       }
     }
   }
   rpc request-csds-vsrx-package-delete {
     description "Remove currently running VNFs";
     junos:command "request csds delete-vsrx";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-extract-vsrx-keys {
     description "Extract keys from VSRX's devices";
     junos:command "request csds extract-vsrx-keys";
     input {
       leaf csds-instance-id {
         description "CSDS Instance ID";
         type union {
           type int32;
           type string {
             pattern "<.*>|$.*";
           }
         }
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc request-csds-sync-controller-keys {
     description "Sync other controller";
     junos:command "request csds sync-controller";
     input {
       leaf other-controller-ip {
         description "Primary controller IP";
         type jt:ipaddr;
         mandatory true;
       }
       leaf force {
         description "Perform operation by discarding any uncommitted changes";
         type empty;
       }
     }
     output {
       choice output_c {
         case output-tag {
           leaf output {
             type string;
           }
         }
         case multichassis-tag {
           anyxml multi-routing-engine-results;
         }
       }
     }
   }
   rpc mgd-jnu-role {
     description "JNU Role";
     junos:command "request jnu role";
     input {
       uses command-forwarding;
       leaf jnu-role {
         junos:cli-feature "nokeyword";
         type enumeration {
           enum "controller" {
             description "Controller";
           }
         }
         mandatory true;
       }
       leaf delete {
         description "Delete JNU";
         type empty;
       }
     }
     output {
       choice output_c {
         case output-tag {
           leaf output {
             type string;
           }
         }
         case multichassis-tag {
           anyxml multi-routing-engine-results;
         }
       }
     }
   }
   rpc mgd-jnu-schema-delete {
     description "Delete a JNU satellite schema";
     junos:command "request jnu schema delete";
     input {
       leaf model {
         description "Satellite model";
         type string;
         mandatory true;
       }
       leaf version {
         description "Satellite version";
         type string {
           junos:posix-pattern "^[[:digit:]][[:alnum:]_.-]+$";
           junos:pattern-message "Version should begin with a number";
         }
         mandatory true;
       }
     }
     output {
       choice output_c {
         case output-tag {
           leaf output {
             type string;
           }
         }
         case multichassis-tag {
           anyxml multi-routing-engine-results;
         }
       }
     }
   }
   rpc mgd-jnu-schema-add {
     description "Add JNU schema to this controller";
     junos:command "request jnu schema add";
     input {
       leaf model {
         description "Satellite model";
         type string;
         mandatory true;
       }
       leaf version {
         description "Satellite version";
         type string {
           junos:posix-pattern "^[[:digit:]][[:alnum:]_.-]+$";
           junos:pattern-message "Version should begin with a number";
         }
         mandatory true;
       }
       leaf filename {
         description "Satellite schema TLV package filename";
         junos:cli-feature "nokeyword";
         type jt:filename;
         mandatory true;
       }
       leaf model-id {
         description "Satellite model id";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc request-jnu-satellite-sync {
     description "Sync satellite with controller";
     junos:command "request jnu satellite sync";
     output {
       choice output_c {
         case output-tag {
           leaf output {
             type string;
           }
         }
         case multichassis-tag {
           anyxml multi-routing-engine-results;
         }
       }
     }
   }
   rpc clear-jdaf-command-client-stats {
     description "Clear JDAF client side statistics";
     junos:command "request jdaf clear statistics service cmd client";
     output {
       container jdaf-request-no-response {
         uses jdaf-request-no-response-block;
       }
     }
   }
   rpc clear-jdaf-command-server-stats {
     description "Clear JDAF server statistics";
     junos:command "request jdaf clear statistics service cmd server";
     output {
       choice output_c {
         case output-tag {
           leaf output {
             type string;
           }
         }
         case multichassis-tag {
           anyxml multi-routing-engine-results;
         }
       }
     }
   }
   rpc clear-jdaf-config-client-stats {
     description "Clear JDAF client side statistics";
     junos:command "request jdaf clear statistics service config client";
     output {
       container jdaf-request-no-response {
         uses jdaf-request-no-response-block;
       }
     }
   }
   rpc clear-jdaf-config-server-stats {
     description "Clear JDAF server statistics";
     junos:command "request jdaf clear statistics service config server";
     output {
       choice output_c {
         case output-tag {
           leaf output {
             type string;
           }
         }
         case multichassis-tag {
           anyxml multi-routing-engine-results;
         }
       }
     }
   }
   rpc clear-jdaf-firewall-client-stats {
     description "Clear JDAF client side statistics";
     junos:command "request jdaf clear statistics service firewall client";
     input {
       leaf client-id {
         description "Client id";
         junos:cli-feature "nokeyword";
         default "0";
         type union {
           type uint32;
           type string {
             pattern "<.*>|$.*";
           }
         }
       }
     }
     output {
       container jdaf-request-no-response {
         uses jdaf-request-no-response-block;
       }
     }
   }
   rpc clear-jdaf-firewall-server-stats {
     description "Clear JDAF server statistics";
     junos:command "request jdaf clear statistics service firewall server";
     output {
       choice output_c {
         case output-tag {
           leaf output {
             type string;
           }
         }
         case multichassis-tag {
           anyxml multi-routing-engine-results;
         }
       }
     }
   }
   rpc clear-jdaf-interface-client-stats {
     description "Clear JDAF client side statistics";
     junos:command "request jdaf clear statistics service interface client";
     input {
       leaf client-id {
         description "Client id";
         junos:cli-feature "nokeyword";
         default "0";
         type union {
           type uint32;
           type string {
             pattern "<.*>|$.*";
           }
         }
       }
     }
     output {
       container jdaf-request-no-response {
         uses jdaf-request-no-response-block;
       }
     }
   }
   rpc clear-jdaf-interface-server-stats {
     description "Clear JDAF server statistics";
     junos:command "request jdaf clear statistics service interface server";
     output {
       choice output_c {
         case output-tag {
           leaf output {
             type string;
           }
         }
         case multichassis-tag {
           anyxml multi-routing-engine-results;
         }
       }
     }
   }
   rpc clear-jdaf-route-client-stats {
     description "Clear JDAF client side statistics";
     junos:command "request jdaf clear statistics service route client";
     input {
       leaf client-id {
         description "Client id";
         junos:cli-feature "nokeyword";
         default "0";
         type union {
           type uint32;
           type string {
             pattern "<.*>|$.*";
           }
         }
       }
     }
     output {
       container jdaf-request-no-response {
         uses jdaf-request-no-response-block;
       }
     }
   }
   rpc clear-jdaf-route-server-stats {
     description "Clear JDAF server statistics";
     junos:command "request jdaf clear statistics service route server";
     output {
       choice output_c {
         case output-tag {
           leaf output {
             type string;
           }
         }
         case multichassis-tag {
           anyxml multi-routing-engine-results;
         }
       }
     }
   }
   rpc request-dhcp-server-reconfigure-information {
     description "Perform DHCP server reconfigure operation";
     junos:command "request dhcp server reconfigure";
     input {
       choice reconfigure-choice {
         case address {
           leaf address {
             description "IP address or MAC address or Session Id of DHCP client binding";
             junos:cli-feature "nokeyword";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-server-reconfigure-interface {
     description "Name of interface";
     junos:command "request dhcp server reconfigure interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc request-dhcp-server-regenerate-persistent-file {
     description "Triggers the flat file backup operation";
     junos:command "request dhcp server regenerate-persistent-storage";
     output {
       choice output_c {
         case output-tag {
           leaf output {
             type string;
           }
         }
         case multichassis-tag {
           anyxml multi-routing-engine-results;
         }
       }
     }
   }
   rpc request-dhcp-server-restore-client-from-file {
     description "Triggers the flat file restore operation";
     junos:command "request dhcp server restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-client-renew-information {
     description "Request DHCP client renew";
     junos:command "request dhcp client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf tenant {
         description "Name of tenant";
         type string {
           junos:posix-pattern "^[a-zA-Z0-9-]{1,63}$";
           junos:pattern-message "Tenant name is a string consisting of up to 63 letters, numbers and dashes";
         }
       }
     }
     output {
       choice output_c {
         case output-tag {
           leaf output {
             type string;
           }
         }
         case multichassis-tag {
           anyxml multi-routing-engine-results;
         }
       }
     }
   }
   rpc request-dhcp-relay-leasequery {
     description "Perform DHCP relay leasequery operation";
     junos:command "request dhcp relay leasequery";
     input {
       leaf address {
         description "Query by IPv4 address or mac-address or Client-ID";
         junos:cli-feature "nokeyword";
         type string;
         mandatory true;
       }
       leaf gateway-address {
         description "Giaddr of leasequery packet";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery {
     description "Perform DHCP relay bulk leasequery operation";
     junos:command "request dhcp relay bulk-leasequery";
     input {
       leaf address {
         description "Query by IPv4 address or mac-address or Client-ID";
         junos:cli-feature "nokeyword";
         type string;
       }
       choice query-server {
         case server-address {
           leaf server-address {
             description "Send leasequery to server address";
             type string;
           }
         }
         case server-group {
           leaf server-group {
             description "Send leasequery to servers in server-group";
             type string;
           }
         }
       }
       leaf all-configured-ip {
         description "Query by all-configure-ip-addresss";
         type empty;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery-relay-id {
     description "Query by relay-id";
     junos:command "request dhcp relay bulk-leasequery relay-id";
     input {
       leaf relay-id {
         description "Query by relay-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery-remote-id {
     description "Query by remote-id";
     junos:command "request dhcp relay bulk-leasequery remote-id";
     input {
       leaf remote-id {
         description "Query by remote-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-active-leasequery {
     description "Request DHCP active-leasequery operations";
     junos:command "request dhcp relay active-leasequery";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-alq-peer {
     description "Active-leasequery peer";
     junos:command "request dhcp relay active-leasequery restart peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-alq-interface {
     description "Active-leasequery interface";
     junos:command "request dhcp relay active-leasequery restart interface";
     input {
       leaf interface-name {
         description "Active-leasequery interface name";
         junos:cli-feature "nokeyword";
         type string;
         mandatory true;
       }
     }
     output {
       choice output_c {
         case output-tag {
           leaf output {
             type string;
           }
         }
         case multichassis-tag {
           anyxml multi-routing-engine-results;
         }
       }
     }
   }
   rpc request-dhcp-relay-regenerate-persistent-file {
     description "Triggers the flat file backup operation";
     junos:command "request dhcp relay regenerate-persistent-storage";
     output {
       choice output_c {
         case output-tag {
           leaf output {
             type string;
           }
         }
         case multichassis-tag {
           anyxml multi-routing-engine-results;
         }
       }
     }
   }
   rpc request-dhcp-relay-restore-client-from-file {
     description "Triggers the flat file restore operation";
     junos:command "request dhcp relay restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-regenerate-persistent-file {
     description "Triggers the flat file backup operation";
     junos:command "request dhcp regenerate-persistent-storage";
     output {
       choice output_c {
         case output-tag {
           leaf output {
             type string;
           }
         }
         case multichassis-tag {
           anyxml multi-routing-engine-results;
         }
       }
     }
   }
   rpc request-dhcp-restore-client-from-file {
     description "Triggers the flat file restore operation";
     junos:command "request dhcp restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-client-renew-information {
     description "Request DHCP client renew";
     junos:command "request dhcpv6 client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf tenant {
         description "Name of tenant";
         type string {
           junos:posix-pattern "^[a-zA-Z0-9-]{1,63}$";
           junos:pattern-message "Tenant name is a string consisting of up to 63 letters, numbers and dashes";
         }
       }
     }
     output {
       choice output_c {
         case output-tag {
           leaf output {
             type string;
           }
         }
         case multichassis-tag {
           anyxml multi-routing-engine-results;
         }
       }
     }
   }
   rpc request-dhcpv6-server-reconfigure-information {
     description "Perform DHCPv6 server reconfigure operation";
     junos:command "request dhcpv6 server reconfigure";
     input {
       choice reconfigure-choice {
         case address {
           leaf address {
             description "IPv6 Prefix, session-id or CID of DHCPv6 client binding";
             junos:cli-feature "nokeyword";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-server-reconfigure-interface {
     description "Name of interface";
     junos:command "request dhcpv6 server reconfigure interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc request-dhcpv6-server-regenerate-persistent-file {
     description "Triggers the flat file backup operation";
     junos:command "request dhcpv6 server regenerate-persistent-storage";
     output {
       choice output_c {
         case output-tag {
           leaf output {
             type string;
           }
         }
         case multichassis-tag {
           anyxml multi-routing-engine-results;
         }
       }
     }
   }
   rpc request-dhcpv6-server-restore-client-from-file {
     description "Triggers the flat file restore operation";
     junos:command "request dhcpv6 server restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-leasequery {
     description "Perform DHCPv6 relay leasequery operation";
     junos:command "request dhcpv6 relay leasequery";
     input {
       leaf address {
         description "Query by IPv6 Prefix or CID of DHCPv6 client binding";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery {
     description "Perform DHCPv6 relay bulk leasequery operation";
     junos:command "request dhcpv6 relay bulk-leasequery";
     input {
       leaf address {
         description "Query by IPv6 Prefix or CID of DHCPv6 client binding";
         junos:cli-feature "nokeyword";
         type string;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-relay-id {
     description "Query by relay-id";
     junos:command "request dhcpv6 relay bulk-leasequery relay-id";
     input {
       leaf relay-id {
         description "Query by relay-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-link-addr {
     description "Query by link-address";
     junos:command "request dhcpv6 relay bulk-leasequery link-addr";
     input {
       leaf link-addr {
         description "Query by link-address";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-remote-id {
     description "Query by remote-id";
     junos:command "request dhcpv6 relay bulk-leasequery remote-id";
     input {
       leaf remote-id {
         description "Query by remote-id";
         junos:cli-feature "nokeyword";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-regenerate-persistent-file {
     description "Triggers the flat file backup operation";
     junos:command "request dhcpv6 relay regenerate-persistent-storage";
     output {
       choice output_c {
         case output-tag {
           leaf output {
             type string;
           }
         }
         case multichassis-tag {
           anyxml multi-routing-engine-results;
         }
       }
     }
   }
   rpc request-dhcpv6-relay-restore-client-from-file {
     description "Triggers the flat file restore operation";
     junos:command "request dhcpv6 relay restore-persistent-clients";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-active-leasequery {
     description "Request DHCP active-leasequery operations";
     junos:command "request dhcpv6 relay active-leasequery";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-alq-peer {
     description "Active-leasequery peer";
     junos:command "request dhcpv6 relay active-leasequery restart peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-alq-interface {
     description "Active-leasequery interface";
     junos:command "request dhcpv6 relay active-leasequery restart interface";
     input {
       leaf interface-name {
         description "Active-leasequery interface name";
         junos:cli-feature "nokeyword";
         type string;
         mandatory true;
       }
     }
     output {
       choice output_c {
         case output-tag {
           leaf output {
             type string;
           }
         }
         case multichassis-tag {
           anyxml multi-routing-engine-results;
         }
       }
     }
   }
   rpc request-as-ra-guard-forward-interface {
     description "Name of interface";
     junos:command "request access-security router-advertisement-guard-forward interface";
     input {
       leaf interface-name {
         description "Name of interface";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-block-interface {
     description "Name of interface";
     junos:command "request access-security router-advertisement-guard-block interface";
     input {
       leaf interface-name {
         description "Name of interface";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-learn-interface {
     description "RA Guard Learn on an Interface";
     junos:command "request access-security router-advertisement-guard-learn interface";
     input {
       leaf interface {
         description "RA Guard Learn on an interface";
         junos:cli-feature "nokeyword";
         type union {
           type jt:interface-name;
           type string {
             pattern "<.*>|$.*";
           }
         }
         mandatory true;
       }
       leaf duration {
         description "Time window for RA Guard learn";
         units "seconds";
         type union {
           type string {
             pattern "<.*>|$.*";
           }
           type uint32 {
             range "1 .. 3600";
           }
         }
         mandatory true;
       }
     }
     output {
       choice output_c {
         case output-tag {
           leaf output {
             type string;
           }
         }
         case multichassis-tag {
           anyxml multi-routing-engine-results;
         }
       }
     }
   }
   rpc request-slaac-unblock-all {
     description "Unblock all interfaces";
     junos:command "request access-security slaac-snooping unblock all";
     output {
       choice output_c {
         case output-tag {
           leaf output {
             type string;
           }
         }
         case multichassis-tag {
           anyxml multi-routing-engine-results;
         }
       }
     }
   }
   rpc request-slaac-unblock-interface {
     description "Name of interface to unblock";
     junos:command "request access-security slaac-snooping unblock interface";
     input {
       leaf interface-name {
         description "Interface-name";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-static-subscribers-login {
     description "Login static subscribers";
     junos:command "request services static-subscribers login";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
     output {
       container static-subscribers-information {
         uses static-subscribers-information-block;
       }
     }
   }
   rpc request-static-subscribers-logout {
     description "Logout static subscribers";
     junos:command "request services static-subscribers logout";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
     output {
       container static-subscribers-information {
         uses static-subscribers-information-block;
       }
     }
   }
   rpc request-services-flow-collector-test-file-transfer {
     description "Transfer a test file to the current primary server";
     junos:command "request services flow-collector test-file-transfer";
     input {
       leaf filename {
         description "Specify the filename to use";
         junos:cli-feature "nokeyword";
         type string;
         mandatory true;
       }
       leaf channel {
         description "File transfer channel to use";
         junos:cli-feature "nokeyword";
         type enumeration {
           enum "channel-zero" {
             description "Channel 0";
           }
           enum "channel-one" {
             description "Channel 1";
           }
         }
       }
       leaf destination-type {
         junos:cli-feature "nokeyword";
         type enumeration {
           enum "primary" {
             description "Primary server";
           }
           enum "secondary" {
             description "Secondary server";
           }
         }
       }
       leaf interface {
         description "Interface name";
         type string;
         mandatory true;
       }
     }
   }
   rpc request-services-flow-collector-destination {
     description "Change to Destination server";
     junos:command "request services flow-collector change-destination";
     input {
       leaf destination-type {
         description "Destination server";
         junos:cli-feature "nokeyword";
         type enumeration {
           enum "primary" {
             description "Primary server";
           }
           enum "secondary" {
             description "Secondary server";
           }
         }
         mandatory true;
       }
       leaf interface {
         description "Physical interface";
         type union {
           type jt:interface-device;
           type string {
             pattern "<.*>|$.*";
           }
         }
         mandatory true;
       }
       leaf clear-files {
         description "Remove existing files";
         type empty;
       }
       leaf clear-logs {
         description "Remove existing logs";
         type empty;
       }
       leaf how-to-switch {
         description "Options when switching destination";
         junos:cli-feature "nokeyword";
         default "gracefully";
         type enumeration {
           enum "gracefully" {
             description "Retain existing FTP connections";
           }
           enum "immediately" {
             description "Terminate existing FTP connections";
           }
         }
       }
     }
   }
   rpc request-extensible-subscriber-services-reload-dictionary {
     description "Reload dictionary";
     junos:command "request services extensible-subscriber-services reload-dictionary";
     output {
       container extensible-subscriber-services-information {
         uses extensible-subscriber-services-information-block;
       }
     }
   }
   rpc request-appid-protocol-bundle-load {
     description "Load a QM protocols bundle dynamically";
     junos:command "request services application-identification load";
     input {
       uses command-forwarding;
       leaf proto_bundle {
         description "Protocol Bundle file name";
         type string;
       }
     }
     output {
       container request-appid-protocol-bundle-load {
         uses request-appid-protocol-bundle-load-block;
       }
     }
   }
   rpc request-appid-protocol-bundle-unload {
     description "UnLoad a QM protocols bundle dynamically";
     junos:command "request services application-identification unload";
     input {
       uses command-forwarding;
       leaf proto_bundle {
         description "Protocol Bundle file name";
         type string;
       }
     }
     output {
       container request-appid-protocol-bundle-unload {
         uses request-appid-protocol-bundle-unload-block;
       }
     }
   }
   rpc request-appid-application-package-download {
     description "Download application package";
     junos:command "request services application-identification download";
   }
   rpc request-appid-application-package-download-version {
     description "Version of application package to download";
     junos:command "request services application-identification download version";
     input {
       leaf version-value {
         description "Version number";
         junos:cli-feature "nokeyword";
         type union {
           type uint32;
           type string {
             pattern "<.*>|$.*";
           }
         }
         mandatory true;
       }
     }
   }
   rpc request-appid-application-package-download-status {
     description "Display download status";
     junos:command "request services application-identification download status";
   }
   rpc request-appid-application-package-download-check-server {
     description "Retrieve version information for latest package on server";
     junos:command "request services application-identification download check-server";
   }
   rpc request-appid-application-package-download-minor {
     description "Download only the minor application package";
     junos:command "request services application-identification download minor-only";
   }
   rpc request-appid-application-package-install {
     description "Install application package";
     junos:command "request services application-identification install";
     input {
       uses command-forwarding;
     }
   }
   rpc request-appid-application-package-install-status {
     description "Display install status";
     junos:command "request services application-identification install status";
     input {
       uses command-forwarding;
     }
   }
   rpc request-appid-force-install {
     description "Ignore version check during sigpack installation (applicable for offline-download only)";
     junos:command "request services application-identification install ignore-duplicate-version-check";
     input {
       uses command-forwarding;
     }
   }
   rpc request-appid-sigpack-rollback {
     description "Rollback application package";
     junos:command "request services application-identification rollback";
     input {
       uses command-forwarding;
     }
   }
   rpc request-appid-sigpack-rollback-status {
     description "Display rollback status";
     junos:command "request services application-identification rollback status";
     input {
       uses command-forwarding;
     }
   }
   rpc request-appid-application-package-uninstall {
     description "Uninstall predefined application package";
     junos:command "request services application-identification uninstall";
     input {
       uses command-forwarding;
     }
   }
   rpc request-appid-application-package-uninstall-status {
     description "Display uninstall status";
     junos:command "request services application-identification uninstall status";
     input {
       uses command-forwarding;
     }
   }
   rpc request-appid-sigpack-offline-download {
     description "Application signature package offline download";
     junos:command "request services application-identification offline-download";
     input {
       leaf package-path {
         description "Package path of the zipped security package";
         type string;
       }
     }
     output {
       container apppack-offline-download-status {
         uses apppack-offline-download-status-block;
       }
     }
   }
   rpc request-appid-sigpack-offline-download-status {
     description "Display offline download status";
     junos:command "request services application-identification offline-download status";
     output {
       container apppack-offline-download-status {
         uses apppack-offline-download-status-block;
       }
     }
   }
   rpc request-appid-application-predefined-disable {
     description "Disable a predefined application";
     junos:command "request services application-identification application disable";
     input {
       uses command-forwarding;
       leaf application-name {
         description "Predefined application name";
         junos:cli-feature "nokeyword";
         type string;
         mandatory true;
       }
       leaf no-commit {
         description "Do not re-compile signatures";
         status deprecated;
         type empty;
       }
     }
   }
   rpc request-appid-application-predefined-enable {
     description "Enable a predefined application";
     junos:command "request services application-identification application enable";
     input {
       uses command-forwarding;
       leaf application-name {
         description "Predefined application name";
         junos:cli-feature "nokeyword";
         type string;
         mandatory true;
       }
       leaf no-commit {
         description "Do not re-compile signatures";
         status deprecated;
         type empty;
       }
     }
   }
   rpc request-appid-application-predefined-group-copy {
     description "Copy a predefined application group into junos configuration";
     junos:command "request services application-identification group copy";
     input {
       uses command-forwarding;
       leaf group-name {
         description "Predefined application group name";
         junos:cli-feature "nokeyword";
         type string;
         mandatory true;
       }
     }
   }
   rpc request-appid-application-predefined-group-disable {
     description "Disable a predefined application group";
     junos:command "request services application-identification group disable";
     input {
       uses command-forwarding;
       leaf group-name {
         description "Predefined application group name";
         junos:cli-feature "nokeyword";
         type string;
         mandatory true;
       }
     }
   }
   rpc request-appid-application-predefined-group-enable {
     description "Enable a predefined application group";
     junos:command "request services application-identification group enable";
     input {
       uses command-forwarding;
       leaf group-name {
         description "Predefined application group name";
         junos:cli-feature "nokeyword";
         type string;
         mandatory true;
       }
     }
   }
   rpc request-appid-clear-pkt-capture {
     description "Clear";
     junos:command "request services application-identification clear";
     input {
       leaf packet-capture {
         description "Clear the pcap files";
         type enumeration {
           enum "all" {
             description "Clear all files";
           }
         }
         mandatory true;
       }
     }
     output {
       container clear-appid-pkt-capture-counter-information {
         uses clear-appid-pkt-capture-counter-information-block;
       }
     }
   }
   rpc request-appid-new-to-production {
     description "To move new apps to production apps";
     junos:command "request services application-identification new-to-production";
     input {
       uses command-forwarding;
       choice application-choice {
         case all {
           leaf all {
             description "Move all new apps to production";
             type empty;
           }
         }
         case applications-list {
           leaf-list applications-list {
             ordered-by user;
             description "List of new applications";
             type string;
           }
         }
       }
     }
     output {
       container request-predefined-operation-status {
         uses request-predefined-operation-status-block;
       }
     }
   }
   rpc get-manual-session-query {
     description "Manual session query";
     junos:command "request services user-identification identity-management session-query";
   }
   rpc get-manual-session-query-session-id {
     description "Specified session-id for session query";
     junos:command "request services user-identification identity-management session-query session-id";
     input {
       uses command-forwarding;
       leaf cookie {
         description "Session cookie for manual query";
         junos:cli-feature "nokeyword";
         type string {
           length "1 .. 65";
         }
         mandatory true;
       }
       leaf query-type {
         junos:cli-feature "nokeyword";
         type enumeration {
           enum "force-probe" {
             description "Trigger force pc-probe on JIMS";
           }
         }
       }
     }
     output {
       choice output_c {
         case output-tag {
           leaf output {
             type string;
           }
         }
         case multichassis-tag {
           anyxml multi-routing-engine-results;
         }
       }
     }
   }
   rpc manual-session-batch-query {
     description "Manual session batch query";
     junos:command "request services user-identification identity-management session-batch-query";
     output {
       choice output_c {
         case output-tag {
           leaf output {
             type string;
           }
         }
         case multichassis-tag {
           anyxml multi-routing-engine-results;
         }
       }
     }
   }
   rpc manual-ip-query {
     description "Manual IP query";
     junos:command "request services user-identification identity-management ip-query";
   }
   rpc manual-ip-query-address {
     description "Specified address for IP query";
     junos:command "request services user-identification identity-management ip-query address";
     input {
       uses command-forwarding;
       leaf address-string {
         description "IP address for manual query";
         junos:cli-feature "nokeyword";
         type jt:ipaddr;
         mandatory true;
       }
       leaf query-type {
         junos:cli-feature "nokeyword";
         type enumeration {
           enum "force-probe" {
             description "Trigger force pc-probe on JIMS";
           }
         }
       }
     }
     output {
       choice output_c {
         case output-tag {
           leaf output {
             type string;
           }
         }
         case multichassis-tag {
           anyxml multi-routing-engine-results;
         }
       }
     }
   }
   rpc manual-batch-query {
     description "Manual batch query";
     junos:command "request services user-identification identity-management batch-query";
     output {
       choice output_c {
         case output-tag {
           leaf output {
             type string;
           }
         }
         case multichassis-tag {
           anyxml multi-routing-engine-results;
         }
       }
     }
   }
   rpc manual-jims-validator-query {
     description "Manual jims validator query";
     junos:command "request services user-identification identity-management jims-validator-query";
     output {
       choice output_c {
         case output-tag {
           leaf output {
             type string;
           }
         }
         case multichassis-tag {
           anyxml multi-routing-engine-results;
         }
       }
     }
   }
   rpc manual-jims-validator-query-files {
     description "Specified file list seperated with comma";
     junos:command "request services user-identification identity-management jims-validator-query files";
     input {
       uses command-forwarding;
       leaf files_str {
         description "File list for jims validator query";
         junos:cli-feature "nokeyword";
         type string {
           length "1 .. 65";
         }
         mandatory true;
       }
     }
     output {
       choice output_c {
         case output-tag {
           leaf output {
             type string;
           }
         }
         case multichassis-tag {
           anyxml multi-routing-engine-results;
         }
       }
     }
   }
   rpc captive-portal-certificate {
     description "Captive portal certificate";
     junos:command "request services user-identification captive-portal certificate";
   }
   rpc captive-portal-certificate-update {
     description "Update Captive portal certificate";
     junos:command "request services user-identification captive-portal certificate update";
     output {
       choice output_c {
         case output-tag {
           leaf output {
             type string;
           }
         }
         case multichassis-tag {
           anyxml multi-routing-engine-results;
         }
       }
     }
   }
   rpc groupname-to-id {
     description "Trigger groupname to id unit test";
     junos:command "request services user-identification fwauth ut groupname-to-id";
     output {
       choice output_c {
         case output-tag {
           leaf output {
             type string;
           }
         }
         case multichassis-tag {
           anyxml multi-routing-engine-results;
         }
       }
     }
   }
   rpc request-auth-table-by-address {
     description "Delete authentication table entry by ip-address";
     junos:command "request services user-identification authentication-table delete ip-address";
     input {
       uses command-forwarding;
       leaf ip-address {
         description "IP address";
         junos:cli-feature "nokeyword";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case multichassis-tag {
           anyxml multi-routing-engine-results;
         }
       }
     }
   }
   rpc request-auth-table-by-session-id {
     description "Delete authentication table entry by session-id";
     junos:command "request services user-identification authentication-table delete session-id";
     input {
       uses command-forwarding;
       leaf session-id {
         description "Session-id";
         junos:cli-feature "nokeyword";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case multichassis-tag {
           anyxml multi-routing-engine-results;
         }
       }
     }
   }
   rpc request-delete-auth-table-all {
     description "Delete the entire authentication table in the userid daemon";
     junos:command "request services user-identification authentication-table delete authentication-source all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc delete-auth-table-by-domain-all {
     description "Delete authentication table entry by domain";
     junos:command "request services user-identification authentication-table delete authentication-source all domain";
     input {
       uses command-forwarding;
       leaf domain {
         description "Delete authentication table per domain";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-authentication-table-delete-group-all {
     description "Delete authentication table entry by group name";
     junos:command "request services user-identification authentication-table delete authentication-source all group";
     input {
       uses command-forwarding;
       leaf group-name {
         description "Group name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per group";
         type string {
           length "1 .. 65";
         }
       }
     }
     output {
       choice output_c {
         case output-tag {
           leaf output {
             type string;
           }
         }
         case multichassis-tag {
           anyxml multi-routing-engine-results;
         }
       }
     }
   }
   rpc request-auth-table-delete-user-all {
     description "Delete authentication table entry by user name";
     junos:command "request services user-identification authentication-table delete authentication-source all user";
     input {
       uses command-forwarding;
       leaf user-name {
         description "User name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per user";
         type string {
           length "1 .. 65";
         }
       }
     }
     output {
       choice output_c {
         case output-tag {
           leaf output {
             type string;
           }
         }
         case multichassis-tag {
           anyxml multi-routing-engine-results;
         }
       }
     }
   }
   rpc request-aruba-clearpass-table-information {
     description "Delete the Authentication table from Aruba ClearPass";
     junos:command "request services user-identification authentication-table delete authentication-source aruba-clearpass";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc delete-auth-table-by-domain-cp {
     description "Delete authentication table entry by domain";
     junos:command "request services user-identification authentication-table delete authentication-source aruba-clearpass domain";
     input {
       uses command-forwarding;
       leaf domain {
         description "Delete authentication table per domain";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-authentication-table-delete-group-cp {
     description "Delete authentication table entry by group name";
     junos:command "request services user-identification authentication-table delete authentication-source aruba-clearpass group";
     input {
       uses command-forwarding;
       leaf group-name {
         description "Group name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per group";
         type string {
           length "1 .. 65";
         }
       }
     }
     output {
       choice output_c {
         case output-tag {
           leaf output {
             type string;
           }
         }
         case multichassis-tag {
           anyxml multi-routing-engine-results;
         }
       }
     }
   }
   rpc request-auth-table-delete-user-cp {
     description "Delete authentication table entry by user name";
     junos:command "request services user-identification authentication-table delete authentication-source aruba-clearpass user";
     input {
       uses command-forwarding;
       leaf user-name {
         description "User name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per user";
         type string {
           length "1 .. 65";
         }
       }
     }
     output {
       choice output_c {
         case output-tag {
           leaf output {
             type string;
           }
         }
         case multichassis-tag {
           anyxml multi-routing-engine-results;
         }
       }
     }
   }
   rpc request-delete-ad-auth-table {
     description "Delete the active directory authentication table";
     junos:command "request services user-identification authentication-table delete authentication-source active-directory";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc delete-auth-table-by-domain-ad {
     description "Delete authentication table entry by domain";
     junos:command "request services user-identification authentication-table delete authentication-source active-directory domain";
     input {
       uses command-forwarding;
       leaf domain {
         description "Delete authentication table per domain";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-authentication-table-delete-group-ad {
     description "Delete authentication table entry by group name";
     junos:command "request services user-identification authentication-table delete authentication-source active-directory group";
     input {
       uses command-forwarding;
       leaf group-name {
         description "Group name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per group";
         type string {
           length "1 .. 65";
         }
       }
     }
     output {
       choice output_c {
         case output-tag {
           leaf output {
             type string;
           }
         }
         case multichassis-tag {
           anyxml multi-routing-engine-results;
         }
       }
     }
   }
   rpc request-auth-table-delete-user-ad {
     description "Delete authentication table entry by user name";
     junos:command "request services user-identification authentication-table delete authentication-source active-directory user";
     input {
       uses command-forwarding;
       leaf user-name {
         description "User name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per user";
         type string {
           length "1 .. 65";
         }
       }
     }
     output {
       choice output_c {
         case output-tag {
           leaf output {
             type string;
           }
         }
         case multichassis-tag {
           anyxml multi-routing-engine-results;
         }
       }
     }
   }
   rpc delete-authentication-table-identity-management {
     description "Identity management server";
     junos:command "request services user-identification authentication-table delete authentication-source identity-management";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc delete-auth-table-by-domain-im {
     description "Delete authentication table entry by domain";
     junos:command "request services user-identification authentication-table delete authentication-source identity-management domain";
     input {
       uses command-forwarding;
       leaf domain {
         description "Delete authentication table per domain";
         junos:cli-feature "nokeyword";
         type string {
           length "1 .. 65";
         }
         mandatory true;
       }
       leaf source-name {
         description "Authentication source name";
         type string {
           length "1 .. 65";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-authentication-table-delete-group-im {
     description "Delete authentication table entry by group name";
     junos:command "request services user-identification authentication-table delete authentication-source identity-management group";
     input {
       uses command-forwarding;
       leaf group-name {
         description "Group name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per group";
         type string {
           length "1 .. 65";
         }
       }
       leaf source-name {
         description "Authentication source name";
         type string {
           length "1 .. 65";
         }
       }
     }
     output {
       choice output_c {
         case output-tag {
           leaf output {
             type string;
           }
         }
         case multichassis-tag {
           anyxml multi-routing-engine-results;
         }
       }
     }
   }
   rpc request-auth-table-delete-user-im {
     description "Delete authentication table entry by user name";
     junos:command "request services user-identification authentication-table delete authentication-source identity-management user";
     input {
       uses command-forwarding;
       leaf user-name {
         description "User name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per user";
         type string {
           length "1 .. 65";
         }
       }
       leaf source-name {
         description "Authentication source name";
         type string {
           length "1 .. 65";
         }
       }
     }
     output {
       choice output_c {
         case output-tag {
           leaf output {
             type string;
           }
         }
         case multichassis-tag {
           anyxml multi-routing-engine-results;
         }
       }
     }
   }
   rpc request-auth-table-delete-source-name-im {
     description "Delete authentication table entry by source name";
     junos:command "request services user-identification authentication-table delete authentication-source identity-management source-name";
     input {
       uses command-forwarding;
       leaf src-name {
         description "Source name";
         junos:cli-feature "nokeyword";
         type string {
           length "1 .. 65";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Delete authentication table per source name";
         type string {
           length "1 .. 65";
         }
       }
     }
   }
   rpc request-domain-controller-list {
     description "Discovery domain-controller";
     junos:command "request services user-identification active-directory-access domain-controller discovery";
     input {
       uses command-forwarding;
       leaf domain {
         description "Show domain-controller status per domain";
         type string {
           length "1 .. 65";
         }
         mandatory true;
       }
     }
     output {
       container domain-controller-status {
         uses domain-controller-status-block;
       }
     }
   }
   rpc probe-specified-address {
     description "Probe specified ip-address";
     junos:command "request services user-identification active-directory-access ip-user-probe";
   }
   rpc probe-pc-by-address {
     description "Request probe specified address";
     junos:command "request services user-identification active-directory-access ip-user-probe address";
     input {
       uses command-forwarding;
       leaf ip-address {
         description "IP address";
         junos:cli-feature "nokeyword";
         type jt:ipaddr;
         mandatory true;
       }
       leaf domain {
         description "Probe PC per domain";
         type string {
           length "1 .. 65";
         }
       }
     }
     output {
       choice output_c {
         case output-tag {
           leaf output {
             type string;
           }
         }
         case multichassis-tag {
           anyxml multi-routing-engine-results;
         }
       }
     }
   }
   rpc delete-active-directory-auth-table-by-domain {
     description "Delete active directory authentication table entry by domain";
     junos:command "request services user-identification active-directory-access active-directory-authentication-table delete domain";
     input {
       uses command-forwarding;
       leaf domain {
         description "Update domain-controller status per domain";
         junos:cli-feature "nokeyword";
         type string {
           length "1 .. 65";
         }
         mandatory true;
       }
     }
   }
   rpc request-active-directory-auth-table-delete-ip {
     description "Delete active directory authentication table entry by ip-address";
     junos:command "request services user-identification active-directory-access active-directory-authentication-table delete ip-address";
     input {
       uses command-forwarding;
       leaf ip-address {
         description "IP address";
         junos:cli-feature "nokeyword";
         type jt:ipaddr;
         mandatory true;
       }
     }
     output {
       choice output_c {
         case output-tag {
           leaf output {
             type string;
           }
         }
         case multichassis-tag {
           anyxml multi-routing-engine-results;
         }
       }
     }
   }
   rpc request-active-directory-auth-table-delete-group {
     description "Delete active directory authentication table entry by group name";
     junos:command "request services user-identification active-directory-access active-directory-authentication-table delete group";
     input {
       uses command-forwarding;
       leaf group-name {
         description "Group name";
         junos:cli-feature "nokeyword";
         type string {
           length "1 .. 65";
         }
         mandatory true;
       }
       leaf domain {
         description "Show active directory authentication table status per domain";
         type string {
           length "1 .. 65";
         }
       }
     }
     output {
       choice output_c {
         case output-tag {
           leaf output {
             type string;
           }
         }
         case multichassis-tag {
           anyxml multi-routing-engine-results;
         }
       }
     }
   }
   rpc request-active-directory-auth-table-delete-user {
     description "Delete active directory authentication table entry by user name";
     junos:command "request services user-identification active-directory-access active-directory-authentication-table delete user";
     input {
       uses command-forwarding;
       leaf user-name {
         description "User name";
         junos:cli-feature "nokeyword";
         type string {
           length "1 .. 65";
         }
         mandatory true;
       }
       leaf domain {
         description "Show active directory authentication table status per domain";
         type string {
           length "1 .. 65";
         }
       }
     }
     output {
       choice output_c {
         case output-tag {
           leaf output {
             type string;
           }
         }
         case multichassis-tag {
           anyxml multi-routing-engine-results;
         }
       }
     }
   }
   rpc remove-ad-ug-mapping-by-domain {
     description "Remove active directory user-group-mapping by domain";
     junos:command "request services user-identification active-directory-access user-group-mapping remove domain";
     input {
       uses command-forwarding;
       leaf domain {
         description "Remove active directory user-group-mapping per domain";
         junos:cli-feature "nokeyword";
         type string {
           length "1 .. 65";
         }
         mandatory true;
       }
       leaf user {
         description "User name";
         type string {
           length "1 .. 65";
         }
         mandatory true;
       }
     }
     output {
       choice output_c {
         case output-tag {
           leaf output {
             type string;
           }
         }
         case multichassis-tag {
           anyxml multi-routing-engine-results;
         }
       }
     }
   }
   rpc fetch-ad-ug-mapping-by-domain {
     description "Fetch active directory user-group-mapping by domain";
     junos:command "request services user-identification active-directory-access user-group-mapping fetch domain";
     input {
       uses command-forwarding;
       leaf domain {
         description "Fetch active directory user-group-mapping per domain";
         junos:cli-feature "nokeyword";
         type string {
           length "1 .. 65";
         }
         mandatory true;
       }
       leaf user {
         description "User name";
         type string {
           length "1 .. 65";
         }
       }
       leaf group {
         description "Group name";
         type string {
           length "1 .. 65";
         }
       }
     }
     output {
       choice output_c {
         case output-tag {
           leaf output {
             type string;
           }
         }
         case multichassis-tag {
           anyxml multi-routing-engine-results;
         }
       }
     }
   }
   rpc refresh-ad-ug-mapping-by-domain {
     description "Refresh active directory user-group-mapping by domain";
     junos:command "request services user-identification active-directory-access user-group-mapping refresh domain";
     input {
       uses command-forwarding;
       leaf domain {
         description "Refresh active directory user-group-mapping per domain";
         junos:cli-feature "nokeyword";
         type string {
           length "1 .. 65";
         }
         mandatory true;
       }
       leaf group {
         description "Group name";
         type string {
           length "1 .. 65";
         }
         mandatory true;
       }
     }
     output {
       choice output_c {
         case output-tag {
           leaf output {
             type string;
           }
         }
         case multichassis-tag {
           anyxml multi-routing-engine-results;
         }
       }
     }
   }
   rpc periodic-fetch-ad-ug-mapping-add {
     description "Add group to periodic user-group-mapping fetching list";
     junos:command "request services user-identification active-directory-access user-group-mapping periodic-fetch add";
     input {
       uses command-forwarding;
       leaf domain {
         description "Periodic fetching active directory user-group-mapping per domain";
         type string {
           length "1 .. 65";
         }
         mandatory true;
       }
       leaf group {
         description "Group name";
         type string {
           length "1 .. 65";
         }
         mandatory true;
       }
     }
     output {
       choice output_c {
         case output-tag {
           leaf output {
             type string;
           }
         }
         case multichassis-tag {
           anyxml multi-routing-engine-results;
         }
       }
     }
   }
   rpc periodic-fetch-ad-ug-mapping-remove {
     description "Remove group from periodic user-group-mapping fetching list";
     junos:command "request services user-identification active-directory-access user-group-mapping periodic-fetch remove";
     input {
       uses command-forwarding;
       leaf domain {
         description "Periodic fetching active directory user-group-mapping per domain";
         type string {
           length "1 .. 65";
         }
         mandatory true;
       }
       leaf group {
         description "Group name";
         type string {
           length "1 .. 65";
         }
         mandatory true;
       }
     }
     output {
       choice output_c {
         case output-tag {
           leaf output {
             type string;
           }
         }
         case multichassis-tag {
           anyxml multi-routing-engine-results;
         }
       }
     }
   }
   rpc periodic-fetch-ad-ug-mapping-timestamp {
     description "Timestamp hh:mm to start user-group-mapping fetching everyday";
     junos:command "request services user-identification active-directory-access user-group-mapping periodic-fetch timestamp";
     input {
       uses command-forwarding;
       leaf timestamp-string {
         description "Timestamp hh:mm to start user-group-mapping fetching everyday";
         junos:cli-feature "nokeyword";
         type string {
           junos:posix-pattern "[0-2][0-9]:[0-5][0-9]";
           junos:pattern-message "Timestamp must be hh:mm";
         }
         mandatory true;
       }
     }
     output {
       choice output_c {
         case output-tag {
           leaf output {
             type string;
           }
         }
         case multichassis-tag {
           anyxml multi-routing-engine-results;
         }
       }
     }
   }
   rpc query-specified-address {
     description "ClearPass user query operations";
     junos:command "request services user-identification authentication-source aruba-clearpass user-query";
   }
   rpc cp-user-query-by-address {
     description "Specified address for user-query";
     junos:command "request services user-identification authentication-source aruba-clearpass user-query address";
     input {
       uses command-forwarding;
       leaf address-string {
         description "IP address for query";
         junos:cli-feature "nokeyword";
         type jt:ipaddr;
         mandatory true;
       }
     }
     output {
       choice output_c {
         case output-tag {
           leaf output {
             type string;
           }
         }
         case multichassis-tag {
           anyxml multi-routing-engine-results;
         }
       }
     }
   }
   rpc get-groups-from-jims {
     description "Get groups from JIMS";
     junos:command "request services user-identification authentication-source jims groups";
     input {
       uses command-forwarding;
       leaf domain {
         description "Domain name";
         type string {
           length "1 .. 65";
         }
         mandatory true;
       }
       leaf force-fetch {
         type empty;
       }
       leaf status {
         type empty;
       }
     }
     output {
       choice output_c {
         case output-tag {
           leaf output {
             type string;
           }
         }
         case multichassis-tag {
           anyxml multi-routing-engine-results;
         }
       }
     }
   }
   rpc validate-device-from-jims {
     description "Validate device";
     junos:command "request services user-identification authentication-source jims validate device";
     input {
       uses command-forwarding;
       leaf device-name {
         description "Device name";
         junos:cli-feature "nokeyword";
         type string {
           length "1 .. 65";
         }
         mandatory true;
       }
       leaf domain {
         description "Domain name";
         type string {
           length "1 .. 65";
         }
         mandatory true;
       }
       leaf force-fetch {
         type empty;
       }
       leaf status {
         type empty;
       }
     }
     output {
       container validate-device-group-user-status {
         uses validate-device-group-user-status-block;
       }
     }
   }
   rpc validate-group-from-jims {
     description "Validate group";
     junos:command "request services user-identification authentication-source jims validate group";
     input {
       uses command-forwarding;
       leaf group-name {
         description "Group name";
         junos:cli-feature "nokeyword";
         type string {
           length "1 .. 65";
         }
         mandatory true;
       }
       leaf domain {
         description "Domain name";
         type string {
           length "1 .. 65";
         }
         mandatory true;
       }
       leaf force-fetch {
         type empty;
       }
       leaf status {
         type empty;
       }
     }
     output {
       container validate-device-group-user-status {
         uses validate-device-group-user-status-block;
       }
     }
   }
   rpc validate-user-from-jims {
     description "Validate user";
     junos:command "request services user-identification authentication-source jims validate user";
     input {
       uses command-forwarding;
       leaf user-name {
         description "User name";
         junos:cli-feature "nokeyword";
         type string {
           length "1 .. 65";
         }
         mandatory true;
       }
       leaf domain {
         description "Domain name";
         type string {
           length "1 .. 65";
         }
         mandatory true;
       }
       leaf force-fetch {
         type empty;
       }
       leaf status {
         type empty;
       }
     }
     output {
       container validate-device-group-user-status {
         uses validate-device-group-user-status-block;
       }
     }
   }
   rpc request-device-identity-table-add {
     description "Add device identity table entry";
     junos:command "request services user-identification device add";
     input {
       uses command-forwarding;
       leaf ip-address {
         description "IP address";
         type jt:ipaddr;
         mandatory true;
       }
       leaf domain {
         description "Domain name";
         type string {
           length "1 .. 65";
         }
       }
       leaf device-id {
         description "Device ID";
         type string {
           length "1 .. 65";
         }
       }
       leaf attributes {
         description "Device attributes";
         type string {
           length "1 .. 257";
         }
       }
       leaf auth-src {
         junos:cli-feature "nokeyword";
         default "cp";
         type enumeration {
           enum "ad" {
             description "AD auth";
           }
           enum "cp" {
             description "CP auth (default)";
           }
         }
       }
     }
     output {
       choice output_c {
         case output-tag {
           leaf output {
             type string;
           }
         }
         case multichassis-tag {
           anyxml multi-routing-engine-results;
         }
       }
     }
   }
   rpc request-device-identity-table-delete {
     description "Delete device identity table entry";
     junos:command "request services user-identification device delete-by-ip";
     input {
       uses command-forwarding;
       leaf ip-address {
         description "IP address";
         type jt:ipaddr;
         mandatory true;
       }
     }
     output {
       choice output_c {
         case output-tag {
           leaf output {
             type string;
           }
         }
         case multichassis-tag {
           anyxml multi-routing-engine-results;
         }
       }
     }
   }
   rpc request-device-identity-table-update {
     description "Update device identity attributes";
     junos:command "request services user-identification device update";
     input {
       uses command-forwarding;
       leaf domain {
         description "Domain name";
         type string {
           length "1 .. 65";
         }
         mandatory true;
       }
       leaf device-id {
         description "Device ID";
         type string {
           length "1 .. 65";
         }
         mandatory true;
       }
       leaf attributes {
         description "Device attributes";
         type string {
           length "1 .. 257";
         }
       }
     }
     output {
       choice output_c {
         case output-tag {
           leaf output {
             type string;
           }
         }
         case multichassis-tag {
           anyxml multi-routing-engine-results;
         }
       }
     }
   }
   rpc request-device-identity-table-remove {
     description "Remove device identity attributes";
     junos:command "request services user-identification device delete-by-deviceid";
     input {
       uses command-forwarding;
       leaf domain {
         description "Domain name";
         type string {
           length "1 .. 65";
         }
         mandatory true;
       }
       leaf device-id {
         description "Device ID";
         type string {
           length "1 .. 65";
         }
         mandatory true;
       }
     }
     output {
       choice output_c {
         case output-tag {
           leaf output {
             type string;
           }
         }
         case multichassis-tag {
           anyxml multi-routing-engine-results;
         }
       }
     }
   }
   rpc request-device-identity-table-change {
     description "Change profile flag";
     junos:command "request services user-identification device change";
     input {
       uses command-forwarding;
     }
     output {
       choice output_c {
         case output-tag {
           leaf output {
             type string;
           }
         }
         case multichassis-tag {
           anyxml multi-routing-engine-results;
         }
       }
     }
   }
   rpc request-device-identity-table-clear {
     description "Clear device db";
     junos:command "request services user-identification device clear";
     input {
       uses command-forwarding;
     }
     output {
       choice output_c {
         case output-tag {
           leaf output {
             type string;
           }
         }
         case multichassis-tag {
           anyxml multi-routing-engine-results;
         }
       }
     }
   }
   rpc request-device-profile-resync {
     description "Request resync end-user-profile information";
     junos:command "request services user-identification device-information end-user-profile resync";
     output {
       choice output_c {
         case output-tag {
           leaf output {
             type string;
           }
         }
         case multichassis-tag {
           anyxml multi-routing-engine-results;
         }
       }
     }
   }
   rpc request-device-profile-jason {
     description "Request resync end-user-profile information";
     junos:command "request services user-identification device-information end-user-profile json-message";
     input {
       leaf message {
         description "Message";
         junos:cli-feature "nokeyword";
         type string;
         mandatory true;
       }
     }
     output {
       choice output_c {
         case output-tag {
           leaf output {
             type string;
           }
         }
         case multichassis-tag {
           anyxml multi-routing-engine-results;
         }
       }
     }
   }
   rpc start-aamw-conn-test {
     description "Start Advanced Anti-malware cloud connectivity test";
     junos:command "request services advanced-anti-malware data-connection test start";
     input {
       uses command-forwarding;
       leaf payload-size {
         description "Ping payload size in bytes";
         junos:cli-feature "nokeyword";
         type union {
           type string {
             pattern "<.*>|$.*";
           }
           type int32 {
             range "0 .. 4096";
           }
         }
         mandatory true;
       }
     }
     output {
       container aamw-start-conn-test {
         uses aamw-start-conn-test-block;
       }
     }
   }
   rpc get-aamw-conn-test-status {
     description "Show Advanced Anti-malware cloud connectivity test status";
     junos:command "request services advanced-anti-malware data-connection test status";
     input {
       uses command-forwarding;
     }
     output {
       container aamw-show-conn-test-status {
         uses aamw-show-conn-test-status-block;
       }
     }
   }
   rpc request-aamw-diagnostics {
     description "Diagnostics for Advanced Anti-malware service";
     junos:command "request services advanced-anti-malware diagnostics";
     input {
       uses command-forwarding;
       leaf url {
         description "SKYATP server hostname";
         junos:cli-feature "nokeyword";
         type string;
       }
       leaf detail {
         junos:cli-feature "nokeyword";
         type enumeration {
           enum "detail" {
             description "Show detail information";
           }
         }
       }
       leaf pre-detection {
         junos:cli-feature "nokeyword";
         type enumeration {
           enum "pre-detection" {
             description "Pre detection for andvance anti-malware service enrollment";
           }
         }
       }
       leaf routing-instance {
         description "Routing instance used in enrollment";
         type string;
       }
     }
   }
   rpc request-aamw-enrollment {
     description "Advanced Anti-malware service enrollment";
     junos:command "request services advanced-anti-malware enroll";
     input {
       leaf url {
         description "URL";
         junos:cli-feature "nokeyword";
         type string;
       }
     }
   }
   rpc request-aamw-disenrollment {
     description "Advanced Anti-malware service disenrollment";
     junos:command "request services advanced-anti-malware disenroll";
     input {
       leaf url {
         description "URL";
         junos:cli-feature "nokeyword";
         type string;
       }
     }
   }
   rpc request-aamw-redirect-add {
     description "Add redirect file";
     junos:command "request services advanced-anti-malware redirect-file add";
     input {
       uses command-forwarding;
       leaf file-name {
         description "Add a redirect file";
         junos:cli-feature "nokeyword";
         type jt:filename;
         mandatory true;
       }
     }
   }
   rpc request-aamw-redirect-delete {
     description "Delete a redirect file";
     junos:command "request services advanced-anti-malware redirect-file delete";
     input {
       uses command-forwarding;
       leaf file-name {
         description "Delete a redirect file";
         junos:cli-feature "nokeyword";
         type jt:filename;
         mandatory true;
       }
     }
   }
   rpc request-anti-virus-update {
     description "Update on anti-virus service";
     junos:command "request services anti-virus update";
     input {
       uses command-forwarding;
     }
   }
   rpc request-anti-virus-update-status {
     description "Request anti-virus update status";
     junos:command "request services anti-virus update status";
     input {
       uses command-forwarding;
     }
   }
   rpc request-anti-virus-update-check-server {
     description "Update on anti-virus update-check-server";
     junos:command "request services anti-virus update-check-server";
     input {
       uses command-forwarding;
     }
   }
   rpc request-anti-virus-machine-learning-eng-status {
     description "Request anti-virus machine-learning-engine status";
     junos:command "request services anti-virus machine-learning-engine status";
     input {
       uses command-forwarding;
     }
     output {
       container aamw-mesg {
         uses aamw-mesg-block;
       }
     }
   }
   rpc request-anti-virus-machine-learning-engine-stop {
     description "Request anti-virus machine-learning-engine stop";
     junos:command "request services anti-virus machine-learning-engine stop";
     input {
       uses command-forwarding;
     }
     output {
       container aamw-mesg {
         uses aamw-mesg-block;
       }
     }
   }
   rpc request-anti-virus-machine-learning-engine-start {
     description "Request anti-virus machine-learning-engine start";
     junos:command "request services anti-virus machine-learning-engine start";
     input {
       uses command-forwarding;
     }
     output {
       container aamw-mesg {
         uses aamw-mesg-block;
       }
     }
   }
   rpc request-anti-virus-exempt-list-add {
     description "Add a signature ID to the exempt list";
     junos:command "request services anti-virus signature-exempt-list add";
     input {
       uses command-forwarding;
       leaf signature-id {
         description "Add a exempt list";
         junos:cli-feature "nokeyword";
         type string;
         mandatory true;
       }
     }
     output {
       container aamw-cmd-status {
         uses aamw-cmd-status-block;
       }
     }
   }
   rpc request-anti-virus-exempt-list-del {
     description "Delete a signature ID from the exempt list";
     junos:command "request services anti-virus signature-exempt-list delete";
     input {
       uses command-forwarding;
       leaf signature-id {
         description "Delete a exempt list";
         junos:cli-feature "nokeyword";
         type string;
         mandatory true;
       }
     }
     output {
       container aamw-cmd-status {
         uses aamw-cmd-status-block;
       }
     }
   }
   rpc request-anti-virus-exempt-list-import {
     description "Import exempt list from a file";
     junos:command "request services anti-virus signature-exempt-list import";
     input {
       uses command-forwarding;
       leaf file {
         description "Exempt list file";
         junos:cli-feature "nokeyword";
         type string;
         mandatory true;
       }
     }
     output {
       container aamw-cmd-status {
         uses aamw-cmd-status-block;
       }
     }
   }
   rpc request-anti-virus-exempt-list-export {
     description "Export exempt list to a file";
     junos:command "request services anti-virus signature-exempt-list export";
     input {
       uses command-forwarding;
       leaf file {
         description "Exempt list file";
         junos:cli-feature "nokeyword";
         type string;
         mandatory true;
       }
     }
     output {
       container aamw-cmd-status {
         uses aamw-cmd-status-block;
       }
     }
   }
   rpc check-service-policies {
     description "Check the security policies";
     junos:command "request services policies check";
     input {
       uses command-forwarding;
       leaf from-zone {
         description "Check the policies from this zone";
         type string;
       }
       leaf to-zone {
         description "Check the policies to this zone";
         type string;
       }
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc check-global-service-policies {
     description "Check global policies";
     junos:command "request services policies check global";
     input {
       uses command-forwarding;
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc recover-service-policy {
     description "Recover the security policies";
     junos:command "request services policies resync";
     input {
       uses command-forwarding;
       leaf from-zone {
         description "Recover the policies from this zone";
         type string;
       }
       leaf to-zone {
         description "Recover the policies to this zone";
         type string;
       }
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc recover-global-service-policies {
     description "Recover global policies";
     junos:command "request services policies resync global";
     input {
       uses command-forwarding;
       leaf pfe {
         description "Packet forwarding engine";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc request-secintel-download {
     description "Download security intelligence feed";
     junos:command "request services security-intelligence download";
     input {
       uses command-forwarding;
     }
     output {
       container secintel-download {
         uses secintel-download-block;
       }
     }
   }
   rpc request-secintel-download-status {
     description "Show feed download status";
     junos:command "request services security-intelligence download status";
     input {
       uses command-forwarding;
     }
   }
   rpc request-secintel-redirect-add {
     description "Add redirect file";
     junos:command "request services security-intelligence redirect-file add";
     input {
       uses command-forwarding;
       leaf file-name {
         description "Add a redirect file";
         junos:cli-feature "nokeyword";
         type jt:filename;
         mandatory true;
       }
     }
   }
   rpc request-secintel-redirect-delete {
     description "Delete a redirect file";
     junos:command "request services security-intelligence redirect-file delete";
     input {
       uses command-forwarding;
       leaf file-name {
         description "Delete a redirect file";
         junos:cli-feature "nokeyword";
         type jt:filename;
         mandatory true;
       }
     }
   }
   rpc request-secintel-uninstall {
     description "Uninstall feed data";
     junos:command "request services security-intelligence uninstall";
     input {
       uses command-forwarding;
     }
     output {
       container secintel-uninstall {
         uses secintel-uninstall-block;
       }
     }
   }
   rpc request-secintel-uninstall-status {
     description "Show uninstall status";
     junos:command "request services security-intelligence uninstall status";
     input {
       uses command-forwarding;
     }
   }
   rpc rdm-reload-dictionary {
     description "Reload dictionary";
     junos:command "request services remote-device-management reload-dictionary";
     input {
       leaf dictionary-path {
         description "Complete path with dictionary name";
         junos:cli-feature "nokeyword";
         type jt:filename;
         mandatory true;
       }
     }
     output {
       container rdm-information {
         uses rdm-information-block;
       }
     }
   }
   rpc rdm-sd-reconfigure {
     description "Reconfigure service device";
     junos:command "request services remote-device-management reconfigure service-device";
     input {
       leaf service-device-name {
         description "Service device name";
         junos:cli-feature "nokeyword";
         type string;
         mandatory true;
       }
     }
     output {
       container rdm-information {
         uses rdm-information-block;
       }
     }
   }
   rpc twamp-test-start {
     description "Start TWAMP test sessions";
     junos:command "request services rpm twamp start client";
     input {
       leaf control-connection {
         description "Name of the control connection";
         junos:cli-feature "nokeyword";
         default "all";
         type string;
       }
     }
     output {
       choice output_c {
         case output-tag {
           leaf output {
             type string;
           }
         }
         case multichassis-tag {
           anyxml multi-routing-engine-results;
         }
       }
     }
   }
   rpc twamp-test-stop {
     description "Stop TWAMP test sessions";
     junos:command "request services rpm twamp stop client";
     input {
       leaf control-connection {
         description "Name of the control connection";
         junos:cli-feature "nokeyword";
         default "all";
         type string;
       }
     }
     output {
       choice output_c {
         case output-tag {
           leaf output {
             type string;
           }
         }
         case multichassis-tag {
           anyxml multi-routing-engine-results;
         }
       }
     }
   }
   rpc request-netconf-trace {
     description "NETCONF tracing";
     junos:command "request services netconf trace";
     input {
       leaf on-demand {
         description "Control on-demand tracing";
         junos:cli-feature "nokeyword";
         type enumeration {
           enum "start" {
             description "Start NETCONF tracing";
           }
           enum "stop" {
             description "Stop NETCONF tracing";
           }
         }
         mandatory true;
       }
     }
     output {
       choice output_c {
         case output-tag {
           leaf output {
             type string;
           }
         }
         case multichassis-tag {
           anyxml multi-routing-engine-results;
         }
       }
     }
   }
   rpc request-service-capture-snapshot {
     description "Request a snapshot of the current packet capture";
     junos:command "request services capture snapshot";
     input {
       leaf interface {
         description "Name of adaptive services interface";
         type string;
         mandatory true;
       }
       leaf file {
         junos:cli-feature "nokeyword";
         type string;
         mandatory true;
       }
     }
   }
   rpc request-service-capture-clear {
     description "Clear the current packet capture";
     junos:command "request services capture clear";
     input {
       leaf interface {
         description "Name of adaptive services interface";
         type string;
         mandatory true;
       }
     }
   }
   rpc request-services-redundancy-set {
     description "Request services redundancy-set";
     junos:command "request services redundancy-set";
     input {
       leaf id {
         description "Set id";
         type union {
           type uint32;
           type string {
             pattern "<.*>|$.*";
           }
         }
         mandatory true;
       }
       leaf trigger {
         description "Trigger a redundancy-event";
         type empty;
         mandatory true;
       }
       leaf redundancy-event {
         description "Redundancy event which needs to be triggered";
         type string;
         mandatory true;
       }
       leaf force {
         description "Trigger event forcefully overriding warnings";
         type empty;
       }
     }
   }
   rpc request-services-ip-monitoring {
     description "Ip monitoring requests";
     junos:command "request services ip-monitoring";
     output {
       choice output_c {
         case output-tag {
           leaf output {
             type string;
           }
         }
         case multichassis-tag {
           anyxml multi-routing-engine-results;
         }
       }
     }
   }
   rpc request-services-ip-monitoring-preempt-restore {
     description "Restore no-preempt failover state on ip monitoring";
     junos:command "request services ip-monitoring preempt-restore";
     input {
       leaf policy {
         description "Policy";
         type string;
         mandatory true;
       }
     }
     output {
       choice output_c {
         case output-tag {
           leaf output {
             type string;
           }
         }
         case multichassis-tag {
           anyxml multi-routing-engine-results;
         }
       }
     }
   }
   rpc request-flb-maintenance-down {
     description "Request for destination to go in maintenance-down mode";
     junos:command "request services traffic-load-balance flb-destination maintenance-down";
     input {
       leaf destination {
         description "Destination VSRX";
         type string;
       }
     }
     output {
       container tdir-flb-maintenance-down-status {
         uses tdir-flb-maintenance-down-status-block;
       }
     }
   }
   rpc request-traffic-loadbalance-real-service-rejoin {
     description "Rejoin for load-balance request";
     junos:command "request services traffic-load-balance real-service rejoin";
     input {
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
     output {
       choice output_c {
         case output-tag {
           leaf output {
             type string;
           }
         }
         case multichassis-tag {
           anyxml multi-routing-engine-results;
         }
       }
     }
   }
   rpc request-url-filter-force-dns-resolution-all {
     description "All profiles";
     junos:command "request services web-filter force dns-resolution all";
     output {
       container force-dns-options {
         uses force-dns-options-block;
       }
     }
   }
   rpc request-url-filter-force-dns-resolution-profile {
     description "Profile name";
     junos:command "request services web-filter force dns-resolution profile";
     input {
       leaf profile-name {
         description "Profile name";
         junos:cli-feature "nokeyword";
         type string;
         mandatory true;
       }
       leaf url-filter-template {
         description "Template name";
         type string;
       }
     }
     output {
       container force-dns-options {
         uses force-dns-options-block;
       }
     }
   }
   rpc request-url-filter-database-update {
     description "Update the specific url-filter-database";
     junos:command "request services web-filter update url-filter-database";
     input {
       leaf file {
         description "URL filter database file";
         type string;
         mandatory true;
       }
     }
     output {
       container update-db-filepath {
         uses update-db-filepath-block;
       }
     }
   }
   rpc request-dns-filter-database-update {
     description "Update the specific dns-filter-database";
     junos:command "request services web-filter update dns-filter-database";
     input {
       choice file_type {
         case file {
           leaf file {
             description "DNS filter database file";
             type string;
           }
         }
         case multi-tenant-file {
           leaf multi-tenant-file {
             description "Multi-tenant-file";
             type enumeration {
               enum "plain-text" {
                 description "DNS filter plain-text database file ";
               }
               enum "hashed" {
                 description "DNS filter encrypted database file ";
               }
             }
           }
         }
       }
     }
     output {
       container update-db-filepath {
         uses update-db-filepath-block;
       }
     }
   }
   rpc request-url-filter-validate {
     description "Validate the web-filter database";
     junos:command "request services web-filter validate";
     input {
       choice file {
         case all {
           leaf all {
             description "Validate the url-filter database for all profiles";
             type empty;
           }
         }
         case url-filter-file-name {
           leaf url-filter-file-name {
             description "URL filter database file";
             type string;
           }
         }
         case dns-filter-file-name {
           leaf dns-filter-file-name {
             description "DNS filter database file";
             type string;
           }
         }
       }
       leaf hash-method {
         description "Hash method";
         type enumeration {
           enum "hmac-md5-96" {
             description "HMAC-MD5-96 algorithm";
           }
           enum "hmac-sha1-96" {
             description "HMAC-SHA1-96 algorithm";
           }
           enum "hmac-sha2-256" {
             description "HMAC-SHA2-256 algorithm";
           }
           enum "hmac-sha-256-128" {
             description "HMAC-SHA-256-128 algorithm";
           }
         }
       }
       leaf hash-key {
         description "Hash key";
         type string;
       }
     }
     output {
       container validate-db-options {
         uses validate-db-options-block;
       }
     }
   }
   rpc request-services-url-filter-delete-gencfg-data {
     description "Gencfg data";
     junos:command "request services web-filter delete gencfg-data";
     output {
       container request-delete-gencfg {
         uses request-delete-gencfg-block;
       }
     }
   }
   rpc request-lacp-link-protection-switchover {
     description "Request LACP link protection switchover";
     junos:command "request lacp link-switchover";
     input {
       leaf interface-name {
         description "Name of AE interface";
         junos:cli-feature "nokeyword";
         type union {
           type jt:interface-wildcard;
           type string {
             pattern "<.*>|$.*";
           }
         }
         mandatory true;
       }
     }
     output {
       container lacp-link-switchover {
         uses lacp-link-switchover-block;
       }
     }
   }
   rpc request-message {
     description "Send text message to other users";
     junos:command "request message";
     input {
       leaf user {
         description "Name of user (account@terminal) to receive message";
         type string;
         mandatory true;
       }
       leaf terminal {
         description "Device name of target terminal (/dev/ttyXX)";
         type string;
       }
       leaf message {
         description "Text of message";
         type string;
       }
     }
     output {
       choice output_c {
         case output-tag {
           leaf output {
             type string;
           }
         }
         case multichassis-tag {
           anyxml multi-routing-engine-results;
         }
       }
     }
   }
   rpc request-message-all {
     description "Send message to all logged-in users";
     junos:command "request message all";
     input {
       leaf message {
         description "Text of message";
         type string;
       }
     }
     output {
       choice output_c {
         case output-tag {
           leaf output {
             type string;
           }
         }
         case multichassis-tag {
           anyxml multi-routing-engine-results;
         }
       }
     }
   }
   rpc request-compute-node-cleanup-log {
     description "Compute node cleanup /var/tmp and /var/log";
     junos:command "request app-engine cleanup";
     input {
       uses command-forwarding;
       leaf compute-cluster {
         description "Compute cluster name";
         type string {
           length "1 .. 15";
         }
       }
       leaf compute-node {
         description "Compute node name";
         type string {
           length "1 .. 15";
         }
       }
     }
     output {
       choice output_c {
         case output-tag {
           leaf output {
             type string;
           }
         }
         case multichassis-tag {
           anyxml multi-routing-engine-results;
         }
       }
     }
   }
   rpc request-compute-node-file-copy {
     description "Copy file from host to vjunos";
     junos:command "request app-engine file-copy";
     input {
       leaf host-path {
         description "Copy files related to";
         junos:cli-feature "nokeyword";
         type enumeration {
           enum "crash" {
             description "Files in /var/crash";
           }
           enum "log" {
             description "Files in /var/log";
           }
         }
         mandatory true;
       }
       leaf from-jhost {
         description "Host file name";
         type string {
           junos:posix-pattern "!(^/|\\.\\./)";
           junos:pattern-message "Must not be absolute path or contain relative components";
         }
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-guest-virtual-machine-package-copy {
     description "Copy guest virtual-machine package to Junos";
     junos:command "request app-engine virtual-machine-package-copy";
     input {
       leaf package-name {
         description "Name of the virtual-machine package";
         type string;
         mandatory true;
       }
       leaf destination-path {
         description "Path to the destination directory in Junos";
         type string;
         mandatory true;
       }
     }
     output {
       choice output_c {
         case output-tag {
           leaf output {
             type string;
           }
         }
         case multichassis-tag {
           anyxml multi-routing-engine-results;
         }
       }
     }
   }
   rpc request-vmhost-poweroff {
     description "Power off the software on RE";
     junos:command "request vmhost power-off";
     input {
       leaf other-routing-engine {
         description "Power off other Routing Engine";
         type empty;
       }
     }
     output {
       choice output_c {
         case output-tag {
           leaf output {
             type string;
           }
         }
         case multichassis-tag {
           anyxml multi-routing-engine-results;
         }
       }
     }
   }
   rpc request-vmhost-halt {
     description "Halt the software on RE";
     junos:command "request vmhost halt";
     input {
       uses command-forwarding;
     }
     output {
       choice output_c {
         case output-tag {
           leaf output {
             type string;
           }
         }
         case multichassis-tag {
           anyxml multi-routing-engine-results;
         }
       }
     }
   }
   rpc request-vmhost-power-on-other-re {
     description "Power on the system";
     junos:command "request vmhost power-on";
     input {
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc request-vmhost-power-cycle {
     description "Power cycle the vmhost";
     junos:command "request vmhost power-cycle";
     input {
       uses command-forwarding;
     }
     output {
       choice output_c {
         case output-tag {
           leaf output {
             type string;
           }
         }
         case multichassis-tag {
           anyxml multi-routing-engine-results;
         }
       }
     }
   }
   rpc request-vmhost-power-cycle-cb {
     description "Power Cycle Chassis";
     junos:command "request vmhost power-cycle-cb";
     output {
       choice output_c {
         case output-tag {
           leaf output {
             type string;
           }
         }
         case multichassis-tag {
           anyxml multi-routing-engine-results;
         }
       }
     }
   }
   rpc request-vmhost-power-cycle-re {
     description "Power Cycle RE";
     junos:command "request vmhost power-cycle-re";
     output {
       choice output_c {
         case output-tag {
           leaf output {
             type string;
           }
         }
         case multichassis-tag {
           anyxml multi-routing-engine-results;
         }
       }
     }
   }
   rpc request-vmhost-reboot {
     description "Reboot RE vmhost";
     junos:command "request vmhost reboot";
     input {
       uses command-forwarding;
       leaf media {
         junos:cli-feature "nokeyword";
         type enumeration {
           enum "disk1" {
             description "Boot off disk1(primary) device";
           }
           enum "disk2" {
             description "Boot off disk2(backup) device";
           }
           enum "network" {
             description "Network boot via PXE";
           }
           enum "usb" {
             description "Boot off USB device";
           }
         }
       }
       leaf partition {
         junos:cli-feature "nokeyword";
         type enumeration {
           enum "primary" {
             description "Boot from primary partition";
           }
           enum "alternate" {
             description "Boot from alternate partition";
           }
         }
       }
       leaf in {
         description "Number of minutes to delay before reboot operation";
         type union {
           type string {
             pattern "<.*>|$.*";
           }
           type uint32 {
             range "0 .. 100";
           }
         }
       }
     }
     output {
       choice output_c {
         case output-tag {
           leaf output {
             type string;
           }
         }
         case multichassis-tag {
           anyxml multi-routing-engine-results;
         }
       }
     }
   }
   rpc request-vmhost-file-cleanup {
     description "RE vmhost cleanup /var/tmp, /var/crash and /var/log";
     junos:command "request vmhost cleanup";
     input {
       uses command-forwarding;
     }
     output {
       choice output_c {
         case output-tag {
           leaf output {
             type string;
           }
         }
         case multichassis-tag {
           anyxml multi-routing-engine-results;
         }
       }
     }
   }
   rpc request-vmhost-file-cleanup-dry-run {
     description "Only list the cleanup candidates, do not remove them";
     junos:command "request vmhost cleanup dry-run";
     output {
       choice output_c {
         case output-tag {
           leaf output {
             type string;
           }
         }
         case multichassis-tag {
           anyxml multi-routing-engine-results;
         }
       }
     }
   }
   rpc request-vmhost-file-copy {
     description "Copy file from vmhost to vjunos";
     junos:command "request vmhost file-copy";
     input {
       leaf node-path {
         description "Copy files related to";
         junos:cli-feature "nokeyword";
         type enumeration {
           enum "crash" {
             description "Files in /var/crash";
           }
           enum "log" {
             description "Files in /var/log";
           }
         }
         mandatory true;
       }
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-copy-vjunos-to-jnode {
     description "Copy file from vjunos to vmhost";
     junos:command "request vmhost copy vjunos-to-jnode";
     input {
       leaf from-vjunos {
         description "Junos file name";
         type string;
         mandatory true;
       }
       leaf to-jnode {
         description "Host file name";
         type string;
         mandatory true;
       }
     }
     output {
       choice output_c {
         case output-tag {
           leaf output {
             type string;
           }
         }
         case multichassis-tag {
           anyxml multi-routing-engine-results;
         }
       }
     }
   }
   rpc request-copy-jnode-to-vjunos {
     description "Copy file from vmhost to vjunos";
     junos:command "request vmhost copy jnode-to-vjunos";
     input {
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-vmhost-package-add {
     description "Add extension or upgrade package";
     junos:command "request vmhost software add";
     input {
       leaf i40-driver {
         description "Upgrade only the i40 driver";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf reboot {
         description "Reboot RE vmhost after adding package";
         type empty;
       }
       leaf in {
         description "Number of minutes to delay before reboot operation";
         type union {
           type string {
             pattern "<.*>|$.*";
           }
           type uint32 {
             range "0 .. 100";
           }
         }
       }
       choice re-choice {
         case re0 {
           leaf re0 {
             description "Install package on RE0";
             type empty;
           }
         }
         case re1 {
           leaf re1 {
             description "Install package on RE1";
             type empty;
           }
         }
       }
       choice validate_choice {
         case no-validate {
           leaf no-validate {
             description "Don't check compatibility with current configuration";
             type empty;
           }
         }
       }
       choice chassis {
         case dont-forward {
           leaf dont-forward {
             type empty;
           }
         }
       }
       leaf issu-internal {
         description "Internally executed by mgd, to allow software adds during issu";
         type empty;
       }
       leaf upgrade-to-model {
         description "Name of the model to upgrade to";
         type string;
       }
       leaf unlink {
         description "Remove the package after successful installation";
         type empty;
       }
     }
     output {
       choice output_c {
         case output-tag {
           leaf output {
             type string;
           }
         }
         case multichassis-tag {
           anyxml multi-routing-engine-results;
         }
       }
     }
   }
   rpc request-vmhost-package-delete {
     description "Remove extension or upgrade package";
     junos:command "request vmhost software delete";
     input {
       leaf force {
         description "Force removal of package (ignore warnings)";
         type empty;
       }
       leaf virtual-machine-package {
         description "Remove virtual-machine package";
         type empty;
       }
       choice package-options {
         case set {
           leaf-list set {
             ordered-by user;
             description "List of package name";
             type string;
           }
         }
         case package-name {
           leaf package-name {
             description "Name of package";
             junos:cli-feature "nokeyword";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
     }
     output {
       choice output_c {
         case output-tag {
           leaf output {
             type string;
           }
         }
         case multichassis-tag {
           anyxml multi-routing-engine-results;
         }
       }
     }
   }
   rpc abort-vmhost-in-service-upgrade {
     description "Abort in-service software upgrade";
     junos:command "request vmhost software abort in-service-upgrade";
     output {
       choice output_c {
         case output-tag {
           leaf output {
             type string;
           }
         }
         case multichassis-tag {
           anyxml multi-routing-engine-results;
         }
       }
     }
   }
   rpc request-vmhost-package-in-service-upgrade {
     description "In-service software upgrade";
     junos:command "request vmhost software in-service-upgrade";
     input {
       leaf package-name {
         description "URL or pathname of package";
         junos:cli-feature "nokeyword";
         type jt:filename;
         mandatory true;
       }
       leaf no-old-master-upgrade {
         description "Don't upgrade the old master after switchover";
         type empty;
       }
       leaf verbose {
         description "Enable detailed output";
         type empty;
       }
       leaf reboot {
         description "Reboot RE vmhost after adding package";
         type empty;
       }
       leaf enhanced-mode {
         description "Try to upgrade without any traffic loss";
         type empty;
       }
     }
     output {
       choice output_c {
         case output-tag {
           leaf output {
             type string;
           }
         }
         case multichassis-tag {
           anyxml multi-routing-engine-results;
         }
       }
     }
   }
   rpc request-vmhost-in-service-upgrade-status {
     description "In-Service software upgrade status";
     junos:command "request vmhost software in-service-upgrade status";
     output {
       leaf issu-status {
         type string;
         description "Show issu status";
       }
     }
   }
   rpc request-vmhost-nonstop-upgrade {
     description "Nonstop software upgrade";
     junos:command "request vmhost software nonstop-upgrade";
     input {
       leaf force-host {
         description "Force addition of host os package (ignore version check)";
         type empty;
       }
       leaf no-auto-recovery {
         description "Will not recover in case of NSSU failure";
         type empty;
       }
       leaf reboot {
         description "Reboot system after adding package";
         type empty;
       }
       choice package-options {
         case set {
           leaf-list set {
             ordered-by user;
             description "List of URLs or pathnames corresponding to packages";
             type jt:filename;
           }
         }
         case package-name {
           leaf package-name {
             description "URL or pathname of package";
             junos:cli-feature "nokeyword";
             type jt:filename;
           }
         }
       }
       leaf no-old-master-upgrade {
         description "Don't upgrade the old master after switchover";
         type empty;
       }
       leaf no-copy {
         description "Don't save copies of package files";
         status deprecated;
         type empty;
       }
       leaf unlink {
         description "Remove the package after successful installation";
         status deprecated;
         type empty;
       }
       leaf no-validate {
         description "Don't check compatibility with current configuration";
         type empty;
       }
     }
     output {
       choice output_c {
         case output-tag {
           leaf output {
             type string;
           }
         }
         case multichassis-tag {
           anyxml multi-routing-engine-results;
         }
       }
     }
   }
   rpc request-vmhost-package-validate {
     description "Verify package compatibility with current configuration";
     junos:command "request vmhost software validate";
     input {
       choice package-options {
         case package-name {
           leaf package-name {
             description "URL or pathname of package";
             junos:cli-feature "nokeyword";
             type jt:filename;
           }
         }
       }
       choice chassis {
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-vmhost-package-rollback {
     description "Attempt to roll back to previous set of packages";
     junos:command "request vmhost software rollback";
     input {
       uses command-forwarding;
       leaf reboot {
         description "Reboot system after rollback";
         type empty;
       }
     }
     output {
       choice output_c {
         case output-tag {
           leaf output {
             type string;
           }
         }
         case actual-tag-1 {
           anyxml rollback-information;
         }
         case multichassis-tag {
           anyxml multi-routing-engine-results;
         }
       }
     }
   }
   rpc request-vmhost-jdm-package-add {
     description "Install fresh JDM package or upgrade package";
     junos:command "request vmhost jdm add";
     input {
       leaf package-name {
         description "JDM package name";
         junos:cli-feature "nokeyword";
         type jt:filename;
         mandatory true;
       }
       leaf force {
         description "Force package add";
         type empty;
       }
     }
     output {
       choice output_c {
         case output-tag {
           leaf output {
             type string;
           }
         }
         case multichassis-tag {
           anyxml multi-routing-engine-results;
         }
       }
     }
   }
   rpc request-vmhost-jdm-package-delete {
     description "Remove currently installed JDM package";
     junos:command "request vmhost jdm delete";
     output {
       choice output_c {
         case output-tag {
           leaf output {
             type string;
           }
         }
         case multichassis-tag {
           anyxml multi-routing-engine-results;
         }
       }
     }
   }
   rpc request-package-vmhost-jdm-start {
     description "Start the JDM";
     junos:command "request vmhost jdm start";
     output {
       choice output_c {
         case output-tag {
           leaf output {
             type string;
           }
         }
         case multichassis-tag {
           anyxml multi-routing-engine-results;
         }
       }
     }
   }
   rpc request-package-vmhost-jdm-stop {
     description "Stop the JDM";
     junos:command "request vmhost jdm stop";
     output {
       choice output_c {
         case output-tag {
           leaf output {
             type string;
           }
         }
         case multichassis-tag {
           anyxml multi-routing-engine-results;
         }
       }
     }
   }
   rpc request-vmhost-jdm-login {
     description "Login to JDM";
     junos:command "request vmhost jdm login";
     output {
       choice output_c {
         case output-tag {
           leaf output {
             type string;
           }
         }
         case multichassis-tag {
           anyxml multi-routing-engine-results;
         }
       }
     }
   }
   rpc request-vmhost-snapshot {
     description "Create a vmhost recovery snapshot";
     junos:command "request vmhost snapshot";
     input {
       uses command-forwarding;
       leaf no-confirm {
         description "Do not ask for confirmation";
         type empty;
       }
     }
   }
   rpc request-vmhost-snapshot-config {
     description "Sychronise Configuration between the disks";
     junos:command "request vmhost snapshot config";
     input {
       uses command-forwarding;
     }
   }
   rpc request-vmhost-snapshot-partition {
     description "Partition the target media";
     junos:command "request vmhost snapshot partition";
     input {
       uses command-forwarding;
     }
   }
   rpc request-vmhost-snapshot-recovery {
     description "Recover the primary media from snapshot";
     junos:command "request vmhost snapshot recovery";
     input {
       uses command-forwarding;
     }
   }
   rpc request-vmhost-snapshot-recovery-partition {
     description "Partition the media before snapshot";
     junos:command "request vmhost snapshot recovery partition";
     input {
       uses command-forwarding;
     }
   }
   rpc request-vmhost-zeroize {
     description "Erase all data, including configuration and log files";
     junos:command "request vmhost zeroize";
     input {
       uses command-forwarding;
       leaf ztp-option {
         description "ZTP mode";
         type enumeration {
           enum "secure-enable" {
             description "Secure Enable";
           }
           enum "secure-disable" {
             description "Secure Disable";
           }
         }
       }
     }
   }
   rpc request-vmhost-zeroize-erase-disk {
     description "Erase all disks";
     junos:command "request vmhost zeroize erase-disk";
     input {
       uses command-forwarding;
     }
   }
   rpc request-vmhost-hard-disk-test {
     description "Run smartd self tests on hard disks";
     junos:command "request vmhost hard-disk-test";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       container raid-information {
         uses raid-information-block;
       }
     }
   }
   rpc request-vmhost-last-known-good-bios {
     description "Backup/Restore last known good bios image";
     junos:command "request vmhost last-known-good-bios";
   }
   rpc request-vmhost-last-known-good-bios-backup {
     description "Backup last known good bios";
     junos:command "request vmhost last-known-good-bios backup";
     input {
       leaf path {
         description "Path to take backup";
         junos:cli-feature "nokeyword";
         type string;
       }
     }
     output {
       choice output_c {
         case output-tag {
           leaf output {
             type string;
           }
         }
         case multichassis-tag {
           anyxml multi-routing-engine-results;
         }
       }
     }
   }
   rpc request-vmhost-last-known-good-bios-restore {
     description "Restore last known good bios";
     junos:command "request vmhost last-known-good-bios restore";
     input {
       leaf path {
         description "Path which contains last known bios";
         junos:cli-feature "nokeyword";
         type string;
       }
     }
     output {
       choice output_c {
         case output-tag {
           leaf output {
             type string;
           }
         }
         case multichassis-tag {
           anyxml multi-routing-engine-results;
         }
       }
     }
   }
   rpc request-storage-self-test {
     description "Perform vmhost storage self test operations";
     junos:command "request vmhost storage";
     input {
       leaf storage-name {
         description "Storage  name";
         junos:cli-feature "nokeyword";
         type string {
           junos:posix-pattern "^[a-zA-Z0-9]+$";
           junos:pattern-message "Storage name must be a string of alphanumericals";
         }
         mandatory true;
       }
       choice storage_request {
         case self-test-long {
           leaf self-test-long {
             description "Long Storage Test";
             type empty;
           }
         }
         case self-test-short {
           leaf self-test-short {
             description "Long Storage Test";
             type empty;
           }
         }
         case self-test-messages {
           leaf self-test-messages {
             description "Storage Self Test messages";
             type empty;
           }
         }
       }
     }
   }
   rpc request-storage-external-ssd-initialize {
     description "Initialize an external SSD";
     junos:command "request vmhost storage external-ssd initialize";
     input {
       leaf slot {
         description "SSD slot number";
         type union {
           type string {
             pattern "<.*>|$.*";
           }
           type uint32 {
             range "0 .. 1";
           }
         }
         mandatory true;
       }
       leaf public-dir-name {
         description "Public directory for SSD";
         type string {
           junos:posix-pattern "^[[:alnum:]_-]+$";
           junos:pattern-message "Directory name must be a string of alphanumericals, dashes or underscores";
         }
         mandatory true;
       }
       leaf force {
         description "Force initialization";
         type empty;
       }
     }
     output {
       container external-ssd-op-result {
         uses external-ssd-op-result-block;
       }
     }
   }
   rpc request-storage-external-ssd-add {
     description "Add SSD paths to device";
     junos:command "request vmhost storage external-ssd add";
     input {
       leaf slot {
         description "SSD slot number";
         type union {
           type string {
             pattern "<.*>|$.*";
           }
           type uint32 {
             range "0 .. 1";
           }
         }
         mandatory true;
       }
     }
     output {
       container external-ssd-op-result {
         uses external-ssd-op-result-block;
       }
     }
   }
   rpc request-storage-external-ssd-remove {
     description "Remove SSD paths from device";
     junos:command "request vmhost storage external-ssd remove";
     input {
       leaf slot {
         description "SSD slot number";
         type union {
           type string {
             pattern "<.*>|$.*";
           }
           type uint32 {
             range "0 .. 1";
           }
         }
         mandatory true;
       }
     }
     output {
       container external-ssd-op-result {
         uses external-ssd-op-result-block;
       }
     }
   }
   rpc request-vmhost-mode {
     description "Request operation on vmhost mode";
     junos:command "request vmhost mode";
     input {
       leaf mode-name {
         junos:cli-feature "nokeyword";
         type string;
         mandatory true;
       }
     }
     output {
       choice output_c {
         case output-tag {
           leaf output {
             type string;
           }
         }
         case multichassis-tag {
           anyxml multi-routing-engine-results;
         }
       }
     }
   }
   rpc request-vmhost-remote-file-copy {
     description "Copy a file from/to a remote source/destination";
     junos:command "request vmhost remote-file-copy";
     input {
       leaf interface {
         description "Choose interface for file copy";
         type enumeration {
           enum "in-band" {
             description "Use in-band interface";
           }
           enum "out-of-band" {
             description "Use out-of-band interface";
           }
         }
         mandatory true;
       }
       leaf source {
         description "File path (remote format: [user[:password]@]<protocol>://<host>[:port]:<file_path>)";
         type string;
         mandatory true;
       }
       leaf destination {
         description "File path (remote format: [user[:password]@]<protocol>://<host>[:port]:<file_path>)";
         type string;
         mandatory true;
       }
     }
     output {
       container vmhost-remote-file-copy-information {
         uses vmhost-remote-file-copy-information-block;
       }
     }
   }
   rpc request-vmhost-local-file-copy {
     description "Make a local copy of a file";
     junos:command "request vmhost local-file-copy";
     input {
       leaf source {
         description "File path";
         type string;
         mandatory true;
       }
       leaf destination {
         description "File path";
         type string;
         mandatory true;
       }
     }
     output {
       container vmhost-local-file-copy-information {
         uses vmhost-local-file-copy-information-block;
       }
     }
   }
   rpc request-snmp-spoof-trap {
     description "Generate artificial SNMP notification";
     junos:command "request snmp spoof-trap";
     input {
       leaf control-plane-instance {
         type string;
       }
       leaf trap {
         description "The name of the trap to spoof";
         junos:cli-feature "nokeyword";
         type string;
         mandatory true;
       }
       leaf variable-bindings {
         description "The list of variables & values to include in the trap";
         type string;
       }
     }
     output {
       container snmp-spoof-trap-results {
         uses snmp-spoof-trap-results-block;
       }
     }
   }
   rpc request-snmp-utility-mib-set {
     description "Set values in utility mib objects";
     junos:command "request snmp utility-mib set";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
       leaf object-value {
         type string;
         mandatory true;
       }
     }
     output {
       container snmp-utility-mib-results {
         uses snmp-utility-mib-results-block;
       }
     }
   }
   rpc request-snmp-utility-mib-clear {
     description "Clear values in utility mib objects";
     junos:command "request snmp utility-mib clear";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
     }
     output {
       container snmp-utility-mib-results {
         uses snmp-utility-mib-results-block;
       }
     }
   }
   rpc request-ancp-oam-information {
     description "Request ANCP operation, administration, and management";
     junos:command "request ancp oam";
     output {
       container ancp-oam-information {
         uses ancp-oam-information-block;
       }
     }
   }
   rpc request-ancp-oam-neighbor-information {
     description "Neighbor identifier";
     junos:command "request ancp oam neighbor";
     input {
       choice neighbor-opts {
         case system-name {
           leaf system-name {
             description "MAC address of the neighbor";
             type string;
           }
         }
         case ip-address {
           leaf ip-address {
             description "IP address of the neighbor";
             type jt:ipaddr;
           }
         }
       }
       leaf subscriber {
         description "Subscriber identifier";
         type string;
         mandatory true;
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
     output {
       container ancp-oam-information {
         uses ancp-oam-information-block;
       }
     }
   }
   rpc request-ancp-oam-interface-information {
     description "ANCP interface specific options";
     junos:command "request ancp oam interface";
     input {
       choice interface-opts {
         case interface-name {
           leaf interface-name {
             description "Name of ANCP interface";
             junos:cli-feature "nokeyword";
             type string;
           }
         }
         case interface-set {
           leaf interface-set {
             description "Name of ANCP interface set";
             type string {
               junos:posix-pattern "^.{1,64}$";
               junos:pattern-message "Must be string of 64 characters or less";
             }
           }
         }
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
     output {
       container ancp-oam-information {
         uses ancp-oam-information-block;
       }
     }
   }
   rpc request-ancp-oam-port-up {
     description "ANCP port-up processing";
     junos:command "request ancp oam port-up";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
         mandatory true;
       }
       leaf remote-id {
         description "Access loop remote id";
         type string {
           junos:posix-pattern "^.{1,63}$";
           junos:pattern-message "Must be a string of 63 characters or less";
         }
         mandatory true;
       }
       leaf outer-vlan-id {
         description "Access aggregation circuit id binary";
         type union {
           type string {
             pattern "<.*>|$.*";
           }
           type uint16 {
             range "1 .. 4094";
           }
         }
         mandatory true;
       }
     }
   }
   rpc request-ancp-oam-port-down {
     description "ANCP port-down processing";
     junos:command "request ancp oam port-down";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
       }
       leaf remote-id {
         description "Access loop remote id";
         type string {
           junos:posix-pattern "^.{1,63}$";
           junos:pattern-message "Must be a string of 63 characters or less";
         }
       }
       leaf outer-vlan-id {
         description "Access aggregation circuit id binary";
         type union {
           type string {
             pattern "<.*>|$.*";
           }
           type uint16 {
             range "1 .. 4094";
           }
         }
       }
     }
   }
   rpc aaa-subscriber-add-service {
     description "Service activation";
     junos:command "request network-access aaa subscriber add";
     input {
       leaf control-plane-instance {
         type string;
       }
       leaf session-id {
         description "Session id";
         type union {
           type string {
             pattern "<.*>|$.*";
           }
           type uint64 {
             range "1 .. 18446744073709551615";
           }
         }
         mandatory true;
       }
       leaf service-profile {
         description "Name of service-profile";
         type string;
         mandatory true;
       }
     }
   }
   rpc aaa-subscriber-delete-service {
     description "Service deactivation";
     junos:command "request network-access aaa subscriber delete";
     input {
       leaf control-plane-instance {
         type string;
       }
       leaf session-id {
         description "Session id";
         type union {
           type string {
             pattern "<.*>|$.*";
           }
           type uint64 {
             range "1 .. 18446744073709551615";
           }
         }
         mandatory true;
       }
       leaf service-profile {
         description "Name of dynamic-profile";
         type string;
         mandatory true;
       }
     }
   }
   rpc aaa-subscriber-modify-variable {
     description "Modify dynamic variable";
     junos:command "request network-access aaa subscriber modify";
     input {
       leaf control-plane-instance {
         type string;
       }
       leaf session-id {
         description "Session id";
         type union {
           type string {
             pattern "<.*>|$.*";
           }
           type uint64 {
             range "1 .. 18446744073709551615";
           }
         }
         mandatory true;
       }
       leaf junos-cos-traffic-control-profile {
         description "Modify $junos-cos-traffic-control-profile variable";
         type string;
       }
     }
   }
   rpc aaa-subscriber-set-parameters {
     description "Set AAA subscriber parameters";
     junos:command "request network-access aaa subscriber set";
     input {
       leaf control-plane-instance {
         type string;
       }
       leaf session-id {
         description "Session id";
         type union {
           type string {
             pattern "<.*>|$.*";
           }
           type uint64 {
             range "1 .. 18446744073709551615";
           }
         }
         mandatory true;
       }
       leaf provisioning-state {
         description "Provisioning state";
         type enumeration {
           enum "none" {
             description "Set provisioning to none";
           }
         }
         mandatory true;
       }
     }
   }
   rpc replay-pending-accounting-stops {
     description "Replay pending acct stops to radius";
     junos:command "request network-access aaa replay pending-accounting-stops";
     input {
       leaf control-plane-instance {
         type string;
       }
     }
   }
   rpc request-accounting-action {
     description "Accounting suspend or baseline";
     junos:command "request network-access aaa accounting";
     input {
       leaf control-plane-instance {
         type string;
       }
       choice accounting_action {
         case suspend {
           leaf suspend {
             description "Suspend accounting";
             type empty;
           }
         }
         case baseline {
           leaf baseline {
             description "Baseline statistics";
             type empty;
           }
         }
         case resume {
           leaf resume {
             description "Resume accounting";
             type empty;
           }
         }
       }
     }
     output {
       choice output_c {
         case output-tag {
           leaf output {
             type string;
           }
         }
         case multichassis-tag {
           anyxml multi-routing-engine-results;
         }
       }
     }
   }
   rpc address-assignment-domain-profile {
     description "Request domain-profile specific command options";
     junos:command "request network-access aaa address-assignment domain-profile";
     input {
       leaf control-plane-instance {
         type string;
       }
       leaf ri-name {
         description "Routing instance name";
         type string;
         mandatory true;
       }
       leaf profile-name {
         description "Domain profile name";
         type string;
         mandatory true;
       }
       leaf action-type {
         junos:cli-feature "nokeyword";
         type enumeration {
           enum "enable-logins" {
             description "Enable subsequent logins";
           }
           enum "disable-logins" {
             description "Disable subsequent logins";
           }
         }
         mandatory true;
       }
     }
     output {
       choice output_c {
         case output-tag {
           leaf output {
             type string;
           }
         }
         case multichassis-tag {
           anyxml multi-routing-engine-results;
         }
       }
     }
   }
   rpc address-assignment-subscriber-group {
     description "Request subscriber-group specific command options";
     junos:command "request network-access aaa address-assignment subscriber-group";
     input {
       leaf control-plane-instance {
         type string;
       }
       leaf subscriber-group-name {
         description "Subscriber group name";
         junos:cli-feature "nokeyword";
         type string;
         mandatory true;
       }
       leaf action-type {
         junos:cli-feature "nokeyword";
         type enumeration {
           enum "enable-logins" {
             description "Enable subsequent logins";
           }
           enum "disable-logins" {
             description "Disable subsequent logins";
           }
         }
         mandatory true;
       }
     }
     output {
       choice output_c {
         case output-tag {
           leaf output {
             type string;
           }
         }
         case multichassis-tag {
           anyxml multi-routing-engine-results;
         }
       }
     }
   }
   rpc address-assignment-drain-pool {
     description "Drain a specific dynamic pool";
     junos:command "request network-access aaa address-assignment drain pool";
     input {
       leaf control-plane-instance {
         type string;
       }
       leaf pool-name {
         description "Pool name";
         junos:cli-feature "nokeyword";
         type string;
         mandatory true;
       }
     }
     output {
       choice output_c {
         case output-tag {
           leaf output {
             type string;
           }
         }
         case multichassis-tag {
           anyxml multi-routing-engine-results;
         }
       }
     }
   }
   rpc aaa-saml-export-sp-metadata {
     description "Export service provider metadata to a file";
     junos:command "request network-access aaa saml export-sp-metadata";
     input {
       leaf control-plane-instance {
         type string;
       }
       leaf access-profile-name {
         description "Access profile name";
         type string;
         mandatory true;
       }
     }
   }
   rpc aaa-saml-load-idp-metadata {
     description "Load an identity provider metadata file";
     junos:command "request network-access aaa saml load-idp-metadata";
     input {
       leaf control-plane-instance {
         type string;
       }
       leaf metadata-id {
         description "Metadata identifier";
         type string;
         mandatory true;
       }
       leaf filename {
         description "File pathname containing metadata to load";
         type string;
         mandatory true;
       }
     }
   }
   rpc request-auto-configuration-reconnect-pending {
     description "Request reconnect of pending out-of-band sessions";
     junos:command "request auto-configuration reconnect-pending";
     output {
       choice output_c {
         case output-tag {
           leaf output {
             type string;
           }
         }
         case multichassis-tag {
           anyxml multi-routing-engine-results;
         }
       }
     }
   }
   rpc request-rps-download-firmware {
     description "Upgrade redundant-power-system firmware";
     junos:command "request redundant-power-system firmware upgrade";
     input {
       leaf member {
         description "Member of virtual chassis configuration";
         type union {
           type string {
             pattern "<.*>|$.*";
           }
           type int32;
         }
         mandatory true;
       }
       leaf server {
         description "TFTP server IP address";
         type jt:ipv4addr;
         mandatory true;
       }
       leaf image {
         description "Firmware image with path";
         type string;
         mandatory true;
       }
     }
   }
   rpc request-rps-multi-backup {
     description "Enable RPS multi-backup";
     junos:command "request redundant-power-system multi-backup";
     input {
       leaf member {
         description "Member of virtual chassis configuration";
         type union {
           type string {
             pattern "<.*>|$.*";
           }
           type int32;
         }
         mandatory true;
       }
     }
   }
   rpc request-rps-no-multi-backup {
     description "Disable RPS multi-backup";
     junos:command "request redundant-power-system no-multi-backup";
     input {
       leaf member {
         description "Member of virtual chassis configuration";
         type union {
           type string {
             pattern "<.*>|$.*";
           }
           type int32;
         }
         mandatory true;
       }
     }
   }
   rpc request-system-mode-change {
     description "Change member's current system-mode configuration";
     junos:command "request chassis system-mode";
     input {
       uses command-forwarding;
       leaf mode {
         junos:cli-feature "nokeyword";
         type enumeration {
           enum "mode-104port" {
             description "104port-mode. This will restart PFE";
           }
           enum "non-oversubscribed-mode" {
             description "Non-oversubscribed-mode. This will restart PFE";
           }
           enum "flexi-pic-mode" {
             description "Flexi-pic-mode. This will restart PFE";
           }
           enum "mode-2x100G" {
             description "PIC mode configuration 2x100G. This will restart PFE and disable VCP ports";
           }
           enum "default-mode" {
             description "Default-mode is oversubscribed mode. This will restart PFE";
           }
         }
         mandatory true;
       }
     }
     output {
       choice output_c {
         case output-tag {
           leaf output {
             type string;
           }
         }
         case multichassis-tag {
           anyxml multi-routing-engine-results;
         }
       }
     }
   }
   rpc request-chassis-device-recorder {
     description "Device recorder configuration";
     junos:command "request chassis device-recorder";
     input {
       uses command-forwarding;
       leaf cmd {
         junos:cli-feature "nokeyword";
         type enumeration {
           enum "enable" {
             description "Enable device recorder";
           }
           enum "disable" {
             description "Disable device recorder";
           }
         }
         mandatory true;
       }
     }
     output {
       choice output_c {
         case output-tag {
           leaf output {
             type string;
           }
         }
         case multichassis-tag {
           anyxml multi-routing-engine-results;
         }
       }
     }
   }
   rpc request-chassis-mic {
     description "Change Media Interface Card status";
     junos:command "request chassis mic";
     input {
       uses command-forwarding;
       leaf fpc-slot {
         description "Slot number of FPC that houses MIC";
         type union {
           type string {
             pattern "<.*>|$.*";
           }
           type uint32;
         }
         mandatory true;
       }
       leaf mic-slot {
         description "MIC slot number";
         type union {
           type string {
             pattern "<.*>|$.*";
           }
           type uint32;
         }
         mandatory true;
       }
       leaf cmd {
         junos:cli-feature "nokeyword";
         type enumeration {
           enum "offline" {
             description "Take MIC offline";
           }
           enum "online" {
             description "Bring MIC online";
           }
         }
         mandatory true;
       }
     }
     output {
       container chassis-mic-state {
         uses chassis-mic-state-block;
       }
     }
   }
   rpc request-chassis-optics {
     description "Change linecard optics status";
     junos:command "request chassis optics";
     input {
       uses command-forwarding;
       leaf fpc-slot {
         description "Slot number of FPC that houses optics";
         type union {
           type string {
             pattern "<.*>|$.*";
           }
           type uint32;
         }
         mandatory true;
       }
       leaf reactivate {
         description "Reactivate linecard optics";
         type empty;
         mandatory true;
       }
     }
     output {
       container chassis-optics-state {
         uses chassis-optics-state-block;
       }
     }
   }
   rpc request-chassis-pic {
     description "Change Physical Interface Card status";
     junos:command "request chassis pic";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf cmd {
         junos:cli-feature "nokeyword";
         type enumeration {
           enum "offline" {
             description "Take PIC offline";
           }
           enum "online" {
             description "Bring PIC online";
           }
         }
         mandatory true;
       }
     }
     output {
       choice output_c {
         case output-tag {
           leaf output {
             type string;
           }
         }
         case multichassis-tag {
           anyxml multi-routing-engine-results;
         }
       }
     }
   }
   rpc request-chassis-port-led-switch-on {
     description "Switch on LED";
     junos:command "request chassis port-led start";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-1g {
           description "All 1Gig ports";
           type empty;
         }
         leaf all-10g {
           description "All 10Gig ports";
           type empty;
         }
         leaf all-25g {
           description "All 25Gig ports";
           type empty;
         }
         leaf all-50g {
           description "All 50Gig ports";
           type empty;
         }
         leaf all-40g {
           description "All 40Gig ports";
           type empty;
         }
         leaf all-100g {
           description "All 100Gig ports";
           type empty;
         }
         leaf all-400g {
           description "All 400Gig ports";
           type empty;
         }
         leaf all-200g {
           description "All 200Gig ports";
           type empty;
         }
         leaf all-800g {
           description "All 800Gig ports";
           type empty;
         }
         leaf all-ports {
           description "All PIC ports";
           type empty;
         }
         leaf pic-port {
           description "PIC port number";
           junos:cli-feature "nokeyword";
           type union {
             type string {
               pattern "<.*>|$.*";
             }
             type uint32;
           }
         }
       }
       leaf duration {
         description "Duration (in seconds) to perform LED blinking";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc request-chassis-port-led-switch-off {
     description "Switch off LED";
     junos:command "request chassis port-led stop";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-1g {
           description "All 1Gig ports";
           type empty;
         }
         leaf all-10g {
           description "All 10Gig ports";
           type empty;
         }
         leaf all-25g {
           description "All 25Gig ports";
           type empty;
         }
         leaf all-50g {
           description "All 50Gig ports";
           type empty;
         }
         leaf all-40g {
           description "All 40Gig ports";
           type empty;
         }
         leaf all-100g {
           description "All 100Gig ports";
           type empty;
         }
         leaf all-400g {
           description "All 400Gig ports";
           type empty;
         }
         leaf all-200g {
           description "All 200Gig ports";
           type empty;
         }
         leaf all-800g {
           description "All 800Gig ports";
           type empty;
         }
         leaf all-ports {
           description "All PIC ports";
           type empty;
         }
         leaf pic-port {
           description "PIC port number";
           junos:cli-feature "nokeyword";
           type union {
             type string {
               pattern "<.*>|$.*";
             }
             type uint32;
           }
         }
       }
     }
     output {
       choice output_c {
         case output-tag {
           leaf output {
             type string;
           }
         }
         case multichassis-tag {
           anyxml multi-routing-engine-results;
         }
       }
     }
   }
   rpc request-chassis-port-led-enable {
     description "Enable LED";
     junos:command "request chassis port-led enable";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-ports {
           description "All PIC ports";
           type empty;
         }
         leaf pic-port {
           description "PIC port number";
           junos:cli-feature "nokeyword";
           type union {
             type string {
               pattern "<.*>|$.*";
             }
             type uint32;
           }
         }
       }
     }
     output {
       choice output_c {
         case output-tag {
           leaf output {
             type string;
           }
         }
         case multichassis-tag {
           anyxml multi-routing-engine-results;
         }
       }
     }
   }
   rpc request-chassis-port-led-disable {
     description "Disable LED";
     junos:command "request chassis port-led disable";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-ports {
           description "All PIC ports";
           type empty;
         }
         leaf pic-port {
           description "PIC port number";
           junos:cli-feature "nokeyword";
           type union {
             type string {
               pattern "<.*>|$.*";
             }
             type uint32;
           }
         }
       }
     }
     output {
       choice output_c {
         case output-tag {
           leaf output {
             type string;
           }
         }
         case multichassis-tag {
           anyxml multi-routing-engine-results;
         }
       }
     }
   }
   rpc request-redundancy-feb {
     description "Change Forwarding Engine Board redundancy status";
     junos:command "request chassis redundancy feb";
     input {
       leaf slot {
         description "FEB slot number";
         type union {
           type string {
             pattern "<.*>|$.*";
           }
           type uint32;
         }
         mandatory true;
       }
       leaf cmd {
         junos:cli-feature "nokeyword";
         type enumeration {
           enum "switch-to-backup" {
             description "Switch mastership to other FEB";
           }
           enum "revert-from-backup" {
             description "Revert mastership back to configured default";
           }
         }
         mandatory true;
       }
     }
     output {
       choice output_c {
         case output-tag {
           leaf output {
             type string;
           }
         }
         case multichassis-tag {
           anyxml multi-routing-engine-results;
         }
       }
     }
   }
   rpc request-chassis-fpc {
     description "Change Flexible PIC Concentrator status";
     junos:command "request chassis fpc";
     input {
       uses command-forwarding;
       leaf slot {
         description "FPC slot number";
         type union {
           type string {
             pattern "<.*>|$.*";
           }
           type uint32;
         }
         mandatory true;
       }
       leaf pfe-instance {
         description "PFE-instance number";
         type union {
           type string {
             pattern "<.*>|$.*";
           }
           type uint32;
         }
       }
       leaf pfe {
         description "Pfe id number";
         type union {
           type string {
             pattern "<.*>|$.*";
           }
           type uint32;
         }
       }
       leaf slc {
         description "SLC ID";
         type union {
           type string {
             pattern "<.*>|$.*";
           }
           type uint32 {
             range "1 .. 2";
           }
         }
       }
       leaf force {
         description "Forcefully restart the FPC";
         type empty;
       }
       leaf cmd {
         junos:cli-feature "nokeyword";
         type enumeration {
           enum "offline" {
             description "Take FPC or PFE-instance offline";
           }
           enum "online" {
             description "Bring FPC or PFE-instance online";
           }
           enum "restart" {
             description "Restart FPC or PFE-instance";
           }
         }
         mandatory true;
       }
       leaf tag {
         description "Firmware tag for online-reload";
         type union {
           type int32;
           type string {
             pattern "<.*>|$.*";
           }
         }
       }
       leaf no-confirm {
         description "Do not ask for confirmation";
         type empty;
       }
     }
     output {
       container chassis-fpc-state {
         uses chassis-fpc-state-block;
       }
     }
   }
   rpc request-fpc-optical-module {
     description "Change optical module status";
     junos:command "request chassis fpc optical-module";
     output {
       choice output_c {
         case output-tag {
           leaf output {
             type string;
           }
         }
         case multichassis-tag {
           anyxml multi-routing-engine-results;
         }
       }
     }
   }
   rpc request-fpc-optical-module-amplifier-chain {
     description "Change amplifier-chain status";
     junos:command "request chassis fpc optical-module amplifier-chain";
     output {
       choice output_c {
         case output-tag {
           leaf output {
             type string;
           }
         }
         case multichassis-tag {
           anyxml multi-routing-engine-results;
         }
       }
     }
   }
   rpc request-fpc-optical-module-ila {
     description "Change inline-amplifier status";
     junos:command "request chassis fpc optical-module amplifier-chain ila";
     output {
       choice output_c {
         case output-tag {
           leaf output {
             type string;
           }
         }
         case multichassis-tag {
           anyxml multi-routing-engine-results;
         }
       }
     }
   }
   rpc request-fpc-optical-module-ila-firmware-upgrade {
     description "Change firmware bundle of inline-amplifier";
     junos:command "request chassis fpc optical-module amplifier-chain ila firmware-upgrade";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-soft-reset {
     description "Perform soft-reset on inline-amplifier";
     junos:command "request chassis fpc optical-module amplifier-chain ila soft-reset";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-hard-reset {
     description "Perform hard-reset on inline-amplifier";
     junos:command "request chassis fpc optical-module amplifier-chain ila hard-reset";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-firmware-upgrade {
     description "Change firmware bundle of optical module";
     junos:command "request chassis fpc optical-module firmware-upgrade";
     input {
       leaf fpc-slot {
         description "FPC slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-chassis-fabric-plane-sfb {
     description "Change Switch Fabric Card status";
     junos:command "request chassis sfb";
     input {
       uses command-forwarding;
       leaf slot {
         description "SFB slot number";
         type union {
           type string {
             pattern "<.*>|$.*";
           }
           type uint32;
         }
         mandatory true;
       }
       leaf cmd {
         junos:cli-feature "nokeyword";
         type enumeration {
           enum "offline" {
             description "Take SFB offline";
           }
           enum "online" {
             description "Bring SFB online";
           }
         }
         mandatory true;
       }
     }
     output {
       container chassis-fabric-plane-state {
         uses chassis-fabric-plane-state-block;
       }
     }
   }
   rpc request-chassis-afeb {
     description "Change Forwarding Engine Board status";
     junos:command "request chassis afeb";
     input {
       leaf cmd {
         junos:cli-feature "nokeyword";
         type enumeration {
           enum "offline" {
             description "Take AFEB offline";
           }
           enum "online" {
             description "Bring AFEB online";
           }
           enum "restart" {
             description "Restart AFEB";
           }
         }
         mandatory true;
       }
     }
     output {
       container chassis-afeb-state {
         uses chassis-afeb-state-block;
       }
     }
   }
   rpc request-chassis-tfeb {
     description "Change Taz Forwarding Engine Board status";
     junos:command "request chassis tfeb";
     input {
       leaf cmd {
         junos:cli-feature "nokeyword";
         type enumeration {
           enum "offline" {
             description "Take TFEB offline";
           }
           enum "online" {
             description "Bring TFEB online";
           }
           enum "restart" {
             description "Restart TFEB";
           }
         }
         mandatory true;
       }
     }
     output {
       container chassis-tfeb-state {
         uses chassis-tfeb-state-block;
       }
     }
   }
   rpc request-chassis-fabric-plane {
     description "Change fabric plane status";
     junos:command "request chassis fabric plane";
     input {
       uses command-forwarding;
       leaf plane {
         description "Fabric plane number";
         junos:cli-feature "nokeyword";
         type union {
           type string {
             pattern "<.*>|$.*";
           }
           type uint32;
         }
         mandatory true;
       }
       leaf which-command {
         junos:cli-feature "nokeyword";
         type enumeration {
           enum "offline" {
             description "Take fabric plane offline";
           }
           enum "online" {
             description "Bring fabric plane online";
           }
         }
         mandatory true;
       }
     }
     output {
       container chassis-fabric-plane-state {
         uses chassis-fabric-plane-state-block;
       }
     }
   }
   rpc request-chassis-fabric-pfe {
     description "Change PFE's fabric status";
     junos:command "request chassis fabric pfe";
     input {
       leaf pfe {
         description "PFE number";
         junos:cli-feature "nokeyword";
         type union {
           type string {
             pattern "<.*>|$.*";
           }
           type uint32 {
             range "0 .. 31";
           }
         }
         mandatory true;
       }
       leaf fpc {
         description "FPC slot number";
         type union {
           type string {
             pattern "<.*>|$.*";
           }
           type uint32;
         }
         mandatory true;
       }
       leaf which-command {
         junos:cli-feature "nokeyword";
         type enumeration {
           enum "offline" {
             description "Offline FPC,PFE's fabric";
           }
         }
         mandatory true;
       }
     }
     output {
       choice output_c {
         case output-tag {
           leaf output {
             type string;
           }
         }
         case multichassis-tag {
           anyxml multi-routing-engine-results;
         }
       }
     }
   }
   rpc request-chassis-fabric-pfe-mask {
     description "Change PFE's fabric status";
     junos:command "request chassis fabric pfe-mask";
     input {
       leaf pfe {
         description "PFE mask";
         junos:cli-feature "nokeyword";
         type union {
           type string {
             pattern "<.*>|$.*";
           }
           type uint32 {
             range "0 .. 4095";
           }
         }
         mandatory true;
       }
       leaf fpc {
         description "FPC slot number";
         type union {
           type string {
             pattern "<.*>|$.*";
           }
           type uint32;
         }
         mandatory true;
       }
       leaf slc {
         description "SLC slot number";
         type union {
           type string {
             pattern "<.*>|$.*";
           }
           type uint32 {
             range "0 .. 3";
           }
         }
         mandatory true;
       }
       leaf which-command {
         junos:cli-feature "nokeyword";
         type enumeration {
           enum "offline" {
             description "Offline FPC,PFE's fabric";
           }
           enum "online" {
             description "Online FPC,PFE's fabric";
           }
           enum "disable" {
             description "Disable FPC,PFE's fabric";
           }
           enum "enable" {
             description "Enable FPC,PFE's fabric";
           }
         }
         mandatory true;
       }
     }
     output {
       choice output_c {
         case output-tag {
           leaf output {
             type string;
           }
         }
         case multichassis-tag {
           anyxml multi-routing-engine-results;
         }
       }
     }
   }
   rpc request-chassis-fabric-upgrade-bandwidth-fpc {
     description "Flexible PIC Concentrator";
     junos:command "request chassis fabric upgrade-bandwidth fpc";
     input {
       choice slot_type {
         case slot {
           leaf slot {
             description "FPC slot number for upgrade";
             type union {
               type string {
                 pattern "<.*>|$.*";
               }
               type uint32;
             }
           }
         }
         case all {
           leaf all {
             description "Upgrade all available/possible FPCs";
             type empty;
           }
         }
       }
     }
     output {
       choice output_c {
         case output-tag {
           leaf output {
             type string;
           }
         }
         case multichassis-tag {
           anyxml multi-routing-engine-results;
         }
       }
     }
   }
   rpc request-chassis-fabric-upgrade-bandwidth-info {
     description "Status of FPC to fabric connections";
     junos:command "request chassis fabric upgrade-bandwidth info";
     output {
       choice output_c {
         case output-tag {
           leaf output {
             type string;
           }
         }
         case multichassis-tag {
           anyxml multi-routing-engine-results;
         }
       }
     }
   }
   rpc request-chassis-spmb {
     description "Change Switch Processor Mezzanine Board status";
     junos:command "request chassis spmb";
     input {
       uses command-forwarding;
       leaf slot {
         description "SPMB slot number";
         type union {
           type string {
             pattern "<.*>|$.*";
           }
           type uint32;
         }
         mandatory true;
       }
       leaf cmd {
         junos:cli-feature "nokeyword";
         type enumeration {
           enum "restart" {
             description "Restart SPMB";
           }
         }
         mandatory true;
       }
     }
     output {
       choice output_c {
         case output-tag {
           leaf output {
             type string;
           }
         }
         case multichassis-tag {
           anyxml multi-routing-engine-results;
         }
       }
     }
   }
   rpc request-chassis-sib {
     description "Change Switch Interface Board status";
     junos:command "request chassis sib";
     input {
       uses command-forwarding;
       leaf slot {
         description "SIB slot number";
         type union {
           type string {
             pattern "<.*>|$.*";
           }
           type uint32;
         }
         mandatory true;
       }
       choice cmd {
         case online-offline {
           leaf online-offline {
             junos:cli-feature "nokeyword";
             type enumeration {
               enum "offline" {
                 description "Take SIB offline";
               }
               enum "online" {
                 description "Bring SIB online";
               }
               enum "restart" {
                 description "Perform Sib restart";
               }
             }
           }
         }
         case start-receiver {
           leaf start-receiver {
             description "Start SIB optical receiver";
             type union {
               type string {
                 pattern "<.*>|$.*";
               }
               type uint32;
             }
           }
         }
         case stop-receiver {
           leaf stop-receiver {
             description "Stop SIB optical receiver";
             type union {
               type string {
                 pattern "<.*>|$.*";
               }
               type uint32;
             }
           }
         }
         case train-rx-tx {
           leaf train-rx-tx {
             junos:cli-feature "nokeyword";
             type enumeration {
               enum "train-link-receive" {
                 description "Train link receiver";
               }
               enum "train-link-transmit" {
                 description "Train link transmitter";
               }
             }
           }
         }
       }
     }
     output {
       choice output_c {
         case output-tag {
           leaf output {
             type string;
           }
         }
         case multichassis-tag {
           anyxml multi-routing-engine-results;
         }
       }
     }
   }
   rpc request-chassis-frutype-replacement {
     description "Perform fru replacement start or stop";
     junos:command "request chassis fru";
     input {
       leaf frutype {
         description "Select frutype";
         junos:cli-feature "nokeyword";
         type enumeration {
           enum "sfb" {
             description "Replace SFB";
           }
         }
         mandatory true;
       }
       leaf replacement {
         description "Starts or stops the fru replacement";
         type enumeration {
           enum "start" {
             description "Start the fru replacement";
           }
           enum "stop" {
             description "Stop the fru replacement";
           }
         }
         mandatory true;
       }
     }
     output {
       choice output_c {
         case output-tag {
           leaf output {
             type string;
           }
         }
         case multichassis-tag {
           anyxml multi-routing-engine-results;
         }
       }
     }
   }
   rpc request-chassis-ccg {
     description "Change clock generator status";
     junos:command "request chassis ccg";
     input {
       leaf slot {
         description "CCG slot number";
         type union {
           type string {
             pattern "<.*>|$.*";
           }
           type uint32 {
             range "0 .. 1";
           }
         }
         mandatory true;
       }
       leaf cmd {
         junos:cli-feature "nokeyword";
         type enumeration {
           enum "offline" {
             description "Take CCG offline";
           }
           enum "online" {
             description "Bring CCG online";
           }
         }
         mandatory true;
       }
     }
     output {
       choice output_c {
         case output-tag {
           leaf output {
             type string;
           }
         }
         case multichassis-tag {
           anyxml multi-routing-engine-results;
         }
       }
     }
   }
   rpc request-chassis-routing-engine {
     description "Change Routing Engine status";
     junos:command "request chassis routing-engine";
     output {
       container chassis-routing-engine-state {
         uses chassis-routing-engine-state-block;
       }
     }
   }
   rpc request-chassis-routing-engine-hard-disk-test {
     description "Run smartd self tests on hard disks";
     junos:command "request chassis routing-engine hard-disk-test";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       container raid-information {
         uses raid-information-block;
       }
     }
   }
   rpc request-chassis-routing-engine-acquire {
     description "Attempt to become master Routing Engine";
     junos:command "request chassis routing-engine master acquire";
     input {
       uses command-forwarding;
       leaf no-confirm {
         description "Do not ask for confirmation";
         type empty;
       }
       leaf check {
         description "Check status of graceful switchover";
         type empty;
       }
     }
     output {
       container chassis-routing-engine-state {
         uses chassis-routing-engine-state-block;
       }
     }
   }
   rpc request-chassis-routing-engine-release {
     description "Request that other Routing Engine become master";
     junos:command "request chassis routing-engine master release";
     input {
       uses command-forwarding;
       leaf no-confirm {
         description "Do not ask for confirmation";
         type empty;
       }
       leaf check {
         description "Check status of graceful switchover";
         type empty;
       }
     }
     output {
       container chassis-routing-engine-state {
         uses chassis-routing-engine-state-block;
       }
     }
   }
   rpc request-chassis-routing-engine-switch {
     description "Toggle mastership between Routing Engines";
     junos:command "request chassis routing-engine master switch";
     input {
       uses command-forwarding;
       leaf no-confirm {
         description "Do not ask for confirmation";
         type empty;
       }
       leaf check {
         description "Check status of graceful switchover";
         type empty;
       }
     }
     output {
       container chassis-routing-engine-state {
         uses chassis-routing-engine-state-block;
       }
     }
   }
   rpc request-feb {
     description "Change Forwarding Engine Board status";
     junos:command "request chassis feb";
     input {
       leaf slot {
         description "FEB slot number";
         type union {
           type string {
             pattern "<.*>|$.*";
           }
           type uint32;
         }
         mandatory true;
       }
       leaf cmd {
         junos:cli-feature "nokeyword";
         type enumeration {
           enum "offline" {
             description "Take FEB offline";
           }
           enum "online" {
             description "Bring FEB online";
           }
           enum "restart" {
             description "Restart FEB";
           }
         }
         mandatory true;
       }
       leaf force {
         description "Force execute the offline/restart command";
         type empty;
       }
     }
     output {
       choice output_c {
         case output-tag {
           leaf output {
             type string;
           }
         }
         case multichassis-tag {
           anyxml multi-routing-engine-results;
         }
       }
     }
   }
   rpc request-chassis-fpc-control-port {
     description "Disable/enable FPC HA control port on SRX5K";
     junos:command "request chassis fpc-control-port";
     input {
       leaf fpc {
         description "FPC slot number";
         type union {
           type string {
             pattern "<.*>|$.*";
           }
           type uint32;
         }
         mandatory true;
       }
       leaf port {
         description "Port number";
         type union {
           type string {
             pattern "<.*>|$.*";
           }
           type int32 {
             range "0 .. 1";
           }
         }
         mandatory true;
       }
       leaf set {
         junos:cli-feature "nokeyword";
         type enumeration {
           enum "enable" {
             description "Enable HA control port";
           }
           enum "disable" {
             description "Disable HA control port";
           }
         }
         mandatory true;
       }
     }
     output {
       choice output_c {
         case output-tag {
           leaf output {
             type string;
           }
         }
         case multichassis-tag {
           anyxml multi-routing-engine-results;
         }
       }
     }
   }
   rpc request-chassis-ha-control-port-transition {
     description "Transit local HA control port0 between FPC and SCB";
     junos:command "request chassis primary-ha-control-port-transition";
     input {
       leaf order {
         junos:cli-feature "nokeyword";
         type enumeration {
           enum "from-fpc-to-scb" {
             description "Transition from FPC to SCB";
           }
           enum "from-scb-to-fpc" {
             description "Transition from SCB to FPC";
           }
         }
         mandatory true;
       }
       leaf fpc {
         description "FPC slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-chassis-cb {
     description "Change Control Board status";
     junos:command "request chassis cb";
     input {
       uses command-forwarding;
       leaf slot {
         description "CB slot number";
         type union {
           type string {
             pattern "<.*>|$.*";
           }
           type uint32;
         }
         mandatory true;
       }
       leaf cmd {
         junos:cli-feature "nokeyword";
         type enumeration {
           enum "offline" {
             description "Take CB offline";
           }
           enum "online" {
             description "Bring CB online";
           }
         }
         mandatory true;
       }
     }
     output {
       choice output_c {
         case output-tag {
           leaf output {
             type string;
           }
         }
         case multichassis-tag {
           anyxml multi-routing-engine-results;
         }
       }
     }
   }
   rpc request-chassis-fpm {
     description "Change craft interface status";
     junos:command "request chassis fpm";
     input {
       uses command-forwarding;
       leaf cmd {
         junos:cli-feature "nokeyword";
         type enumeration {
           enum "resync" {
             description "Resynchronize craft interface";
           }
         }
         mandatory true;
       }
     }
     output {
       container chassis-fpm {
         uses chassis-fpm-block;
       }
     }
   }
   rpc request-chassis-beacon {
     description "Change beacon status";
     junos:command "request chassis beacon";
     input {
       leaf cmd {
         junos:cli-feature "nokeyword";
         type enumeration {
           enum "off" {
             description "Turn beacon off";
           }
           enum "on" {
             description "Turn beacon on";
           }
         }
         mandatory true;
       }
       leaf timer {
         description "Set timer for beacon LED";
         type union {
           type string {
             pattern "<.*>|$.*";
           }
           type uint32 {
             range "1 .. 120";
           }
         }
       }
       choice which-arg {
         case all {
           leaf all {
             description "All beacons";
             type empty;
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
           leaf service-node {
             description "Service node slot number";
             type union {
               type string {
                 pattern "<.*>|$.*";
               }
               type uint32 {
                 range "0 .. 1";
               }
             }
           }
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       container chassis-beacon-information {
         uses chassis-beacon-information-block;
       }
     }
   }
   rpc request-chassis-cluster-control-interface {
     description "Disable/enable HA control-link interface";
     junos:command "request chassis cluster control-interface";
     input {
       leaf node {
         description "Node identifier";
         type union {
           type string {
             pattern "<.*>|$.*";
           }
           type int32 {
             range "0 .. 1";
           }
         }
         mandatory true;
       }
       leaf set {
         junos:cli-feature "nokeyword";
         type enumeration {
           enum "enable" {
             description "Enable HA control interface";
           }
           enum "disable" {
             description "Disable HA control interface";
           }
         }
         mandatory true;
       }
     }
     output {
       choice output_c {
         case output-tag {
           leaf output {
             type string;
           }
         }
         case multichassis-tag {
           anyxml multi-routing-engine-results;
         }
       }
     }
   }
   rpc request-chassis-cluster-failover {
     description "Trigger a manual failover";
     junos:command "request chassis cluster failover";
     input {
       uses command-forwarding;
       choice redundancy-group-id {
         description "Redundancy-group that needs to be failovered to";
         case redundancy-group {
           leaf redundancy-group {
             description "Redundancy-group identifier";
             type union {
               type string {
                 pattern "<.*>|$.*";
               }
               type uint8;
             }
             mandatory true;
           }
         }
       }
     }
     output {
       choice output_c {
         case output-tag {
           leaf output {
             type string;
           }
         }
         case multichassis-tag {
           anyxml multi-routing-engine-results;
         }
       }
     }
   }
   rpc request-chassis-cluster-failover-reset {
     description "Undo the previous failover command";
     junos:command "request chassis cluster failover reset";
     input {
       uses command-forwarding;
       choice redundancy-group-id {
         description "Redundancy-group that needs to be reset";
         case redundancy-group {
           leaf redundancy-group {
             description "Redundancy-group identifier";
             type union {
               type string {
                 pattern "<.*>|$.*";
               }
               type uint8;
             }
             mandatory true;
           }
         }
       }
     }
     output {
       choice output_c {
         case output-tag {
           leaf output {
             type string;
           }
         }
         case multichassis-tag {
           anyxml multi-routing-engine-results;
         }
       }
     }
   }
   rpc request-chassis-cluster-in-service-upgrade {
     description "Initiate in-service-upgrade";
     junos:command "request chassis cluster in-service-upgrade";
     input {
       leaf abort {
         description "Abort in-service-upgrade";
         type empty;
       }
     }
     output {
       choice output_c {
         case output-tag {
           leaf output {
             type string;
           }
         }
         case multichassis-tag {
           anyxml multi-routing-engine-results;
         }
       }
     }
   }
   rpc set-chassis-cluster-configuration-synchronize {
     description "Perform configuration synchronize from primary to secondary node";
     junos:command "request chassis cluster configuration-synchronize";
     output {
       choice output_c {
         case output-tag {
           leaf output {
             type string;
           }
         }
         case multichassis-tag {
           anyxml multi-routing-engine-results;
         }
       }
     }
   }
   rpc request-chassis-ha-failover {
     description "Trigger a manual failover";
     junos:command "request chassis high-availability failover";
     input {
       choice services-redundancy-group-id {
         description "Services redundancy-group that needs to be failovered to";
         case services-redundancy-group {
           leaf services-redundancy-group {
             description "Services redundancy-group identifier";
             type union {
               type string {
                 pattern "<.*>|$.*";
               }
               type uint8 {
                 range "1 .. 255";
               }
             }
             mandatory true;
           }
         }
       }
       leaf peer-id {
         description "Node identifier of the new primary";
         type union {
           type string {
             pattern "<.*>|$.*";
           }
           type int32 {
             range "1 .. 10";
           }
         }
         mandatory true;
       }
     }
     output {
       choice output_c {
         case output-tag {
           leaf output {
             type string;
           }
         }
         case multichassis-tag {
           anyxml multi-routing-engine-results;
         }
       }
     }
   }
   rpc request-chassis-satellite-device-mode {
     description "Satellite device specific commands";
     junos:command "request chassis satellite";
     input {
       leaf interface {
         description "Interface name";
         type string;
         mandatory true;
       }
       leaf device-mode {
         description "Device Mode";
         type enumeration {
           enum "satellite" {
             description "Satellite Mode";
           }
         }
         mandatory true;
       }
     }
     output {
       choice output_c {
         case output-tag {
           leaf output {
             type string;
           }
         }
         case multichassis-tag {
           anyxml multi-routing-engine-results;
         }
       }
     }
   }
   rpc request-chassis-satellite-reboot {
     description "Reboot one or more satellite";
     junos:command "request chassis satellite reboot";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
     }
     output {
       choice output_c {
         case output-tag {
           leaf output {
             type string;
           }
         }
         case multichassis-tag {
           anyxml multi-routing-engine-results;
         }
       }
     }
   }
   rpc request-chassis-satellite-restart {
     description "Restart a process on one or more satellite";
     junos:command "request chassis satellite restart";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf process {
         description "Remote fpc shell command";
         junos:cli-feature "nokeyword";
         type enumeration {
           enum "packet-forwarding-engine" {
             description "SPFE process";
           }
           enum "discovery-and-provisioning-daemon" {
             description "DPD process";
           }
           enum "chassis-management-daemon" {
             description "LCMD process";
           }
           enum "api-management-daemon" {
             description "AMD process";
           }
           enum "ppman" {
             description "PPMAN process";
           }
           enum "ppman-lite" {
             description "PPMAN-lite process";
           }
         }
         mandatory true;
       }
     }
     output {
       choice output_c {
         case output-tag {
           leaf output {
             type string;
           }
         }
         case multichassis-tag {
           anyxml multi-routing-engine-results;
         }
       }
     }
   }
   rpc request-chassis-satellite-shell-command {
     description "Execute shell command on one or more satellite";
     junos:command "request chassis satellite shell-command";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf remote-command {
         description "Remote fpc shell command";
         junos:cli-feature "nokeyword";
         type string;
         mandatory true;
       }
     }
     output {
       choice output_c {
         case output-tag {
           leaf output {
             type string;
           }
         }
         case multichassis-tag {
           anyxml multi-routing-engine-results;
         }
       }
     }
   }
   rpc request-chassis-satellite-file-copy {
     description "File copy";
     junos:command "request chassis satellite file-copy";
     input {
       leaf cmd {
         junos:cli-feature "nokeyword";
         type enumeration {
           enum "local" {
             description "Local user";
           }
           enum "remote" {
             description "Remote user";
           }
         }
       }
       leaf source {
         description "URL of source file e.g. For SD, use sd100:/..";
         junos:cli-feature "nokeyword";
         type string;
       }
       leaf destination {
         description "URL of destination file e.g. For SD, use sd100:/..";
         junos:cli-feature "nokeyword";
         type string;
       }
     }
     output {
       choice output_c {
         case output-tag {
           leaf output {
             type string;
           }
         }
         case multichassis-tag {
           anyxml multi-routing-engine-results;
         }
       }
     }
   }
   rpc request-chassis-satellite-login {
     description "Connect to satellite device";
     junos:command "request chassis satellite login";
     input {
       leaf fpc-slot {
         description "Satellite slot number";
         type union {
           type string {
             pattern "<.*>|$.*";
           }
           type uint32 {
             range "65 .. 254";
           }
         }
       }
       leaf interface-name {
         description "Name of the interface";
         type string;
       }
     }
     output {
       choice output_c {
         case output-tag {
           leaf output {
             type string;
           }
         }
         case multichassis-tag {
           anyxml multi-routing-engine-results;
         }
       }
     }
   }
   rpc request-chassis-satellite-beacon {
     description "Change beacon status";
     junos:command "request chassis satellite beacon";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf cmd {
         junos:cli-feature "nokeyword";
         type enumeration {
           enum "off" {
             description "Beacon(s) in OFF state";
           }
           enum "on" {
             description "Beacon(s) in ON state";
           }
         }
         mandatory true;
       }
     }
     output {
       choice output_c {
         case output-tag {
           leaf output {
             type string;
           }
         }
         case multichassis-tag {
           anyxml multi-routing-engine-results;
         }
       }
     }
   }
   rpc request-chassis-satellite-disable {
     description "Disable satellite";
     junos:command "request chassis satellite disable";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-enable {
     description "Enable satellite";
     junos:command "request chassis satellite enable";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-install {
     description "Convert satellite device to standalone Junos device";
     junos:command "request chassis satellite install";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf package-name {
         description "URL or pathname of package";
         junos:cli-feature "nokeyword";
         type jt:filename;
       }
       leaf no-confirm {
         description "Do not ask for confirmation";
         type empty;
       }
     }
     output {
       choice output_c {
         case output-tag {
           leaf output {
             type string;
           }
         }
         case multichassis-tag {
           anyxml multi-routing-engine-results;
         }
       }
     }
   }
   rpc set-chassis-pic-mode-to-intraconnect {
     description "Set the mode to intraconnect";
     junos:command "request chassis pic-mode intraconnect";
     input {
       uses command-forwarding;
     }
     output {
       choice output_c {
         case output-tag {
           leaf output {
             type string;
           }
         }
         case multichassis-tag {
           anyxml multi-routing-engine-results;
         }
       }
     }
   }
   rpc set-chassis-pic-mode-to-vc {
     description "Set the mode to virtual-chassis";
     junos:command "request chassis pic-mode virtual-chassis";
     input {
       uses command-forwarding;
     }
     output {
       choice output_c {
         case output-tag {
           leaf output {
             type string;
           }
         }
         case multichassis-tag {
           anyxml multi-routing-engine-results;
         }
       }
     }
   }
   rpc self-mirror-enable-disable {
     description "Enable or disable port-mirroring";
     junos:command "request forwarding-options port-mirroring";
     input {
       leaf instance {
         description "Name of port-mirroring instance";
         type string;
         mandatory true;
       }
       leaf family {
         description "Family of port-mirroring instance";
         type enumeration {
           enum "inet" {
             description "IPv4 instance";
           }
           enum "inet6" {
             description "IPv6 instance";
           }
           enum "any" {
             description "Any instance";
           }
         }
       }
       choice which-cmd {
         case self-mirror-stop {
           leaf self-mirror-stop {
             description "Stop the capture";
             type empty;
           }
         }
         case self-mirror-start {
           leaf self-mirror-start {
             description "Duration in seconds";
             default "300";
             units "seconds";
             type union {
               type string {
                 pattern "<.*>|$.*";
               }
               type int32 {
                 range "45 .. 1800";
               }
             }
           }
         }
       }
     }
     output {
       container helper-self-mirror-enable-disable {
         uses helper-self-mirror-enable-disable-block;
       }
     }
   }
   rpc request-genisoimage {
     description "Generate ISO image";
     junos:command "request genisoimage";
     input {
       leaf input-file {
         description "Input file for ISO image generation";
         junos:cli-feature "nokeyword";
         type string;
       }
       leaf iso-file {
         description "Output file for ISO image";
         junos:cli-feature "nokeyword";
         type string;
       }
     }
     output {
       choice output_c {
         case output-tag {
           leaf output {
             type string;
           }
         }
         case multichassis-tag {
           anyxml multi-routing-engine-results;
         }
       }
     }
   }
   rpc request-virtual-machine-package-add {
     description "Add a virtual-machine package";
     junos:command "request virtual-machine-package add";
     input {
       leaf package-name {
         description "Name of package";
         junos:cli-feature "nokeyword";
         type string {
           junos:posix-pattern "^[a-zA-Z0-9.:/_-]+$";
           junos:pattern-message "Package name must be a string of alphanumericals, dashes, underscores, dots, colons or slashes";
         }
         mandatory true;
       }
       leaf image-name {
         description "URL or pathname of image";
         type string {
           junos:posix-pattern "^[a-zA-Z0-9.:/_-]+$";
           junos:pattern-message "Image name must be a string of alphanumericals, dashes, underscores, dots, colons or slashes";
         }
         mandatory true;
       }
       leaf descriptor-file-name {
         description "URL or pathname of XML config file";
         type string {
           junos:posix-pattern "^[a-zA-Z0-9.:/_-]+$";
           junos:pattern-message "Descriptor name must be a string of alphanumericals, dashes, underscores, dots, colons or slashes";
         }
         mandatory true;
       }
       leaf bootstrap-config-name {
         description "URL or pathname of bootstrap config file";
         type string {
           junos:posix-pattern "^[a-zA-Z0-9.:/_-]+$";
           junos:pattern-message "Bootstrap config name must be a string of alphanumericals, dashes, underscores, dots, colons or slashes";
         }
       }
       leaf bootstrap-script-name {
         description "URL or pathname of bootstrap python script";
         type string {
           junos:posix-pattern "^[a-zA-Z0-9.:/_-]+$";
           junos:pattern-message "Bootstrap script name must be a string of alphanumericals, dashes, underscores, dots, colons or slashes";
         }
       }
     }
     output {
       choice output_c {
         case output-tag {
           leaf output {
             type string;
           }
         }
         case multichassis-tag {
           anyxml multi-routing-engine-results;
         }
       }
     }
   }
   rpc request-virtual-machine-package-delete {
     description "Delete a virtual-machine package";
     junos:command "request virtual-machine-package delete";
     input {
       leaf package-name {
         description "URL or pathname of package";
         junos:cli-feature "nokeyword";
         type string;
         mandatory true;
       }
     }
     output {
       choice output_c {
         case output-tag {
           leaf output {
             type string;
           }
         }
         case multichassis-tag {
           anyxml multi-routing-engine-results;
         }
       }
     }
   }
   rpc request-virtual-network-functions {
     description "Perform virtual-network-functions operations";
     junos:command "request virtual-network-functions";
     input {
       leaf vnf-name {
         description "VNF Name";
         junos:cli-feature "nokeyword";
         type string {
           length "1 .. 256";
           junos:posix-pattern "^[[:alnum:]._-]+$";
           junos:pattern-message "VNF name must be a string of alphanumericals, dashes or underscores";
         }
         mandatory true;
       }
       choice vnf-request {
         case restart {
           leaf restart {
             description "Restart VNF";
             type empty;
           }
         }
         case start {
           leaf start {
             description "Start VNF";
             type empty;
           }
         }
         case stop {
           leaf stop {
             description "Stop VNF";
             type empty;
           }
         }
         case console {
           leaf console {
             description "Console to VNF";
             type empty;
           }
         }
         case ssh {
           leaf ssh {
             description "Ssh";
             type empty;
           }
         }
         case telnet {
           leaf telnet {
             description "Telnet";
             type empty;
           }
         }
       }
       leaf force {
         description "Enable force access ";
         type empty;
       }
       leaf user-name {
         description "User name for VNF";
         type string {
           length "1 .. 64";
         }
       }
     }
     output {
       container request-vnf-information {
         uses request-vnf-information-block;
       }
     }
   }
   rpc request-load-configuration {
     description "Load certain configuration";
     junos:command "request load";
     input {
       leaf configuration-file {
         description "Configuration file name";
         junos:cli-feature "nokeyword";
         type string;
         mandatory true;
       }
       leaf format {
         description "Configuration file format";
         junos:cli-feature "nokeyword";
         type string;
       }
       leaf operation {
         description "Action to take on configuration file";
         junos:cli-feature "nokeyword";
         type enumeration {
           enum "merge" {
             description "Merge contents with existing configuration";
           }
           enum "override" {
             description "Override existing configuration";
           }
         }
       }
       leaf on-virtual-machine {
         description "VM on which configuration file shall be loaded";
         junos:cli-feature "nokeyword";
         type string;
       }
     }
     output {
       choice output_c {
         case output-tag {
           leaf output {
             type string;
           }
         }
         case multichassis-tag {
           anyxml multi-routing-engine-results;
         }
       }
     }
   }
   rpc request-packet-capture-start {
     description "Start packet-capture ";
     junos:command "request packet-capture start";
     input {
       leaf capture-file {
         description "Capture file name";
         type string {
           length "1 .. 1024";
           junos:posix-pattern "![/ %]";
           junos:pattern-message "Must not contain \'/\', % or a space";
         }
       }
       leaf size {
         description "Maximum file size";
         type string;
       }
       leaf maximum-capture-size {
         description "Max packet capture length";
         default "1514";
         type union {
           type string {
             pattern "<.*>|$.*";
           }
           type uint32 {
             range "68 .. 10000";
           }
         }
       }
       leaf bidirectional {
         description "Allow to collect bidirectional info";
         type empty;
       }
       leaf count {
         description "Collect the number of the packet";
         default "100";
         type union {
           type string {
             pattern "<.*>|$.*";
           }
           type uint32 {
             range "10 .. 1000000";
           }
         }
       }
       leaf source-prefix {
         description "Source IPv4/IPv6 address prefix";
         type jt:ipprefix;
       }
       leaf destination-prefix {
         description "Destination IPv4/IPv6 address prefix";
         type jt:ipprefix;
       }
       leaf interface {
         description "Logical interface";
         type string;
       }
       leaf protocol {
         description "Match IP protocol type";
         type string;
       }
       leaf source-port {
         description "Source port";
         type string;
       }
       leaf destination-port {
         description "Destination port";
         type string;
       }
     }
     output {
       container request-packet-capture-start-result {
         uses request-packet-capture-start-result-block;
       }
     }
   }
   rpc request-packet-capture-stop {
     description "Stop packet-capture";
     junos:command "request packet-capture stop";
     output {
       container request-packet-capture-stop-result {
         uses request-packet-capture-stop-result-block;
       }
     }
   }
   rpc request-wlan-access-point-restart {
     description "Restart operation";
     junos:command "request wlan access-point restart";
     input {
       leaf wlan-access-point-name {
         description "Name of the access point";
         junos:cli-feature "nokeyword";
         type string {
           junos:posix-pattern "^[A-Za-z][_0-9A-Za-z-]{0,15}$";
           junos:pattern-message "Must be a string beginning with a letter and consisting of no more than 16 total letters, numbers, dashes and underscores.";
         }
         mandatory true;
       }
     }
     output {
       choice output_c {
         case output-tag {
           leaf output {
             type string;
           }
         }
         case multichassis-tag {
           anyxml multi-routing-engine-results;
         }
       }
     }
   }
   rpc request-wlan-access-point-reset-interface {
     description "Reset to factory settings for wlan interface";
     junos:command "request wlan access-point reset interface";
     input {
       leaf wlan-interface-name {
         description "Name of wlan interface";
         junos:cli-feature "nokeyword";
         type string;
         mandatory true;
       }
     }
     output {
       choice output_c {
         case output-tag {
           leaf output {
             type string;
           }
         }
         case multichassis-tag {
           anyxml multi-routing-engine-results;
         }
       }
     }
   }
   rpc request-wlan-access-point-packet-capture-start {
     description "Start the packet capture";
     junos:command "request wlan access-point packet-capture start";
     input {
       leaf wlan-access-point-name {
         description "Name of the access point";
         junos:cli-feature "nokeyword";
         type string {
           junos:posix-pattern "^[A-Za-z][_0-9A-Za-z-]{0,15}$";
           junos:pattern-message "Must be a string beginning with a letter and consisting of no more than 16 total letters, numbers, dashes and underscores.";
         }
         mandatory true;
       }
       leaf interface {
         description "Name of the interface";
         type enumeration {
           enum "Bridge" {
             description "Bridge interface on the access point";
           }
           enum "Ethernet" {
             description "Ethernet interface on the access point";
           }
           enum "Radio1VAP0" {
             description "Radio 1 VAP 0 interface on the access point";
           }
           enum "Radio1VAP1" {
             description "Radio 1 VAP 1 interface on the access point";
           }
           enum "Radio1VAP2" {
             description "Radio 1 VAP 2 interface on the access point";
           }
           enum "Radio1VAP3" {
             description "Radio 1 VAP 3 interface on the access point";
           }
           enum "Radio1VAP4" {
             description "Radio 1 VAP 4 interface on the access point";
           }
           enum "Radio1VAP5" {
             description "Radio 1 VAP 5 interface on the access point";
           }
           enum "Radio1VAP6" {
             description "Radio 1 VAP 6 interface on the access point";
           }
           enum "Radio1VAP7" {
             description "Radio 1 VAP 7 interface on the access point";
           }
           enum "Radio2VAP0" {
             description "Radio 2 VAP 0 interface on the access point";
           }
           enum "Radio2VAP1" {
             description "Radio 2 VAP 1 interface on the access point";
           }
           enum "Radio2VAP2" {
             description "Radio 2 VAP 2 interface on the access point";
           }
           enum "Radio2VAP3" {
             description "Radio 2 VAP 3 interface on the access point";
           }
           enum "Radio2VAP4" {
             description "Radio 2 VAP 4 interface on the access point";
           }
           enum "Radio2VAP5" {
             description "Radio 2 VAP 5 interface on the access point";
           }
           enum "Radio2VAP6" {
             description "Radio 2 VAP 6 interface on the access point";
           }
           enum "Radio2VAP7" {
             description "Radio 2 VAP 7 interface on the access point";
           }
         }
         mandatory true;
       }
       leaf duration {
         description "Capture duration";
         default "60";
         units "seconds";
         type union {
           type string {
             pattern "<.*>|$.*";
           }
           type uint32 {
             range "10 .. 3600";
           }
         }
       }
       leaf filename {
         description "Name of the captured file";
         type string;
       }
       leaf size {
         description "Maximum file size";
         default "1024";
         units "kilobytes";
         type union {
           type string {
             pattern "<.*>|$.*";
           }
           type uint32 {
             range "64 .. 4096";
           }
         }
       }
       leaf promiscuous {
         description "Enable promiscuous mode";
         type empty;
       }
       leaf filter-mac {
         description "MAC address of the interface";
         type jt:mac-addr;
       }
     }
     output {
       container wlan-access-point-packet-capture-start {
         uses wlan-access-point-packet-capture-start-block;
       }
     }
   }
   rpc request-wlan-access-point-packet-capture-stop {
     description "Stop the packet capture";
     junos:command "request wlan access-point packet-capture stop";
     input {
       leaf wlan-access-point-name {
         description "Name of the access point";
         junos:cli-feature "nokeyword";
         type string {
           junos:posix-pattern "^[A-Za-z][_0-9A-Za-z-]{0,15}$";
           junos:pattern-message "Must be a string beginning with a letter and consisting of no more than 16 total letters, numbers, dashes and underscores.";
         }
         mandatory true;
       }
     }
     output {
       container wlan-access-point-packet-capture-stop {
         uses wlan-access-point-packet-capture-stop-block;
       }
     }
   }
   rpc activate-wireless-modem {
     description "Activate the modem";
     junos:command "request modem wireless activate";
     output {
       choice output_c {
         case output-tag {
           leaf output {
             type string;
           }
         }
         case multichassis-tag {
           anyxml multi-routing-engine-results;
         }
       }
     }
   }
   rpc request-modem-wireless-activate-iota {
     description "Internet Over The Air Activation";
     junos:command "request modem wireless activate iota";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc request-modem-wireless-activate-otasp {
     description "Over The Air Service Provisioning";
     junos:command "request modem wireless activate otasp";
     input {
       leaf interface-name {
         description "Name of physical interface";
         junos:cli-feature "nokeyword";
         type string;
         mandatory true;
       }
       leaf dial-string {
         type string;
         mandatory true;
       }
     }
     output {
       choice output_c {
         case output-tag {
           leaf output {
             type string;
           }
         }
         case multichassis-tag {
           anyxml multi-routing-engine-results;
         }
       }
     }
   }
   rpc request-modem-wireless-activate-manual {
     description "Manual Activation";
     junos:command "request modem wireless activate manual";
     input {
       leaf interface-name {
         description "Name of physical interface";
         junos:cli-feature "nokeyword";
         type string;
         mandatory true;
       }
       leaf msl {
         description "Master Subsidy Lock";
         type string {
           length "1 .. 6";
           junos:posix-pattern "^([0-9]{1,6})$";
           junos:pattern-message "Can contain up to 6 digits";
         }
         mandatory true;
       }
       leaf mdn {
         description "Mobile Dictonary Number";
         type string {
           length "1 .. 10";
           junos:posix-pattern "^([0-9]{1,10})$";
           junos:pattern-message "Can contain up to 10 digits";
         }
         mandatory true;
       }
       leaf imsi {
         description "International Mobile Station Identity";
         type string {
           length "1 .. 15";
           junos:posix-pattern "^([0-9]{1,15})$";
           junos:pattern-message "Can contain up to 10 digits";
         }
         mandatory true;
       }
       leaf sid {
         description "System identification";
         type union {
           type string {
             pattern "<.*>|$.*";
           }
           type uint32 {
             range "0 .. 32767";
           }
         }
       }
       leaf nid {
         description "Network identification";
         type union {
           type string {
             pattern "<.*>|$.*";
           }
           type uint32 {
             range "0 .. 65535";
           }
         }
       }
       leaf sip-user-id {
         description "SIP user ID";
         type string;
       }
       leaf sip-password {
         description "SIP password";
         type string;
       }
     }
     output {
       choice output_c {
         case output-tag {
           leaf output {
             type string;
           }
         }
         case multichassis-tag {
           anyxml multi-routing-engine-results;
         }
       }
     }
   }
   rpc request-gsm-sim-unlock {
     description "Unlock SIM";
     junos:command "request modem wireless sim-unlock";
     input {
       leaf interface-name {
         description "Name of physical interface";
         junos:cli-feature "nokeyword";
         type string;
         mandatory true;
       }
       leaf pin {
         description "SIM unlock code (PIN)";
         type string {
           length "4 .. 8";
           junos:posix-pattern "^([0-9]{4,8})$";
           junos:pattern-message "PIN must be 4 to 8 digits in length";
         }
         mandatory true;
       }
     }
     output {
       choice output_c {
         case output-tag {
           leaf output {
             type string;
           }
         }
         case multichassis-tag {
           anyxml multi-routing-engine-results;
         }
       }
     }
   }
   rpc request-gsm-sim-unblock {
     description "Unblock SIM";
     junos:command "request modem wireless sim-unblock";
     input {
       leaf interface-name {
         description "Name of physical interface";
         junos:cli-feature "nokeyword";
         type string;
         mandatory true;
       }
       leaf puk {
         description "SIM unblock code (PUK)";
         type string {
           length 8;
           junos:posix-pattern "^([0-9]{1,9})$";
           junos:pattern-message "PUK must be 8 digits";
         }
         mandatory true;
       }
       leaf pin {
         description "New SIM unlock code (PIN) to be set";
         type string {
           length "4 .. 8";
           junos:posix-pattern "^([0-9]{4,8})$";
           junos:pattern-message "PIN must be 4 to 8 digits in length";
         }
         mandatory true;
       }
     }
     output {
       choice output_c {
         case output-tag {
           leaf output {
             type string;
           }
         }
         case multichassis-tag {
           anyxml multi-routing-engine-results;
         }
       }
     }
   }
   rpc request-gsm-sim-lock {
     description "Enable or disable SIM lock";
     junos:command "request modem wireless sim-lock";
     input {
       leaf interface-name {
         description "Name of physical interface";
         junos:cli-feature "nokeyword";
         type string;
         mandatory true;
       }
       leaf pin {
         description "SIM unlock code (PIN)";
         type string {
           length "4 .. 8";
           junos:posix-pattern "^([0-9]{4,8})$";
           junos:pattern-message "PIN must be 4 to 8 digits in length";
         }
         mandatory true;
       }
       leaf enable-disable {
         junos:cli-feature "nokeyword";
         type enumeration {
           enum "enable" {
             description "Enable SIM lock";
           }
           enum "disable" {
             description "Disable SIM lock";
           }
         }
         mandatory true;
       }
     }
     output {
       choice output_c {
         case output-tag {
           leaf output {
             type string;
           }
         }
         case multichassis-tag {
           anyxml multi-routing-engine-results;
         }
       }
     }
   }
   rpc request-gsm-change-pin {
     description "Change PIN";
     junos:command "request modem wireless change-pin";
     input {
       leaf interface-name {
         description "Name of physical interface";
         junos:cli-feature "nokeyword";
         type string;
         mandatory true;
       }
       leaf old-pin {
         description "Current SIM unlock code (PIN)";
         type string {
           length "4 .. 8";
           junos:posix-pattern "^([0-9]{4,8})$";
           junos:pattern-message "PIN must be 4 to 8 digits in length";
         }
         mandatory true;
       }
       leaf new-pin {
         description "New SIM unlock code (PIN) to be set";
         type string {
           length "4 .. 8";
           junos:posix-pattern "^([0-9]{4,8})$";
           junos:pattern-message "PIN must be 4 to 8 digits in length";
         }
         mandatory true;
       }
     }
     output {
       choice output_c {
         case output-tag {
           leaf output {
             type string;
           }
         }
         case multichassis-tag {
           anyxml multi-routing-engine-results;
         }
       }
     }
   }
   rpc request-fota {
     description "Enable or disable FOTA upgrade";
     junos:command "request modem wireless fota";
     input {
       leaf interface-name {
         description "Name of physical interface";
         junos:cli-feature "nokeyword";
         type string;
         mandatory true;
       }
       leaf fota-toggle {
         description "Enable/Disable FOTA";
         junos:cli-feature "nokeyword";
         type enumeration {
           enum "enable" {
             description "Enable FOTA";
           }
           enum "disable" {
             description "Disable FOTA";
           }
         }
         mandatory true;
       }
     }
     output {
       choice output_c {
         case output-tag {
           leaf output {
             type string;
           }
         }
         case multichassis-tag {
           anyxml multi-routing-engine-results;
         }
       }
     }
   }
   rpc request-dns-conn-monitor {
     description "Enable or disable DNS connectivity monitor";
     junos:command "request modem wireless dns-conn-monitor";
     input {
       leaf interface-name {
         description "Name of physical interface";
         junos:cli-feature "nokeyword";
         type string;
         mandatory true;
       }
       leaf dns-conn-monitor-toggle {
         description "Enable/Disable DNS connectivity";
         junos:cli-feature "nokeyword";
         type enumeration {
           enum "enable" {
             description "Enable DNS connectivity";
           }
           enum "disable" {
             description "Disable DNS connectivity";
           }
         }
         mandatory true;
       }
     }
     output {
       choice output_c {
         case output-tag {
           leaf output {
             type string;
           }
         }
         case multichassis-tag {
           anyxml multi-routing-engine-results;
         }
       }
     }
   }
   rpc request-fota-upgrade {
     description "Upgrade FOTA modem firmware";
     junos:command "request modem wireless upgrade";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc request-gsm-create-profile {
     description "Create APN profile";
     junos:command "request modem wireless create-profile";
     input {
       leaf interface-name {
         description "Name of physical interface";
         junos:cli-feature "nokeyword";
         type string;
         mandatory true;
       }
       leaf slot {
         description "SIM slot number";
         type union {
           type string {
             pattern "<.*>|$.*";
           }
           type int32;
         }
         mandatory true;
       }
       leaf profile-id {
         description "Profile Id";
         type union {
           type string {
             pattern "<.*>|$.*";
           }
           type int32 {
             range "1 .. 16";
           }
         }
         mandatory true;
       }
       leaf sip-user-id {
         description "SIP User ID";
         type string {
           length "1 .. 63";
         }
       }
       leaf sip-password {
         description "SIP Password";
         type string {
           length "1 .. 63";
         }
       }
       leaf access-point-name {
         description "Access Point Name (APN)";
         type string {
           length "1 .. 63";
         }
         mandatory true;
       }
       leaf authentication-method {
         description "Authentication method";
         type enumeration {
           enum "none" {
             description "None Authentication Protocol";
           }
           enum "pap" {
             description "Password Authentication Protocol";
           }
           enum "chap" {
             description "Challenge Handshake Authentication Protocol";
           }
         }
       }
       leaf ip-version {
         description "IP Version";
         type enumeration {
           enum "ipv4v6" {
             description "Both IPv4 and IPv6";
           }
           enum "ipv4" {
             description "IPv4 Only";
           }
           enum "ipv6" {
             description "IPv6 Only";
           }
         }
       }
     }
     output {
       choice output_c {
         case output-tag {
           leaf output {
             type string;
           }
         }
         case multichassis-tag {
           anyxml multi-routing-engine-results;
         }
       }
     }
   }
   rpc request-gsm-delete-profile {
     description "Delete APN profile";
     junos:command "request modem wireless delete-profile";
     input {
       leaf interface-name {
         description "Name of physical interface";
         junos:cli-feature "nokeyword";
         type string;
         mandatory true;
       }
       leaf slot {
         description "SIM slot number";
         type union {
           type string {
             pattern "<.*>|$.*";
           }
           type int32;
         }
         mandatory true;
       }
       leaf profile-id {
         description "Profile Id";
         type union {
           type string {
             pattern "<.*>|$.*";
           }
           type int32 {
             range "1 .. 16";
           }
         }
         mandatory true;
       }
     }
     output {
       choice output_c {
         case output-tag {
           leaf output {
             type string;
           }
         }
         case multichassis-tag {
           anyxml multi-routing-engine-results;
         }
       }
     }
   }
   rpc request-wireless-wan-adapter-firmware-upgrade-auto {
     description "Automatically upgrade the firmware";
     junos:command "request wireless-wan adapter firmware upgrade auto";
     input {
       leaf apdapter-name {
         description "Name of the adapter";
         junos:cli-feature "nokeyword";
         type string;
         mandatory true;
       }
     }
     output {
       choice output_c {
         case output-tag {
           leaf output {
             type string;
           }
         }
         case multichassis-tag {
           anyxml multi-routing-engine-results;
         }
       }
     }
   }
   rpc request-wireless-wan-adapter-firmware-upgrade-manual {
     description "Manually upgrade the firmware";
     junos:command "request wireless-wan adapter firmware upgrade manual";
     input {
       leaf apdapter-name {
         description "Name of the adapter";
         junos:cli-feature "nokeyword";
         type string;
         mandatory true;
       }
       leaf url {
         description "Manually specified HTTP URL firmware";
         type string {
           junos:posix-pattern "^http://[[:alnum:]]((([[:alnum:]_%+-:/.~]*)*)?)?.(bin)$";
           junos:pattern-message "Invalid http URL. Syntax: http://<server>/<package.bin>";
         }
         mandatory true;
       }
     }
     output {
       choice output_c {
         case output-tag {
           leaf output {
             type string;
           }
         }
         case multichassis-tag {
           anyxml multi-routing-engine-results;
         }
       }
     }
   }
   rpc request-wan-acceleration-login-fpc {
     description "Login to Flexible PIC Concentrator";
     junos:command "request wan-acceleration login fpc";
     input {
       leaf slot {
         description "FPC slot number";
         junos:cli-feature "nokeyword";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-protection-group-ethernet-aps {
     description "Ethernet APS related operations";
     junos:command "request protection-group ethernet-aps";
     input {
       leaf maintenance-domain {
         description "Name of maintenance domain";
         type string {
           length "1 .. 45";
         }
         mandatory true;
       }
       leaf maintenance-association {
         description "Name of maintenance association";
         type string {
           length "1 .. 45";
         }
         mandatory true;
       }
       leaf eaps-action {
         junos:cli-feature "nokeyword";
         type enumeration {
           enum "switch-to-working" {
             description "Switch data path to use working path";
           }
           enum "switch-to-protect" {
             description "Switch data path to use protection path";
           }
           enum "lockout" {
             description "Lockout protection";
           }
           enum "force-switch" {
             description "Force switch data path to use protection path";
           }
           enum "manual-switch" {
             description "Manual switch data path to use protection path";
           }
           enum "exercise" {
             description "Excercise APS protocol";
           }
           enum "clear" {
             description "Clears active local command";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-protection-group-erps-clear {
     description "Clears active local commands";
     junos:command "request protection-group ethernet-ring clear";
     input {
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-manual-switch {
     description "Manual switch data path to use protection path";
     junos:command "request protection-group ethernet-ring manual-switch";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-force-switch {
     description "Force switch data path to use protection path";
     junos:command "request protection-group ethernet-ring force-switch";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-tdr-interface-diagnostics {
     description "Enter TDR interface name";
     junos:command "request diagnostics tdr start interface";
     input {
       leaf interface-name {
         description "Interface name";
         junos:cli-feature "nokeyword";
         type string;
       }
     }
   }
   rpc abort-tdr-interface-diagnostics {
     description "Enter TDR interface name";
     junos:command "request diagnostics tdr abort interface";
     input {
       leaf interface-name {
         description "Interface name";
         junos:cli-feature "nokeyword";
         type string;
       }
     }
   }
   rpc request-evpn {
     junos:command "request evpn";
     input {
       leaf validate-maintenance-mode-pre-checks {
         description "Validate pre-checks for evpn maintenance mode";
         type enumeration {
           enum "erb-leaf" {
             description "EVPN ERB style of deployment for leaf node";
           }
         }
       }
     }
     output {
       choice output_c {
         case output-tag {
           leaf output {
             type string;
           }
         }
         case multichassis-tag {
           anyxml multi-routing-engine-results;
         }
       }
     }
   }
   rpc get-flight-recorder-information {
     description "Debug high cpu issues and scheduler slips";
     junos:command "request flight-recorder set high-cpu";
     input {
       leaf disable {
         description "Disable the flight recorder";
         type empty;
       }
       leaf logical-system {
         description "Enable logical systems";
         type empty;
       }
       leaf cpu-threshold {
         description "Threshold over which the collection is triggered";
         type union {
           type string {
             pattern "<.*>|$.*";
           }
           type uint32 {
             range "1 .. 400";
           }
         }
       }
       leaf polling-frequency {
         description "Frequency of polling for high cpu";
         type union {
           type string {
             pattern "<.*>|$.*";
           }
           type uint32 {
             range "5 .. 100";
           }
         }
       }
       leaf backoff-duration {
         description "Time to wait between two snapshots";
         type union {
           type string {
             pattern "<.*>|$.*";
           }
           type uint32 {
             range "10 .. 1000";
           }
         }
       }
       leaf collect-core {
         description "Whether to take a running core with every snapshot";
         type empty;
       }
       leaf num-snapshots {
         description "How many snapshots to collect before quitting";
         type union {
           type string {
             pattern "<.*>|$.*";
           }
           type uint32 {
             range "1 .. 20";
           }
         }
       }
     }
     output {
       container flight-recorder-information {
         uses flight-recorder-information-block;
       }
     }
   }
   rpc request-l2ckt-switchover {
     description "Perform l2circuit switchover";
     junos:command "request l2circuit-switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         type jt:ipv4addr;
         mandatory true;
       }
       leaf virtual-circuit-id {
         description "Layer 2 circuit ID";
         default "all";
         type string;
       }
     }
     output {
       choice output_c {
         case output-tag {
           leaf output {
             type string;
           }
         }
         case multichassis-tag {
           anyxml multi-routing-engine-results;
         }
       }
     }
   }
   rpc request-vpls-switchover {
     description "Perform LDP VPLS pseudowire switchover";
     junos:command "request vpls-switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of VPLS instance";
         type string;
         mandatory true;
       }
       leaf neighbor {
         description "IP address of neighbor";
         type jt:ipv4addr;
         mandatory true;
       }
       leaf vpls-id {
         description "Layer 2 circuit ID";
         default "all";
         type string;
       }
     }
     output {
       choice output_c {
         case output-tag {
           leaf output {
             type string;
           }
         }
         case multichassis-tag {
           anyxml multi-routing-engine-results;
         }
       }
     }
   }
   rpc request-mpls-lsp-autobandwidth-adjust {
     description "Request LSP autobandwidth adjustment now";
     junos:command "request mpls lsp adjust-autobandwidth";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-autobandwidth-adjust {
     description "Request LSP autobandwidth adjustment now";
     junos:command "request mpls container-lsp adjust-autobandwidth";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-normalization {
     description "Request container LSP normalization now";
     junos:command "request mpls container-lsp normalization";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
       leaf bandwidth {
         description "Use the bandwidth for manual normalization";
         type union {
           type uint64;
           type string {
             pattern "<.*>|$.*";
           }
         }
       }
     }
     output {
       choice output_c {
         case output-tag {
           leaf output {
             type string;
           }
         }
         case multichassis-tag {
           anyxml multi-routing-engine-results;
         }
       }
     }
   }
   rpc request-mpls-lable-range-reserve {
     description "Request label space repartition now";
     junos:command "request mpls label-range reserve";
     output {
       choice output_c {
         case output-tag {
           leaf output {
             type string;
           }
         }
         case multichassis-tag {
           anyxml multi-routing-engine-results;
         }
       }
     }
   }
   rpc request-mvpn-hrs-force-revert {
     description "Request MVPN HRS Force revert";
     junos:command "request mvpn hrs-force-revert";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-mvpn-hrs-force-revert-instance {
     description "Per instance";
     junos:command "request mvpn hrs-force-revert instance";
     input {
       leaf instance_name {
         description "Name of instance";
         junos:cli-feature "nokeyword";
         type string;
         mandatory true;
       }
       leaf group {
         description "IP address of multicast group";
         type jt:ipprefix;
         mandatory true;
       }
       leaf source {
         description "IP address multicast source";
         type jt:ipprefix;
         mandatory true;
       }
     }
     output {
       choice output_c {
         case output-tag {
           leaf output {
             type string;
           }
         }
         case multichassis-tag {
           anyxml multi-routing-engine-results;
         }
       }
     }
   }
   rpc pim-multicast-tunnel {
     description "Request PIM MT rebalance";
     junos:command "request pim multicast-tunnel rebalance";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc request-programmable-rpd-rpc-dump-information {
     description "Request RPC dump from rpd";
     junos:command "request programmable-rpd rpc-dump";
     output {
       choice output_c {
         case output-tag {
           leaf output {
             type string;
           }
         }
         case multichassis-tag {
           anyxml multi-routing-engine-results;
         }
       }
     }
   }
   rpc request-validation-policy {
     description "Request policy reevaluation";
     junos:command "request validation policy";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf record {
         description "Filter by record";
         type jt:ipprefix;
       }
       leaf instance {
         description "Name of route validation instance";
         type string;
       }
     }
     output {
       container rv-request-policy-information {
         uses rv-request-policy-information-block;
       }
     }
   }
   rpc request-validation-reload-source-file {
     description "Request reload source file";
     junos:command "request validation reload-source-file";
     output {
       container rv-reload-source-file-information {
         uses rv-reload-source-file-information-block;
       }
     }
   }
   rpc monitor-mobile-gateways-call-trace-start {
     description "Trace subscriber events";
     junos:command "request unified-edge ggsn-pgw call-trace";
     output {
       container mobile-gateway-sm-af-call-trace-start {
         uses mobile-gateway-sm-af-call-trace-start-block;
       }
     }
   }
   rpc get-mobile-gateways-call-trace-start-information {
     description "Start subscriber events trace";
     junos:command "request unified-edge ggsn-pgw call-trace start";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf apn-name {
         description "Name of APN";
         type string {
           length "1 .. 100";
         }
       }
       leaf file-name-prefix {
         description "Name of file prefix";
         type string {
           length "4 .. 24";
         }
       }
       leaf comment {
         description "Comment to be added in the file";
         type string {
           length "4 .. 100";
         }
       }
     }
     output {
       container mobile-gateways-call-trace-start-information {
         uses mobile-gateways-call-trace-start-information-block;
       }
     }
   }
   rpc get-mobile-gateways-call-trace-stop-information {
     description "Stop subscriber events trace";
     junos:command "request unified-edge ggsn-pgw call-trace stop";
     input {
       leaf identifier {
         description "Name of identifier";
         type string {
           length "1 .. 100";
         }
       }
       leaf all {
         description "All call traces";
         type empty;
       }
     }
     output {
       container mobile-gateways-call-trace-stop-information {
         uses mobile-gateways-call-trace-stop-information-block;
       }
     }
   }
   rpc get-mobile-gateways-call-trace-clear {
     description "Clear subscriber events trace";
     junos:command "request unified-edge ggsn-pgw call-trace clear";
     output {
       choice output_c {
         case output-tag {
           leaf output {
             type string;
           }
         }
         case multichassis-tag {
           anyxml multi-routing-engine-results;
         }
       }
     }
   }
   rpc get-mobile-gateways-call-trace-information {
     description "Show subscriber events trace";
     junos:command "request unified-edge ggsn-pgw call-trace show";
     input {
       leaf selector {
         junos:cli-feature "nokeyword";
         default "all";
         type enumeration {
           enum "current" {
             description "Display information about current traces";
           }
           enum "completed" {
             description "Display information about completed traces";
           }
           enum "all" {
             description "Display information about all trace";
           }
         }
       }
       leaf verbosity-level {
         description "Select the verbosity level";
         junos:cli-feature "nokeyword";
         default "brief";
         type enumeration {
           enum "brief" {
             description "Display brief output (default)";
           }
           enum "detail" {
             description "Display detailed output";
           }
         }
       }
     }
     output {
       container mobile-gateways-call-trace-information {
         uses mobile-gateways-call-trace-information-block;
       }
     }
   }
   rpc get-mobile-gateways-sgw-call-trace-start-information {
     description "Start subscriber events trace";
     junos:command "request unified-edge sgw call-trace start";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       container mobile-gateways-call-trace-start-information {
         uses mobile-gateways-call-trace-start-information-block;
       }
     }
   }
   rpc get-mobile-gateways-sgw-call-trace-stop-information {
     description "Stop subscriber events trace";
     junos:command "request unified-edge sgw call-trace stop";
     input {
       leaf identifier {
         description "Name of identifier";
         type string {
           length "1 .. 100";
         }
       }
       leaf all {
         description "All call traces";
         type empty;
       }
     }
     output {
       container mobile-gateways-call-trace-stop-information {
         uses mobile-gateways-call-trace-stop-information-block;
       }
     }
   }
   rpc get-mobile-gateways-sgw-call-trace-clear {
     description "Clear subscriber events trace";
     junos:command "request unified-edge sgw call-trace clear";
     output {
       choice output_c {
         case output-tag {
           leaf output {
             type string;
           }
         }
         case multichassis-tag {
           anyxml multi-routing-engine-results;
         }
       }
     }
   }
   rpc get-mobile-gateways-sgw-call-trace-information {
     description "Show subscriber events trace";
     junos:command "request unified-edge sgw call-trace show";
     input {
       leaf selector {
         junos:cli-feature "nokeyword";
         default "all";
         type enumeration {
           enum "current" {
             description "Display information about current traces";
           }
           enum "completed" {
             description "Display information about completed traces";
           }
           enum "all" {
             description "Display information about all trace";
           }
         }
       }
       leaf verbosity-level {
         description "Select the verbosity level";
         junos:cli-feature "nokeyword";
         default "brief";
         type enumeration {
           enum "brief" {
             description "Display brief output (default)";
           }
           enum "detail" {
             description "Display detailed output";
           }
         }
       }
     }
     output {
       container mobile-gateways-call-trace-information {
         uses mobile-gateways-call-trace-information-block;
       }
     }
   }
   rpc get-mobile-gateways-tdf-call-trace-start-information {
     description "Start subscriber events trace";
     junos:command "request unified-edge tdf call-trace start";
     input {
       leaf msisdn {
         description "Trace events for a specific msisdn";
         type string {
           length "3 .. 15";
         }
       }
       leaf imsi {
         description "Trace events for a specific imsi";
         type string {
           length "5 .. 15";
         }
       }
       leaf next-call {
         description "Trace the next call events on each session PIC";
         type empty;
       }
       leaf v4-addr {
         description "Trace events for a specific IPV4 subscriber";
         type jt:ipaddr;
       }
       leaf v6-addr {
         description "Trace events for a specific IPV6 subscriber";
         type jt:ipv6addr;
       }
       leaf routing-instance {
         description "Routing Instance which the subscriber belong to";
         type string;
       }
       leaf user-name {
         description "Subscriber User Name";
         type string;
       }
       leaf subscriber-name {
         description "Non-IP Subscriber Name";
         type string;
       }
     }
     output {
       container mobile-gateways-call-trace-start-information {
         uses mobile-gateways-call-trace-start-information-block;
       }
     }
   }
   rpc get-mobile-gateways-tdf-call-trace-stop-information {
     description "Stop subscriber events trace";
     junos:command "request unified-edge tdf call-trace stop";
     input {
       leaf identifier {
         description "Name of identifier";
         type string {
           length "1 .. 100";
         }
       }
       leaf all {
         description "All call traces";
         type empty;
       }
     }
     output {
       container mobile-gateways-call-trace-stop-information {
         uses mobile-gateways-call-trace-stop-information-block;
       }
     }
   }
   rpc get-mobile-gateways-tdf-call-trace-clear {
     description "Clear subscriber events trace";
     junos:command "request unified-edge tdf call-trace clear";
     output {
       choice output_c {
         case output-tag {
           leaf output {
             type string;
           }
         }
         case multichassis-tag {
           anyxml multi-routing-engine-results;
         }
       }
     }
   }
   rpc get-mobile-gateways-tdf-call-trace-information {
     description "Show subscriber events trace";
     junos:command "request unified-edge tdf call-trace show";
     input {
       leaf selector {
         junos:cli-feature "nokeyword";
         default "all";
         type enumeration {
           enum "current" {
             description "Display information about current traces";
           }
           enum "completed" {
             description "Display information about completed traces";
           }
           enum "all" {
             description "Display information about all traces";
           }
         }
       }
       leaf verbosity-level {
         description "Select the verbosity level";
         junos:cli-feature "nokeyword";
         default "brief";
         type enumeration {
           enum "brief" {
             description "Display brief output (default)";
           }
           enum "detail" {
             description "Display detailed output";
           }
         }
       }
     }
     output {
       container mobile-gateways-call-trace-information {
         uses mobile-gateways-call-trace-information-block;
       }
     }
   }
   rpc request-path-computation-client-main-pce {
     description "Request new active PCE";
     junos:command "request path-computation-client active-pce";
     input {
       leaf pce-id {
         description "PCE ID from configuration";
         junos:cli-feature "nokeyword";
         type string;
         mandatory true;
       }
     }
     output {
       choice output_c {
         case output-tag {
           leaf output {
             type string;
           }
         }
         case multichassis-tag {
           anyxml multi-routing-engine-results;
         }
       }
     }
   }
   rpc request-path-computation-retry-delegation {
     description "Request retry delegation";
     junos:command "request path-computation-client retry-delegation";
     input {
       leaf lsp-name {
         description "Name of static label-switched-path";
         junos:cli-feature "nokeyword";
         type string;
         mandatory true;
       }
     }
     output {
       choice output_c {
         case output-tag {
           leaf output {
             type string;
           }
         }
         case multichassis-tag {
           anyxml multi-routing-engine-results;
         }
       }
     }
   }
   rpc pppoe-connect-session {
     description "PPPoE session connect";
     junos:command "request pppoe connect";
     input {
       leaf interface {
         description "Enter PPPoE interface name";
         junos:cli-feature "nokeyword";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc pppoe-diconnect-session {
     description "PPPoE session disconnect";
     junos:command "request pppoe disconnect";
     input {
       leaf interface {
         description "Enter PPPoE interface name or session id";
         junos:cli-feature "nokeyword";
         type string;
       }
     }
     output {
       choice output_c {
         case output-tag {
           leaf output {
             type string;
           }
         }
         case multichassis-tag {
           anyxml multi-routing-engine-results;
         }
       }
     }
   }
   rpc request-virtual-chassis-reactivate {
     description "Make active from inactive-split mode";
     junos:command "request virtual-chassis reactivate";
     output {
       choice output_c {
         case output-tag {
           leaf output {
             type string;
           }
         }
         case multichassis-tag {
           anyxml multi-routing-engine-results;
         }
       }
     }
   }
   rpc request-virtual-chassis-renumber {
     description "Change member ID";
     junos:command "request virtual-chassis renumber";
     input {
       leaf member-id {
         description "Current member ID";
         type union {
           type string {
             pattern "<.*>|$.*";
           }
           type int32;
         }
         mandatory true;
       }
       leaf new-member-id {
         description "New member ID";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc request-virtual-chassis-recycle {
     description "Recycle member ID";
     junos:command "request virtual-chassis recycle";
     input {
       leaf member-id {
         description "Member ID";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc request-virtual-chassis-vc-port-set-interface {
     description "Member's virtual chassis interface";
     junos:command "request virtual-chassis vc-port set interface";
     input {
       uses command-forwarding;
       leaf interface-name {
         description "Name of dedicated virtual chassis interface";
         junos:cli-feature "nokeyword";
         type string;
         mandatory true;
       }
       leaf disable {
         description "Disable virtual chassis interface";
         type empty;
       }
     }
     output {
       choice output_c {
         case output-tag {
           leaf output {
             type string;
           }
         }
         case multichassis-tag {
           anyxml multi-routing-engine-results;
         }
       }
     }
   }
   rpc request-virtual-chassis-vc-port-set-pic-slot {
     description "Member's PIC slot";
     junos:command "request virtual-chassis vc-port set pic-slot";
     input {
       uses command-forwarding;
       leaf pic-slot {
         description "PIC slot number";
         junos:cli-feature "nokeyword";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-virtual-chassis-vc-port-set-fpc-slot {
     description "Member's FPC slot";
     junos:command "request virtual-chassis vc-port set fpc-slot";
     input {
       uses command-forwarding;
       leaf fpc-slot {
         description "FPC slot number";
         junos:cli-feature "nokeyword";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
       leaf channel {
         description "Channel number";
         type union {
           type string {
             pattern "<.*>|$.*";
           }
           type uint32 {
             range "0 .. 3";
           }
         }
       }
     }
     output {
       choice output_c {
         case output-tag {
           leaf output {
             type string;
           }
         }
         case multichassis-tag {
           anyxml multi-routing-engine-results;
         }
       }
     }
   }
   rpc request-virtual-chassis-vc-port-delete-pic-slot {
     description "Member's PIC slot";
     junos:command "request virtual-chassis vc-port delete pic-slot";
     input {
       uses command-forwarding;
       leaf pic-slot {
         description "PIC slot number";
         junos:cli-feature "nokeyword";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-virtual-chassis-vc-port-delete-fpc-slot {
     description "Member's FPC slot";
     junos:command "request virtual-chassis vc-port delete fpc-slot";
     input {
       uses command-forwarding;
       leaf fpc-slot {
         description "FPC slot number";
         junos:cli-feature "nokeyword";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
       leaf channel {
         description "Channel number";
         type union {
           type string {
             pattern "<.*>|$.*";
           }
           type uint32 {
             range "0 .. 3";
           }
         }
       }
     }
     output {
       choice output_c {
         case output-tag {
           leaf output {
             type string;
           }
         }
         case multichassis-tag {
           anyxml multi-routing-engine-results;
         }
       }
     }
   }
   rpc request-virtual-chassis-vc-port-diag-optics {
     description "Virtual chassis port diagnostics optics";
     junos:command "request virtual-chassis vc-port diagnostics optics";
     input {
       uses command-forwarding;
       leaf interface-name {
         description "Name of virtual chassis port";
         junos:cli-feature "nokeyword";
         type string;
       }
     }
     output {
       choice output_c {
         case output-tag {
           leaf output {
             type string;
           }
         }
         case multichassis-tag {
           anyxml multi-routing-engine-results;
         }
       }
     }
   }
   rpc req-virtual-chassis-mode {
     description "Set a member's mode (Warning: member's mode must be consistent)";
     junos:command "request virtual-chassis mode";
     input {
       uses command-forwarding;
       leaf fabric {
         description "Set to virtual chassis fabric mode";
         type empty;
       }
       leaf mixed {
         description "Allow devices from different product families to become members";
         type empty;
       }
       leaf disable {
         description "Disable specified mode";
         type empty;
       }
       leaf reboot {
         description "Reboot system after changing mode";
         type empty;
       }
       leaf ieee-clause-82 {
         description "Allow devices to operate in ieee-clause-82 PCS encoding";
         type empty;
       }
       leaf network-port {
         description "Delete VC ports";
         type empty;
       }
       leaf hgoe {
         description "Virtual Chassis will operate in HGOE mode";
         type empty;
       }
     }
     output {
       choice output_c {
         case output-tag {
           leaf output {
             type string;
           }
         }
         case multichassis-tag {
           anyxml multi-routing-engine-results;
         }
       }
     }
   }
   rpc set-virtual-chassis-member-id {
     description "Set virtual-chassis information";
     junos:command "request virtual-chassis member-id set";
     input {
       leaf member {
         description "Virtual-Chassis member number";
         type union {
           type string {
             pattern "<.*>|$.*";
           }
           type int32;
         }
         mandatory true;
       }
       leaf slots-per-chassis {
         description "Virtual-Chassis FPC slots per chassis number";
         type enumeration {
           enum "12" {
             description "12 FPC slots per chassis";
           }
           enum "20" {
             description "20 FPC slots per chassis";
           }
         }
       }
     }
     output {
       choice output_c {
         case output-tag {
           leaf output {
             type string;
           }
         }
         case multichassis-tag {
           anyxml multi-routing-engine-results;
         }
       }
     }
   }
   rpc delete-virtual-chassis-member-id {
     description "Delete virtual-chassis information";
     junos:command "request virtual-chassis member-id delete";
     output {
       choice output_c {
         case output-tag {
           leaf output {
             type string;
           }
         }
         case multichassis-tag {
           anyxml multi-routing-engine-results;
         }
       }
     }
   }
   rpc get-virtual-chassis-diagnostic-information {
     description "Device reachability diagnostics";
     junos:command "request virtual-chassis device-reachability";
     input {
       leaf test-name {
         description "Name of the test";
         type string {
           length "1 .. 20";
         }
         mandatory true;
       }
       leaf destination-device {
         description "Probe destination (global) device ID";
         type union {
           type uint32;
           type string {
             pattern "<.*>|$.*";
           }
         }
       }
       leaf destination-fpc {
         description "Probe destination FPC";
         type union {
           type uint32;
           type string {
             pattern "<.*>|$.*";
           }
         }
       }
       leaf destination-ip-address {
         description "IP address of destination FPC";
         type jt:ipaddr;
       }
       leaf source-fpc {
         description "Probe initiator FPC";
         type union {
           type uint32;
           type string {
             pattern "<.*>|$.*";
           }
         }
       }
       leaf source-ip-address {
         description "IP address of source FPC";
         type jt:ipaddr;
       }
       leaf probe-size {
         description "Size of one probe in bytes";
         default "56";
         type union {
           type string {
             pattern "<.*>|$.*";
           }
           type uint32 {
             range "56 .. 1500";
           }
         }
       }
       leaf probe-count {
         description "Number of probes in a test";
         default "5";
         type union {
           type string {
             pattern "<.*>|$.*";
           }
           type uint32 {
             range "1 .. 10";
           }
         }
       }
       leaf probe-pattern {
         description "Payload pattern byte in the probe (0x00-0xff)";
         default "0x00";
         type string {
           junos:posix-pattern "^0(x|X)([0-9|a-f|A-F])([0-9|a-f|A-F])$";
           junos:pattern-message "Must be hexadecimal bit pattern in (0x00..0xff)";
         }
       }
       leaf probe-interval {
         description "Duration between successive probes";
         default "1";
         units "seconds";
         type union {
           type string {
             pattern "<.*>|$.*";
           }
           type uint32 {
             range "1 .. 3";
           }
         }
       }
       leaf test-interval {
         description "Time interval to perform this test again";
         default "1";
         units "seconds";
         type union {
           type string {
             pattern "<.*>|$.*";
           }
           type uint32 {
             range "1 .. 5";
           }
         }
       }
       leaf test-count {
         description "Number of times this test to be performed";
         default "1";
         type union {
           type string {
             pattern "<.*>|$.*";
           }
           type uint32 {
             range "1 .. 3";
           }
         }
       }
     }
     output {
       container virtual-chassis-diagnostic-information {
         uses virtual-chassis-diagnostic-information-block;
       }
     }
   }
   rpc switch-vc-routing-engine-protocol-master {
     description "Toggle mastership between VC members";
     junos:command "request virtual-chassis routing-engine master switch";
     input {
       leaf check {
         description "Check status of graceful switchover";
         type empty;
       }
     }
     output {
       choice output_c {
         case output-tag {
           leaf output {
             type string;
           }
         }
         case multichassis-tag {
           anyxml multi-routing-engine-results;
         }
       }
     }
   }
   rpc upgrade-vc-cancel {
     description "Terminate sequential upgrade, rollback software image on protocol-backup";
     junos:command "request virtual-chassis upgrade cancel";
     output {
       choice output_c {
         case output-tag {
           leaf output {
             type string;
           }
         }
         case multichassis-tag {
           anyxml multi-routing-engine-results;
         }
       }
     }
   }
   rpc upgrade-vc-protocol-backup {
     description "Upgrade protocol-backup member chassis";
     junos:command "request virtual-chassis upgrade protocol-backup";
     input {
       leaf halt-re {
         description "Halt routing-engines instead of restarting; manual restart required";
         type empty;
       }
       leaf package-name {
         description "URL or pathname of package";
         junos:cli-feature "nokeyword";
         type jt:filename;
         mandatory true;
       }
     }
     output {
       choice output_c {
         case output-tag {
           leaf output {
             type string;
           }
         }
         case multichassis-tag {
           anyxml multi-routing-engine-results;
         }
       }
     }
   }
   rpc upgrade-vc-protocol-master {
     description "Upgrade protocol-master member chassis";
     junos:command "request virtual-chassis upgrade protocol-master";
     input {
       leaf halt-re {
         description "Halt routing-engines instead of restarting; manual restart required";
         type empty;
       }
       leaf package-name {
         description "URL or pathname of package";
         junos:cli-feature "nokeyword";
         type jt:filename;
         mandatory true;
       }
     }
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping rescue-management-results-block {
     list routing-engine {
       leaf commit-check-success {
         type empty;
         description "Configuration check succeeds";
       }
       leaf commit-success {
         type empty;
         description "Configuration commit is complete";
       }
       leaf commit-queued {
         type empty;
         description "Configuration commit is queued";
       }
       leaf commit-prepare-success {
         type empty;
         description "Commit cache is successfully prepared";
       }
       container satellite-commit-check-results {
         list satellite {
           leaf name {
             type string;
             description "Syslog message tag name";
           }
           leaf satellite-commit-check-success {
             type empty;
             description "Configuration check succeeds";
           }
         }
       }
       leaf name {
         type string;
         description "Syslog message tag name";
       }
       leaf success {
         type empty;
         description "Rescue configuration operation succeeded";
       }
     }
   }
   grouping commit-server-delete-results-block {
     leaf commit-server-delete-success {
       type empty;
     }
     leaf commit-server-delete-failed-match {
       type empty;
     }
   }
   grouping commit-server-operation-block {
     leaf-list message {
       type string;
       description "Pause message";
     }
     container pause-status {
       description "Commit server pause status";
       leaf pause-success {
         type empty;
         description "Pause success";
       }
       leaf pause-error {
         type empty;
         description "Pause error";
       }
       leaf pause-already {
         type empty;
         description "Commit server is already paused";
       }
     }
     container start-status {
       description "Commit server start status";
       leaf start-success {
         type empty;
         description "Start success";
       }
       leaf start-error {
         type empty;
         description "Start error";
       }
       leaf start-already {
         type empty;
         description "Commit server is already running";
       }
     }
   }
   grouping logout-user-block {
     leaf logout-user-message {
       type string;
     }
   }
   grouping package-status-block {
     leaf package-status-message {
       type string;
       description "Show software installation status";
     }
   }
   grouping add-license-results-block {
     leaf add-success {
       type empty;
       description "Add completed with no errors";
     }
     leaf add-error-count {
       type int32;
       description "Number of errors during add license operation";
     }
     list add-individual-result {
       description "Report status of individual license add operation";
       leaf filename {
         type string;
         description "File name in which error exist";
       }
       leaf line-number {
         type int32;
         description "Line number where error exist";
       }
       leaf operation-status {
         type string;
         description "Defines that status of a license operation";
       }
       leaf name {
         type string;
         description "Identifier for this object";
       }
       leaf message {
         type string;
         description "Text to explain the status of an operation";
       }
     }
   }
   grouping inform-block {
     leaf source-daemon {
       type string;
     }
     leaf message {
       type string;
       description "Syslog message text";
     }
   }
   grouping transfer-control-diagnostics-block {
     leaf transfer-node-name-caption {
       type string;
       description "Node name caption string";
     }
     leaf transfer-node-name-value {
       type string;
       description "Node name value string";
     }
     leaf transfer-list-type-caption {
       type string;
       description "Transfer list type caption string";
     }
     leaf transfer-list-type-value {
       type string;
       description "Transfer list type value string";
     }
     leaf transfer-control-status-caption {
       type string;
       description "Transfer control status caption string";
     }
     leaf transfer-control-status-value {
       type string;
       description "Transfer control status value string";
     }
   }
   grouping system-logfiles-block {
     leaf system-logfiles-node-caption {
       type string;
       description "Name of node caption string";
     }
     leaf system-logfiles-node-value {
       type string;
       description "Name of node value string";
     }
     leaf system-logfiles-local-path-caption {
       type string;
       description "Local path caption string";
     }
     leaf system-logfiles-local-path-value {
       type string;
       description "Local path value string";
     }
     leaf system-logfiles-archive-path-caption {
       type string;
       description "Archive path caption string";
     }
     leaf system-logfiles-archive-path-value {
       type string;
       description "Archive path value string";
     }
   }
   grouping system-storage-cleanup-information-block {
     leaf dre-repository-status {
       type string;
       description "DRE repository status";
     }
     container file-list {
       container file {
         leaf size {
           type int32;
           description "File size in bytes";
         }
         leaf date {
           type string;
           description "Modification time";
         }
         leaf file-name {
           type string;
           description "File name";
         }
         container file-fetch {
           leaf source-filename {
             type string;
           }
           leaf source-address {
             type string;
           }
           leaf staging-directory {
             type string;
           }
           leaf routing-instance {
             type string;
           }
           leaf cert-file {
             type string;
           }
           leaf no-check-certificate {
             type string;
           }
           leaf no-stage {
             type string;
           }
           leaf destination-filename {
             type string;
           }
         }
         container file-put {
           leaf source-filename {
             type string;
           }
           leaf destination-filename {
             type string;
           }
           leaf source-address {
             type string;
           }
           leaf routing-instance {
             type string;
           }
           leaf cleanup-source {
             type empty;
           }
           leaf filename {
             type string;
           }
           leaf encoding {
             type string;
             description "Encoding type: ascii or base64";
           }
           leaf permission {
             type string;
             description "Permission of destination file";
           }
           leaf delete-if-exist {
             type empty;
             description "Delete destination file if it exists";
           }
           leaf file-contents {
             type string;
             description "Base64 encoded contents of file";
           }
         }
         container send-file {
           leaf source-filename {
             type string;
           }
           leaf alias-filename {
             type string;
           }
           leaf display-spinner {
             type empty;
           }
           leaf source-address {
             type string;
           }
           leaf routing-instance {
             type string;
           }
         }
       }
     }
     container dre-repository-content {
       leaf dre-repository-content-header {
         type string;
         description "DRE repository content header";
       }
       leaf dre-repository-content-entry {
         type string;
         description "DRE repository content entry";
       }
       leaf dre-repository-content-footer {
         type string;
         description "DRE repository content footer";
       }
     }
   }
   grouping request-reboot-results-block {
     leaf request-reboot-status {
       type string;
       description "Reboot request status";
     }
   }
   grouping snapshot-information-block {
     leaf snapshot-medium {
       type string;
       description "Media type of the snapshot";
     }
     leaf creation-date {
       type string;
       description "Snapshot creation date";
     }
     container inform {
       leaf source-daemon {
         type string;
       }
       leaf message {
         type string;
         description "Syslog message text";
       }
     }
     container snapshot-copy {
       leaf source-directory {
         type string;
         description "Directory to backup";
       }
       leaf destination-directory {
         type string;
         description "Backup directory";
       }
     }
     container archived-directory-list {
       leaf directory-name {
         type string;
         description "Directory name";
       }
     }
     container snapshot-partitions {
       description "Partitions on snapshot medium";
       list partition-information {
         description "Partition information";
         leaf partition {
           type string;
           description "Partition letter";
         }
         leaf mount-point {
           type string;
           description "Mount point";
         }
         leaf partition-size {
           type string;
           description "Size of partition";
         }
         leaf snapshot-argument {
           type string;
           description "Argument to snapshot used to configure size";
         }
       }
     }
     container software-version {
       description "Version of software snapshot";
       list package {
         description "Package in software snapshot";
         leaf package-name {
           type string;
           description "Name of software package";
         }
         leaf package-version {
           type string;
           description "Version of software package";
         }
       }
     }
   }
   grouping system-firmware-information-block {
     list system-firmware {
       leaf firmware-name {
         type string;
         description "Name of this component";
       }
       leaf firmware-type {
         type string;
         description "Type of this component";
       }
       leaf firmware-tag {
         type int32;
         description "Multiple firmware per FRU delimiter";
       }
       leaf firmware-revision {
         type string;
         description "Firmware version for this component";
       }
       leaf firmware-revision-available {
         type string;
         description "Firmware version available on disk for this component";
       }
       leaf firmware-status {
         type string;
         description "Firmware status for this component";
       }
       container system-module {
         leaf firmware-name {
           type string;
           description "Name of this component";
         }
         container firmware-state {
           description "Firmware status per component type";
           leaf firmware-type {
             type string;
             description "Type of this component";
           }
           leaf firmware-status {
             type string;
             description "Firmware status for this component";
           }
         }
       }
       container system-sub-module-firmware-list {
         list system-sub-module-firmware {
           description "Firmware sub module";
           leaf firmware-name {
             type string;
             description "Name of this component";
           }
           leaf firmware-type {
             type string;
             description "Type of this component";
           }
           leaf firmware-tag {
             type int32;
             description "Multiple firmware per FRU delimiter";
           }
           leaf firmware-revision {
             type string;
             description "Firmware version for this component";
           }
           leaf firmware-revision-available {
             type string;
             description "Firmware version available on disk for this component";
           }
           leaf firmware-status {
             type string;
             description "Firmware status for this component";
           }
         }
       }
       list tvp {
         container system-module {
           leaf firmware-name {
             type string;
             description "Name of this component";
           }
           container firmware-state {
             description "Firmware status per component type";
             leaf firmware-type {
               type string;
               description "Type of this component";
             }
             leaf firmware-status {
               type string;
               description "Firmware status for this component";
             }
           }
         }
         container system-sub-module-firmware-list {
           list system-sub-module-firmware {
             description "Firmware sub module";
             leaf firmware-name {
               type string;
               description "Name of this component";
             }
             leaf firmware-type {
               type string;
               description "Type of this component";
             }
             leaf firmware-tag {
               type int32;
               description "Multiple firmware per FRU delimiter";
             }
             leaf firmware-revision {
               type string;
               description "Firmware version for this component";
             }
             leaf firmware-revision-available {
               type string;
               description "Firmware version available on disk for this component";
             }
             leaf firmware-status {
               type string;
               description "Firmware status for this component";
             }
           }
         }
       }
     }
   }
   grouping download-information-block {
     leaf status {
       type string;
       description "Status of a download request";
     }
     leaf progress {
       type string;
       description "Percentage of download completed";
     }
     leaf download-id {
       type string;
       description "ID of the download";
     }
     leaf download-url {
       type string;
       description "URL to download from";
     }
     leaf local-path {
       type string;
       description "Local path to which the file gets downloaded";
     }
     leaf max-rate {
       type string;
       description "Maximum rate for performing the download";
     }
     leaf creation-time {
       type string;
       description "Date and time when the download was created";
     }
     leaf scheduled-time {
       type string;
       description "Date and time when the download was requested to start";
     }
     leaf start-time {
       type string;
       description "Date and time when the download was actually started or restarted after error";
     }
     leaf retry-time {
       type string;
       description "Date and time when the download is scheduled to start again after error";
     }
     leaf retries-left {
       type string;
       description "Number of times the system will retry the download automatically after error";
     }
     leaf completion-time {
       type string;
       description "Date and time when the download completed";
     }
     leaf error-count {
       type string;
       description "Number of times an error condition has been encountered during download";
     }
     leaf error-message {
       type string;
       description "Error message";
     }
     list download-info-brief {
       description "Download status information";
       leaf download-id {
         type string;
         description "ID of the download";
       }
       leaf status {
         type string;
         description "Status of a download request";
       }
       leaf start-time {
         type string;
         description "Date and time when the download was actually started or restarted after error";
       }
       leaf progress {
         type string;
         description "Percentage of download completed";
       }
       leaf download-url {
         type string;
         description "URL to download from";
       }
     }
     list download-info-detail {
       description "Detailed download status information";
       leaf download-id {
         type string;
         description "ID of the download";
       }
       leaf status {
         type string;
         description "Status of a download request";
       }
       leaf progress {
         type string;
         description "Percentage of download completed";
       }
       leaf download-url {
         type string;
         description "URL to download from";
       }
       leaf local-path {
         type string;
         description "Local path to which the file gets downloaded";
       }
       leaf max-rate {
         type string;
         description "Maximum rate for performing the download";
       }
       leaf creation-time {
         type string;
         description "Date and time when the download was created";
       }
       leaf scheduled-time {
         type string;
         description "Date and time when the download was requested to start";
       }
       leaf start-time {
         type string;
         description "Date and time when the download was actually started or restarted after error";
       }
       leaf retry-time {
         type string;
         description "Date and time when the download is scheduled to start again after error";
       }
       leaf completion-time {
         type string;
         description "Date and time when the download completed";
       }
       leaf error-count {
         type string;
         description "Number of times an error condition has been encountered during download";
       }
       leaf retries-left {
         type string;
         description "Number of times the system will retry the download automatically after error";
       }
       leaf error-message {
         type string;
         description "Error message";
       }
     }
   }
   grouping autorecovery-block {
     container autorecovery-state {
       description "Autorecovery state information";
       leaf entity-name {
         type string;
       }
       leaf recovery-info {
         type string;
         description "Presence or absence of autorecovery information for an entity";
       }
       leaf integrity-check {
         type string;
         description "Status of the integrity check of a saved entity";
       }
       leaf action-status {
         type string;
         description "Action required from user or status of recovery attempt by system";
       }
       list autorecovery-state-bsd-label {
         description "Autorecovery information for BSD Labels";
         container bsd-label-status {
           description "Status of one BSD Label";
           leaf entity-name {
             type string;
           }
           leaf recovery-info {
             type string;
             description "Presence or absence of autorecovery information for an entity";
           }
           leaf integrity-check {
             type string;
             description "Status of the integrity check of a saved entity";
           }
           leaf action-status {
             type string;
             description "Action required from user or status of recovery attempt by system";
           }
         }
       }
       container autorecovery-state-config {
         description "Autorecovery information for rescue configuration";
         container config-status {
           description "Status of rescue configuration";
           leaf entity-name {
             type string;
           }
           leaf recovery-info {
             type string;
             description "Presence or absence of autorecovery information for an entity";
           }
           leaf integrity-check {
             type string;
             description "Status of the integrity check of a saved entity";
           }
           leaf action-status {
             type string;
             description "Action required from user or status of recovery attempt by system";
           }
         }
       }
       list autorecovery-state-license {
         description "Autorecovery information for licenses";
         container license-status {
           description "Status of one license key";
           leaf entity-name {
             type string;
           }
           leaf recovery-info {
             type string;
             description "Presence or absence of autorecovery information for an entity";
           }
           leaf integrity-check {
             type string;
             description "Status of the integrity check of a saved entity";
           }
           leaf action-status {
             type string;
             description "Action required from user or status of recovery attempt by system";
           }
         }
       }
     }
   }
   grouping jmrt-scan-result-block {
     leaf found-malware {
       type string;
       description "Found malware?";
     }
     container scan-results {
       description "Scan results";
       list result {
         description "Single scan result";
         leaf rule {
           type string;
           description "Scan rule";
         }
         leaf-list pid {
           type uint32;
           description "Process ID of matched process";
         }
         leaf-list file {
           type string;
           description "File that matched the rule";
         }
       }
     }
   }
   grouping jmrt-veriexec-check-block {
     leaf veriexec-running {
       type string;
       description "Veriexec is running?";
     }
   }
   grouping jmrt-integrity-check-block {
     leaf integrity-enforced {
       type string;
       description "Integrity is enforced?";
     }
   }
   grouping jmrt-fake-malware-block {
     leaf-list pid {
       type int32;
       description "PID of spawned example malware process";
     }
   }
   grouping jmrt-list-fake-malware-block {
     leaf-list pid {
       type int32;
       description "PID of spawned example malware process";
     }
   }
   grouping system-evpn-block {
     leaf evpn-host {
       type string;
       description "Evpn host";
     }
     container vlans {
       leaf summary {
         type string;
         description "Summary";
       }
       leaf vlans-in-sync {
         type string;
         description "Vlans in sync";
       }
       leaf vlans-out-of-sync {
         type string;
         description "Vlans out of sync";
       }
       list mac-table {
         leaf instance {
           type string;
           description "Routing instance name";
         }
         leaf vlan {
           type string;
           description "Vlan name";
         }
         leaf entry {
           type string;
           description "Entry";
         }
         leaf error {
           type string;
           description "Error";
         }
       }
       list mac-ip-table {
         leaf instance {
           type string;
           description "Routing instance name";
         }
         leaf vlan {
           type string;
           description "Vlan name";
         }
         leaf entry {
           type string;
           description "Entry";
         }
         leaf error {
           type string;
           description "Error";
         }
       }
       list mac-table-hash {
         leaf instance {
           type string;
           description "Routing instance name";
         }
         leaf vlan {
           type string;
           description "Vlan name";
         }
         leaf l2-hash {
           type string;
           description "L2 hash";
         }
       }
       list mac-ip-table-hash {
         leaf instance {
           type string;
           description "Routing instance name";
         }
         leaf vlan {
           type string;
           description "Vlan name";
         }
         leaf l2-hash {
           type string;
           description "L2 hash";
         }
       }
     }
   }
   grouping cert-key-pair-block {
     leaf cert-key-pair-name {
       type string;
       description "Key pair name";
     }
     leaf cert-key-pair-size {
       type string;
       description "Key pair size";
     }
   }
   grouping cert-ca-load-status-block {
     leaf cert-ca-profile {
       type string;
       description "Certificate Authority profile";
     }
   }
   grouping default-trusted-ca-certs-download-block {
     leaf trusted-ca-certs-download-status {
       type string;
       description "Download default trusted CA cert status";
     }
   }
   grouping default-trusted-ca-certs-download-cs-block {
     leaf default-trusted-ca-certs-download-check-server-status {
       type string;
       description "Default trusted CA certs check CDN server status";
     }
   }
   grouping default-trusted-ca-certs-download-status-block {
     leaf default-trusted-ca-certs-version-on-system {
       type string;
       description "Existing default trusted CA certs on system status";
     }
   }
   grouping cert-load-status-block {
     leaf cert-certificate-id {
       type string;
       description "Certificate identifier";
     }
   }
   grouping ca-profile-group-cert-status-block {
     leaf ca-group-cert-status {
       type string;
       description "CA Profile Group CA Cert Status";
     }
     leaf ca-group-missing-certs {
       type string;
       description "CA Profile Group CA Cert Status";
     }
   }
   grouping verify-integrity-status-block {
     leaf int-check-verification-status {
       type string;
       description "Integrity check verification status";
     }
   }
   grouping request-idp-policy-load-block {
     leaf idp-policy-load-result {
       type string;
     }
   }
   grouping request-idp-storage-cleanup-block {
     leaf idp-storage-cleanup-secdb {
       type string;
     }
     leaf idp-storage-cleanup-dfa-cache {
       type string;
     }
   }
   grouping secpack-update-status-block {
     leaf secpack-status-detail {
       type string;
       description "Security install detail";
     }
   }
   grouping secpack-download-status-block {
     leaf secpack-download-status-detail {
       type string;
       description "Security download detail";
     }
   }
   grouping offline-download-status-block {
     leaf offline-download-status-detail {
       type string;
       description "Security offline download detail";
     }
   }
   grouping idp-attack-rule-information-block {
     container idp-pcap-attack-detected {
       leaf idp-pcap-attack-exist {
         type string;
       }
     }
     list idp-attack-rule-statistics {
       leaf attack-rulebase-name {
         type string;
         description "Attack Rulebase Name";
       }
       leaf attack-ruleid-value {
         type string;
         description "Attack Rule Id";
       }
       leaf attack-detected-name {
         type string;
         description "Attack Detected Name";
       }
     }
     list idp-pcap-context-statistics {
       leaf attack-context-name {
         type string;
         description "Attack Context Name";
       }
       leaf attack-context-hits {
         type string;
         description "Attack Context Hits";
       }
       leaf attack-context-value {
         type string;
         description "Attack Context Data";
       }
     }
   }
   grouping idp-dmi-to-pcap-block {
     leaf idp-dmi-to-pcap-result {
       type string;
     }
   }
   grouping request-idp-ssl-key-delete-block {
     leaf key-number {
       type uint32;
       description "Number of SSL keys";
     }
     leaf server-number {
       type uint32;
       description "Number of SSL servers";
     }
   }
   grouping jist-conversion-information-block {
     leaf jist-conversion-information-detail {
       type string;
       description "Converted Attacks";
     }
   }
   grouping request-eedebug-capture-start-result-block {
     leaf eedebug-capture-start-status {
       type string;
     }
   }
   grouping request-eedebug-capture-stop-result-block {
     leaf eedebug-capture-stop-status {
       type string;
     }
   }
   grouping key-manager-profiles-get-info-block {
     container profile-config-info {
       leaf request-status {
         type string;
         description "Status of the completed request";
       }
       leaf profile-name {
         type string;
         description "Name of the configured key profile";
       }
       leaf profile-type {
         type string;
         description "Type of the configured key profile";
       }
       leaf profile-url {
         type string;
         description "URL for KME (KME management entity) server";
       }
       leaf profile-local-sae-id {
         type string;
         description "The SAE (Secure Application entity) ID for the local application which the KME server needs to generate and send QKD key(s).";
       }
       leaf profile-local-certificate-id {
         type string;
         description "The certificate id for the corresponding certificate when client authentication needs to be done with the KME server";
       }
       leaf profile-trusted-cas {
         type string;
         description "CA(s) that will be considered as valid when server certificate verification will be performed.";
       }
       leaf profile-peer-sae-ids {
         type string;
         description "The SAE IDs for the remote applications that the KME server needs, to generate and send QKD key(s)";
       }
       leaf profile-default-key-size {
         type uint32;
         description "The default key size that will be used when KME server is requested for QKD key(s)";
       }
     }
     container profile-status-info {
       leaf request-status {
         type string;
         description "Status of the completed request";
       }
       leaf profile-name {
         type string;
         description "Name of the configured key profile";
       }
       leaf profile-type {
         type string;
         description "Type of the configured key profile";
       }
       leaf profile-configured-at {
         type string;
         description "Time at which the key profile was configured";
       }
       leaf profile-time-elapsed {
         type string;
         description "Duration of time since the key profile was configured";
       }
       leaf profile-key-size {
         type uint32;
         description "Key size";
       }
       leaf profile-source-kme-id {
         type string;
         description "Source kme id";
       }
       leaf profile-target-kme-id {
         type string;
         description "Target kme id";
       }
       leaf profile-master-sae-id {
         type string;
         description "Master sae id";
       }
       leaf profile-slave-sae-id {
         type string;
         description "Slave sae id";
       }
       leaf profile-stored-key-count {
         type uint32;
         description "Stored key count";
       }
       leaf profile-max-key-count {
         type uint32;
         description "Max key count";
       }
       leaf profile-max-key-per-request {
         type uint32;
         description "Max key per request";
       }
       leaf profile-max-key-size {
         type uint32;
         description "Max key size";
       }
       leaf profile-min-key-size {
         type uint32;
         description "Min key size";
       }
       leaf profile-max-sae-id-count {
         type uint32;
         description "Max sae id count";
       }
     }
     container profile-keys-info {
       leaf request-status {
         type string;
         description "Status of the completed request";
       }
       leaf profile-name {
         type string;
         description "Name of the configured key profile";
       }
       leaf profile-type {
         type string;
         description "Type of the configured key profile";
       }
       leaf profile-key-size {
         type uint32;
         description "Key size";
       }
       leaf profile-key-count {
         type uint32;
         description "Key count";
       }
       container profile-key-id-list {
         leaf profile-key-id {
           type string;
           description "Key";
         }
       }
       container profile-key-list {
         leaf profile-key {
           type string;
           description "Key";
         }
       }
     }
     container profile-keys-with-id-info {
       leaf request-status {
         type string;
         description "Status of the completed request";
       }
       leaf profile-name {
         type string;
         description "Name of the configured key profile";
       }
       leaf profile-type {
         type string;
         description "Type of the configured key profile";
       }
       leaf profile-key-size {
         type uint32;
         description "Key size";
       }
       leaf profile-key-count {
         type uint32;
         description "Key count";
       }
       container profile-key-id-list {
         leaf profile-key-id {
           type string;
           description "Key";
         }
       }
       container profile-key-list {
         leaf profile-key {
           type string;
           description "Key";
         }
       }
     }
   }
   grouping feed-update-block {
     leaf feed-update-result {
       type string;
       description "Url-feed update info";
     }
   }
   grouping migrate-ng-block {
     leaf migrate-ng-result {
       type string;
       description "Migrate NG result";
     }
     leaf migrate-ng-progress {
       type string;
       description "Migration to Juniper-NG Progress";
     }
     leaf migrate-ng-ignore-command {
       type string;
       description "Ignored Command";
     }
     leaf migrate-ng-ignore-commands {
       type string;
       description "Ignored Commands";
     }
   }
   grouping category-updater-block {
     leaf category-updater-result {
       type string;
       description "Category updater result";
     }
   }
   grouping ng-recategorize-block {
     leaf ng-recategorize-result {
       type string;
       description "NG Juniper recategorize result";
     }
     leaf ng-recategorize-status {
       type string;
       description "NG Juniper recategorize status";
     }
   }
   grouping ng-categorize-block {
     leaf ng-categorize-result {
       type string;
       description "NG Juniper categorize result";
     }
   }
   grouping bounce-interface-block {
     container bounce-operation-status {
       leaf interface-name {
         type string;
         description "Interface name";
       }
       leaf interval {
         type uint32;
       }
     }
   }
   grouping rebalance-interface-block {
     container rebalance-operation-status {
       leaf interface-name {
         type string;
         description "Interface name";
       }
     }
   }
   grouping extension-service-daemonize-restart-status-block {
     leaf extension-service-stop-status {
       type string;
     }
     leaf extension-service-start-status {
       type string;
     }
   }
   grouping jdaf-request-no-response-block {
     leaf error-msg {
       type string;
       description "Error message";
     }
   }
   grouping static-subscribers-information-block {
     container results {
       description "Result for static subscriber operation";
       leaf failure {
         type string;
         description "Static subscriber operation failed";
       }
       leaf success {
         type empty;
         description "Static subscriber operation succeed";
       }
     }
     container subscriber-session {
       leaf interface {
         type string;
         description "Interface name";
       }
       leaf state {
         type string;
         description "Session state";
       }
       leaf group {
         type string;
         description "Group name";
       }
       leaf username {
         type string;
         description "User name";
       }
     }
   }
   grouping extensible-subscriber-services-information-block {
     leaf reload-dictionary {
       type string;
       description "Reload dictionary";
     }
     leaf session-id-error {
       type string;
       description "Session ID error";
     }
     leaf statistics {
       type string;
       description "Statistics";
     }
     leaf error-message {
       type string;
       description " Error Message";
     }
     container sessions {
       leaf session-id {
         type string;
         description "Session ID";
       }
       leaf session-timestamp {
         type string;
         description "Session Timestamp";
       }
       leaf service-name {
         type string;
         description "Service Name";
       }
       leaf total-sessions {
         type int32;
         description "Total Sessions count";
       }
     }
     container session-information {
       leaf service-id {
         type string;
         description "Service ID";
       }
       leaf service-timestamp {
         type string;
         description "Service Timestamp";
       }
       leaf service-name {
         type string;
         description "Service Name";
       }
       leaf commit-status {
         type string;
         description "Commit status of the service";
       }
       leaf total-services {
         type int32;
         description "Total Services count";
       }
     }
     container services {
       leaf service-name {
         type string;
         description "Service Name";
       }
       leaf action-header {
         type string;
         description "Action Header";
       }
       leaf provision-action {
         type string;
         description "Provision Action";
       }
       leaf deprovision-action {
         type string;
         description "Deprovision Action";
       }
       leaf services-per-action {
         type int32;
         description "Services count per action";
       }
       leaf total-services {
         type int32;
         description "Total Services count";
       }
     }
     container dictionary {
       leaf dictionary-type {
         type string;
         description "Dictionary Type";
       }
       container local-param-attributes {
         leaf attribute-name {
           type string;
           description "Attribute Name";
         }
         leaf attribute-code {
           type int32;
           description "Attribute Code";
         }
         leaf attribute-type {
           type string;
           description "Attribute Type";
         }
       }
       container param-attributes {
         leaf attribute-name {
           type string;
           description "Attribute Name";
         }
         leaf vendor-id {
           type int32;
         }
         leaf attribute-code {
           type int32;
           description "Attribute Code";
         }
         leaf attribute-type {
           type string;
           description "Attribute Type";
         }
         leaf has-tag {
           type string;
           description "Has Tag";
         }
         leaf config-type {
           type string;
           description "Config Type";
         }
       }
       container service-info {
         leaf service-name {
           type string;
           description "Service Name";
         }
         leaf service-attribute-name {
           type string;
           description "Service Attribute Name";
         }
         leaf action {
           type string;
           description "Action";
         }
         leaf action-type {
           type int32;
           description "Action Type";
         }
         leaf action-version {
           type string;
           description "Action Version";
         }
         leaf action-name {
           type string;
           description "Action Name";
         }
         leaf parameter-header {
           type string;
           description "Parameter Header";
         }
         leaf param-attribute-name {
           type string;
           description "Parameter Attribute Name";
         }
       }
     }
     container counters {
       leaf total-sessions {
         type int32;
         description "Total Sessions count";
       }
       leaf total-services {
         type int32;
         description "Total Services count";
       }
       leaf active-services {
         type int32;
         description "Active Services count";
       }
       leaf op-script-success {
         type uint32;
         description "Successful Op-script Execution count";
       }
       leaf op-script-failure {
         type uint32;
         description "Unsuccessful Op-script Execution count";
       }
       leaf commit-success {
         type uint32;
         description "Successful Commit Execution count";
       }
       leaf commit-failure {
         type uint32;
         description "Unsuccessful Commit Execution count";
       }
       leaf application-success {
         type uint32;
         description "Successful Application Execution count";
       }
       leaf application-failure {
         type uint32;
         description "Unsuccessful Application Execution count";
       }
       leaf service-requests-received {
         type uint32;
         description "Received Service Requests count";
       }
       leaf service-requests-acked {
         type uint32;
         description "Acknowledged Service Requests count";
       }
       leaf service-requests-nacked {
         type uint32;
         description "Negative Acknowledged Service Requests count";
       }
       leaf out-of-units {
         type uint32;
         description "Number of times there were no available IFL units";
       }
       leaf total-units {
         type uint32;
         description "Total number of IFL units";
       }
       leaf units-in-use {
         type uint32;
         description "Number of IFL units in use";
       }
       leaf units-usage {
         type uint32;
         description "Percentage of total IFL units in use";
       }
     }
     container debug {
       leaf dump-record {
         type string;
         description "File Name of Dump Record";
       }
       leaf dictionary-config-record {
         type string;
         description "File Name of Configured Dictionary";
       }
       leaf dictionary-active-record {
         type string;
         description "File Name of Active Dictionary";
       }
     }
     container profiling {
       leaf profile-dump-record {
         type string;
         description "File Name of Profile Dump Record";
       }
     }
   }
   grouping request-appid-protocol-bundle-load-block {
     leaf appid-protocol-bundle-load-result {
       type string;
     }
   }
   grouping request-appid-protocol-bundle-unload-block {
     leaf appid-protocol-bundle-unload-result {
       type string;
     }
   }
   grouping apppack-offline-download-status-block {
     leaf apppack-offline-download-status-detail {
       type string;
       description "Application package offline download status";
     }
   }
   grouping clear-appid-pkt-capture-counter-information-block {
     leaf clear-appid-pkt-capture-counter-information-status {
       type string;
       description "Status of the clear command";
     }
   }
   grouping request-predefined-operation-status-block {
     leaf request-predefined-operation-status-detail {
       type string;
       description "Detail status of request predefined application or group operation";
     }
   }
   grouping domain-controller-status-block {
     list domain-controller-info {
       description "Domain controller info";
       leaf domain {
         type string;
         description "Domain name";
       }
       list domain-controller {
         description "Domain-controller information";
         leaf dc-name {
           type string;
         }
         leaf address {
           type jt:ipaddr;
           description "Name of the address";
         }
         leaf status {
           type string;
           description "Status";
         }
         leaf reason {
           type string;
           description "Reason";
         }
       }
     }
   }
   grouping validate-device-group-user-status-block {
     leaf server-type {
       type string;
       description "Identity management server type";
     }
     leaf logical-domain {
       type string;
       description "Logical System";
     }
     leaf domain {
       type string;
       description "Domain name";
     }
     leaf nametype {
       type string;
       description "Name type";
     }
     leaf namestring {
       type string;
       description "Name string";
     }
     leaf validate-result {
       type string;
       description "Validate result";
     }
     leaf receive-status-msg {
       type string;
       description "Received status message";
     }
     leaf update-time {
       type string;
       description "Update time";
     }
     leaf validate-progress {
       type string;
       description "Validate progress";
     }
   }
   grouping aamw-start-conn-test-block {
     leaf aamw-test-conn-start {
       type string;
     }
   }
   grouping aamw-show-conn-test-status-block {
     leaf aamw-card-info {
       type string;
     }
     leaf aamw-conn-test-status {
       type string;
     }
   }
   grouping aamw-mesg-block {
     leaf aamw-failed-msg {
       type string;
     }
   }
   grouping aamw-cmd-status-block {
     leaf aamw-cmd-msg {
       type string;
     }
   }
   grouping secintel-download-block {
     leaf secintel-download-result {
       type string;
     }
     leaf secintel-download-status-result {
       type string;
       description "Security intellegence download status";
     }
   }
   grouping secintel-uninstall-block {
     leaf secintel-uninstall-result {
       type string;
     }
     leaf secintel-uninstall-status-result {
       type string;
       description "Security intelligence uninstall status";
     }
   }
   grouping rdm-information-block {
     leaf reload-dictionary {
       type string;
       description "Reload dictionary";
     }
     container debug {
       leaf debug-information {
         type string;
         description "File name to write debug information";
       }
     }
     container rdm-summary {
       description "Show remote service management summary information";
       container service-activations {
         leaf received-count {
           type uint64;
           description "Received count";
         }
         leaf ack-count {
           type uint64;
           description "Total ack sent";
         }
         leaf nack-count {
           type uint64;
           description "Total nack sent";
         }
         leaf inprogress-count {
           type uint64;
           description "In progress count";
         }
       }
       container service-deactivations {
         leaf received-count {
           type uint64;
           description "Received count";
         }
         leaf ack-count {
           type uint64;
           description "Total ack sent";
         }
         leaf nack-count {
           type uint64;
           description "Total nack sent";
         }
         leaf inprogress-count {
           type uint64;
           description "In progress count";
         }
       }
       container sd-by-connection-state {
         leaf up-count {
           type uint32;
           description "Count in up state";
         }
         leaf down-count {
           type uint32;
           description "Count in down state";
         }
       }
       container service-session-by-state {
         leaf active-count {
           type int32;
           description "Count in active state";
         }
         leaf provisioning-count {
           type int32;
           description "Count in provisioning states";
         }
         leaf deprovisioning-count {
           type int32;
           description "Count in deprovisioning states";
         }
       }
     }
     container services {
       description "Show remote service management service sessions";
       list service-session {
         leaf session-id {
           type string;
           description "Service session sdb id";
         }
         leaf subscriber-session-id {
           type string;
           description "Subscriber session sdb id";
         }
         leaf service-state {
           type string;
           description "Service state";
         }
         leaf service-name {
           type string;
           description "Service name";
         }
       }
       list service-device-brief-entry {
         leaf sd-name {
           type string;
           description "Service device name";
         }
         leaf sd-state {
           type string;
           description "Service device state";
         }
         leaf provisioned-state {
           type string;
         }
       }
     }
     list subscriber-session {
       description "Show subscriber session";
       list service-session {
         description "Show service session";
         leaf session-id {
           type string;
           description "Service session sdb id";
         }
         leaf subscriber-session-id {
           type string;
           description "Subscriber session sdb id";
         }
         leaf service-state {
           type string;
           description "Service state";
         }
         leaf service-name {
           type string;
           description "Service name";
         }
       }
     }
     container subscribers {
       description "Show remote service management subscriber service sessions";
       list subscriber-session {
         leaf subscriber-session-id {
           type string;
           description "Subscriber session sdb id";
         }
         leaf session-id {
           type string;
           description "Service session sdb id";
         }
         leaf service-state {
           type string;
           description "Service state";
         }
         leaf service-name {
           type string;
           description "Service name";
         }
         list service-session {
           leaf session-id {
             type string;
             description "Service session sdb id";
           }
           leaf subscriber-session-id {
             type string;
             description "Subscriber session sdb id";
           }
           leaf service-state {
             type string;
             description "Service state";
           }
           leaf service-name {
             type string;
             description "Service name";
           }
         }
       }
       list service-session {
         leaf session-id {
           type string;
           description "Service session sdb id";
         }
         leaf subscriber-session-id {
           type string;
           description "Subscriber session sdb id";
         }
         leaf service-state {
           type string;
           description "Service state";
         }
         leaf service-name {
           type string;
           description "Service name";
         }
       }
       list service-device-brief-entry {
         leaf sd-name {
           type string;
           description "Service device name";
         }
         leaf sd-state {
           type string;
           description "Service device state";
         }
         leaf provisioned-state {
           type string;
         }
       }
     }
     container service-devices {
       description "Show remote service management service devices";
       list service-device {
         description "Service device information";
         leaf sd-name {
           type string;
           description "Service device name";
         }
         leaf sd-state {
           type string;
           description "Service device state";
         }
         leaf sd-eligible-cnt {
           type uint32;
           description "Service device eligible service count";
         }
         leaf sd-provisioned-cnt {
           type uint32;
           description "Service device provisioned count";
         }
         leaf provisioning-method {
           type string;
         }
         container service-device-info {
           leaf sd-name {
             type string;
             description "Service device name";
           }
           leaf sd-state {
             type string;
             description "Service device state";
           }
           leaf routing-instance {
             type string;
             description "Routing instance";
           }
           leaf sd-address {
             type string;
             description "Service device address";
           }
           leaf last-state-change-time {
             type string;
             description "Last time state changed";
           }
           leaf vlan-id-list-raw {
             type string;
             description "Vlan id list";
           }
           leaf sd-dictionary {
             type string;
             description "Dictionary File";
           }
           leaf sd-eligible-cnt {
             type uint32;
             description "Service device eligible service count";
           }
           leaf sd-provisioned-cnt {
             type uint32;
             description "Service device provisioned count";
           }
         }
         container provisioning-method-information {
           leaf provisioning-method {
             type string;
           }
           leaf user-name {
             type uint32;
             description "Login user name";
           }
           leaf connection-retry-interval {
             type uint32;
             description "Connection retry interval";
           }
           leaf response-timeout {
             type uint32;
             description "Response timeout value";
           }
           leaf response-timeout-count {
             type uint32;
             description "Response timeout count";
           }
           leaf bulk-interval {
             type uint32;
             description "Maximum wait interval before bulk commit";
           }
           leaf bulk-limit {
             type uint32;
             description "Maximum requests per bulk commit";
           }
           leaf reconfigure-bulk-limit {
             type uint32;
             description "Maximum requests per bulk reconfigure";
           }
           leaf port {
             type uint32;
             description "TCP port number";
           }
         }
         container bulk-round-trip-time {
           leaf bulk-rt-min {
             type uint32;
             description "Bulk round trip minimum";
           }
           leaf bulk-rt-max {
             type uint32;
             description "Bulk round trip maximum";
           }
           leaf bulk-rt-average {
             type uint32;
             description "Bulk round trip average";
           }
           leaf bulk-rt-last {
             type uint32;
             description "Bulk round trip last";
           }
         }
         container bulk-count-history {
           leaf bulk-count-min {
             type uint32;
             description "Bulk count minimum";
           }
           leaf bulk-count-max {
             type uint32;
             description "Bulk count maximum";
           }
           leaf bulk-count-average {
             type uint32;
             description "Bulk count average";
           }
           leaf bulk-count-last {
             type uint32;
             description "Bulk count last";
           }
         }
         list service-session {
           leaf session-id {
             type string;
             description "Service session sdb id";
           }
           leaf subscriber-session-id {
             type string;
             description "Subscriber session sdb id";
           }
           leaf service-state {
             type string;
             description "Service state";
           }
           leaf service-name {
             type string;
             description "Service name";
           }
         }
         container sd-service-provisioning-stats {
           leaf attempted {
             type uint64;
             description "Attempted count";
           }
           leaf succeeded {
             type uint64;
             description "Succeeded count";
           }
           leaf failed {
             type uint64;
             description "Failed count";
           }
           leaf reject {
             type uint32;
             description "Total reject sent";
           }
           leaf timeout {
             type uint32;
             description "Total timeout count";
           }
           leaf inprogress-count {
             type uint64;
             description "In progress count";
           }
           leaf reconfigure-pending {
             type uint32;
             description "Reconfigure pending count";
           }
           leaf queued {
             type uint32;
             description "Queued count";
           }
         }
         container sd-service-deprovisioning-stats {
           leaf attempted {
             type uint64;
             description "Attempted count";
           }
           leaf succeeded {
             type uint64;
             description "Succeeded count";
           }
           leaf failed {
             type uint64;
             description "Failed count";
           }
           leaf reject {
             type uint32;
             description "Total reject sent";
           }
           leaf timeout {
             type uint32;
             description "Total timeout count";
           }
           leaf inprogress-count {
             type uint64;
             description "In progress count";
           }
           leaf queued {
             type uint32;
             description "Queued count";
           }
         }
         container sd-reconfigure-stats {
           leaf received-count {
             type uint64;
             description "Received count";
           }
           leaf succeeded {
             type uint64;
             description "Succeeded count";
           }
           leaf failed {
             type uint64;
             description "Failed count";
           }
           leaf requests-pending {
             type uint64;
             description "Reconfigure pending count";
           }
         }
         leaf routing-instance {
           type string;
           description "Routing instance";
         }
         leaf sd-address {
           type string;
           description "Service device address";
         }
         leaf last-state-change-time {
           type string;
           description "Last time state changed";
         }
         leaf vlan-id-list-raw {
           type string;
           description "Vlan id list";
         }
         leaf sd-dictionary {
           type string;
           description "Dictionary File";
         }
         leaf user-name {
           type uint32;
           description "Login user name";
         }
         leaf connection-retry-interval {
           type uint32;
           description "Connection retry interval";
         }
         leaf response-timeout {
           type uint32;
           description "Response timeout value";
         }
         leaf response-timeout-count {
           type uint32;
           description "Response timeout count";
         }
         leaf bulk-interval {
           type uint32;
           description "Maximum wait interval before bulk commit";
         }
         leaf bulk-limit {
           type uint32;
           description "Maximum requests per bulk commit";
         }
         leaf reconfigure-bulk-limit {
           type uint32;
           description "Maximum requests per bulk reconfigure";
         }
         leaf port {
           type uint32;
           description "TCP port number";
         }
       }
     }
     container statistics {
       description "Show remote service management statistics";
       container service-activations {
         leaf received-count {
           type uint64;
           description "Received count";
         }
         leaf ack-count {
           type uint64;
           description "Total ack sent";
         }
         leaf nack-count {
           type uint64;
           description "Total nack sent";
         }
         leaf inprogress-count {
           type uint64;
           description "In progress count";
         }
         leaf reconfigure-pending {
           type uint32;
           description "Reconfigure pending count";
         }
         leaf queued {
           type uint32;
           description "Queued count";
         }
         leaf attempted {
           type uint64;
           description "Attempted count";
         }
         leaf succeeded {
           type uint64;
           description "Succeeded count";
         }
         leaf failed {
           type uint64;
           description "Failed count";
         }
         leaf reject {
           type uint32;
           description "Total reject sent";
         }
         leaf timeout {
           type uint32;
           description "Total timeout count";
         }
         leaf requests-pending {
           type uint64;
           description "Reconfigure pending count";
         }
       }
       container service-deactivations {
         leaf received-count {
           type uint64;
           description "Received count";
         }
         leaf ack-count {
           type uint64;
           description "Total ack sent";
         }
         leaf nack-count {
           type uint64;
           description "Total nack sent";
         }
         leaf inprogress-count {
           type uint64;
           description "In progress count";
         }
       }
       container bulk-round-trip-time {
         leaf bulk-rt-min {
           type uint32;
           description "Bulk round trip minimum";
         }
         leaf bulk-rt-max {
           type uint32;
           description "Bulk round trip maximum";
         }
         leaf bulk-rt-average {
           type uint32;
           description "Bulk round trip average";
         }
         leaf bulk-rt-last {
           type uint32;
           description "Bulk round trip last";
         }
       }
       container bulk-count-history {
         leaf bulk-count-min {
           type uint32;
           description "Bulk count minimum";
         }
         leaf bulk-count-max {
           type uint32;
           description "Bulk count maximum";
         }
         leaf bulk-count-average {
           type uint32;
           description "Bulk count average";
         }
         leaf bulk-count-last {
           type uint32;
           description "Bulk count last";
         }
       }
       container sd-service-provisioning-stats {
         leaf attempted {
           type uint64;
           description "Attempted count";
         }
         leaf succeeded {
           type uint64;
           description "Succeeded count";
         }
         leaf failed {
           type uint64;
           description "Failed count";
         }
         leaf reject {
           type uint32;
           description "Total reject sent";
         }
         leaf timeout {
           type uint32;
           description "Total timeout count";
         }
         leaf inprogress-count {
           type uint64;
           description "In progress count";
         }
         leaf reconfigure-pending {
           type uint32;
           description "Reconfigure pending count";
         }
         leaf queued {
           type uint32;
           description "Queued count";
         }
         leaf requests-pending {
           type uint64;
           description "Reconfigure pending count";
         }
       }
       container sd-service-deprovisioning-stats {
         leaf attempted {
           type uint64;
           description "Attempted count";
         }
         leaf succeeded {
           type uint64;
           description "Succeeded count";
         }
         leaf failed {
           type uint64;
           description "Failed count";
         }
         leaf reject {
           type uint32;
           description "Total reject sent";
         }
         leaf timeout {
           type uint32;
           description "Total timeout count";
         }
         leaf inprogress-count {
           type uint64;
           description "In progress count";
         }
         leaf queued {
           type uint32;
           description "Queued count";
         }
       }
       container sd-reconfigure-stats {
         leaf received-count {
           type uint64;
           description "Received count";
         }
         leaf succeeded {
           type uint64;
           description "Succeeded count";
         }
         leaf failed {
           type uint64;
           description "Failed count";
         }
         leaf requests-pending {
           type uint64;
           description "Reconfigure pending count";
         }
       }
     }
     container reconfigure {
       description "Reconfigure remote device";
       leaf reconfigure-sd {
         type string;
         description "Reconfigure service device";
       }
     }
   }
   grouping tdir-flb-maintenance-down-status-block {
     leaf tdir-req-flb-destination-maintenance-down-status {
       type string;
       description "Prints the status";
     }
   }
   grouping force-dns-options-block {
     leaf force-dns-message {
       type string;
       description "Force dns-resolution to happen";
     }
   }
   grouping update-db-filepath-block {
     leaf update-db-filepath-message {
       type string;
       description "Update the url-filter database for a given file path";
     }
     leaf validate-db-message {
       type string;
       description "Status message";
     }
   }
   grouping validate-db-options-block {
     leaf validate-db-message {
       type string;
       description "Status message";
     }
   }
   grouping request-delete-gencfg-block {
     leaf delete-gencfg-data {
       type string;
       description "Delete gencfg data";
     }
   }
   grouping lacp-link-switchover-block {
     leaf aggregate-name {
       type string;
       description "Aggregated Interface name";
     }
     leaf lacp-status {
       type string;
       description "Lacp return status";
     }
   }
   grouping raid-information-block {
     leaf raid-status {
       type string;
     }
     list raid-members {
       leaf raid-member-device {
         type string;
       }
       leaf raid-member-format {
         type string;
       }
       leaf raid-member-name {
         type string;
       }
       leaf raid-member-type {
         type string;
       }
       leaf raid-member-status {
         type string;
       }
       leaf raid-member-size {
         type string;
       }
       leaf raid-member-offset {
         type string;
       }
     }
   }
   grouping external-ssd-op-result-block {
     leaf external-ssd-op-result-summary {
       type string;
     }
   }
   grouping vmhost-remote-file-copy-information-block {
     leaf error-string {
       type string;
     }
     leaf message-string {
       type string;
     }
   }
   grouping vmhost-local-file-copy-information-block {
     leaf error-string {
       type string;
     }
     leaf message-string {
       type string;
     }
   }
   grouping snmp-spoof-trap-results-block {
     leaf snmp-spoofable-traps {
       type string;
       description "SNMP traps supported for spoofing";
     }
     leaf snmp-spoof-trap-result {
       type string;
       description "Result of SNMP 'spoof-trap' request";
     }
   }
   grouping snmp-utility-mib-results-block {
     leaf snmp-utility-mib-result {
       type string;
       description "Result of SNMP 'utility-mib' request";
     }
   }
   grouping ancp-oam-information-block {
     list ancp-oam {
       description "Information about a single OAM request";
       leaf ancp-oam-request-status {
         type string;
         description "OAM request status";
       }
       leaf ancp-oam-response-code {
         type uint32;
         description "OAM response code";
       }
       leaf ancp-oam-response-text {
         type string;
         description "OAM response status";
       }
       leaf ancp-oam-response-type {
         type string;
         description "OAM response type";
       }
     }
   }
   grouping chassis-mic-state-block {
     leaf summary {
       type string;
     }
     leaf-list error-info {
       type string;
     }
   }
   grouping chassis-optics-state-block {
     leaf summary {
       type string;
     }
     leaf-list error-info {
       type string;
     }
   }
   grouping chassis-fpc-state-block {
     leaf summary {
       type string;
     }
     leaf-list error-info {
       type string;
     }
   }
   grouping chassis-fabric-plane-state-block {
     leaf summary {
       type string;
     }
     leaf-list error-info {
       type string;
     }
   }
   grouping chassis-afeb-state-block {
     leaf summary {
       type string;
     }
     leaf-list error-info {
       type string;
     }
   }
   grouping chassis-tfeb-state-block {
     leaf summary {
       type string;
     }
     leaf-list error-info {
       type string;
     }
   }
   grouping chassis-routing-engine-state-block {
     leaf summary {
       type string;
     }
     leaf message {
       type string;
     }
     leaf error {
       type string;
     }
     leaf master-switch-readiness-status {
       type string;
       description "Current status of graceful Routing Engine Switchover";
     }
     leaf nonstop-routing-status {
       type string;
       description "Current status of nonstop routing";
     }
   }
   grouping chassis-fpm-block {
     leaf summary {
       type string;
     }
     leaf-list error-info {
       type string;
     }
   }
   grouping chassis-beacon-information-block {
     container chassis-beacon-item {
       leaf beacon-name {
         type string;
       }
       leaf beacon-state {
         type string;
       }
     }
   }
   grouping helper-self-mirror-enable-disable-block {
     leaf smpl-request-start-stop-status {
       type string;
       description "Request self port-mirroring status";
     }
   }
   grouping request-vnf-information-block {
     leaf error-string {
       type string;
     }
     leaf message-string {
       type string;
     }
   }
   grouping request-packet-capture-start-result-block {
     leaf request-packet-capture-start-status {
       type string;
     }
   }
   grouping request-packet-capture-stop-result-block {
     leaf request-packet-capture-stop-status {
       type string;
     }
   }
   grouping wlan-access-point-packet-capture-start-block {
     container capture-local {
       description "Local packet capture operation";
       leaf capture-interface {
         type string;
         description "Interface on which the packet capture is enabled";
       }
       leaf capture-file {
         type string;
         description "Path to store the file captured";
       }
       leaf capture-duration {
         type uint32;
         description "Duration upto which the packet capture is enabled";
       }
       leaf capture-file-size {
         type uint32;
         description "Maximum packet capture file size";
       }
     }
   }
   grouping wlan-access-point-packet-capture-stop-block {
     container capture-local {
       description "Local packet capture operation";
       leaf capture-interface {
         type string;
         description "Interface on which the packet capture is enabled";
       }
       leaf capture-file {
         type string;
         description "Path to store the file captured";
       }
       leaf capture-duration {
         type uint32;
         description "Duration upto which the packet capture is enabled";
       }
       leaf capture-file-size {
         type uint32;
         description "Maximum packet capture file size";
       }
     }
   }
   grouping flight-recorder-information-block {
     container summary {
       leaf output {
         type string;
       }
     }
   }
   grouping rv-request-policy-information-block {
     leaf ip-prefix-count {
       type uint32;
     }
     leaf ip6-prefix-count {
       type uint32;
     }
   }
   grouping rv-reload-source-file-information-block {
     leaf rv-reload-source-file-name {
       type string;
     }
   }
   grouping mobile-gateway-sm-af-call-trace-start-block {
   }
   grouping mobile-gateways-call-trace-start-information-block {
     container call-trace-start {
       leaf call-trace-services-pic {
         type string;
         description "Service pic";
       }
       leaf call-trace-start-status {
         type string;
         description "Call trace start status";
       }
     }
   }
   grouping mobile-gateways-call-trace-stop-information-block {
     container call-trace-stop {
       leaf call-trace-services-pic {
         type string;
         description "Service pic";
       }
       leaf call-trace-stop-status {
         type string;
         description "Call trace stop status";
       }
     }
   }
   grouping mobile-gateways-call-trace-information-block {
     container call-trace {
       leaf call-trace-identifier {
         type string;
         description "Identifier for the call trace";
       }
       leaf call-trace-file {
         type string;
         description "File for the call trace";
       }
       leaf call-trace-status {
         type string;
         description "Call trace status";
       }
       leaf call-trace-create-mask {
         type string;
         description "Mask of service pics - created";
       }
       leaf call-trace-complete-mask {
         type string;
         description "Mask of service pics - complete";
       }
       leaf call-trace-start-status {
         type string;
         description "Call trace start status";
       }
       leaf call-trace-services-pic {
         type string;
         description "Service pic";
       }
       leaf call-trace-comment {
         type string;
         description "Comment for this call trace";
       }
       leaf imsi {
         type string;
         description "IMSI of the subscriber";
       }
       leaf msisdn {
         type string;
         description "MS ISDN of the subscriber";
       }
       leaf call-trace-next-calls {
         type uint32;
         description "Next call count";
       }
       leaf apn-name {
         type string;
         description "Access Point Name";
       }
       leaf domain-name {
         type string;
         description "Domain Name";
       }
       leaf subscriber-address-v4 {
         type jt:ipaddr;
         description "IPV4 address of the subscriber";
       }
       leaf subscriber-address-v6 {
         type jt:ipv6addr;
         description "IPV6 address of the subscriber";
       }
       leaf user-name {
         type string;
         description "User Name";
       }
       leaf subscriber-name {
         type string;
         description "Subscriber Name";
       }
       leaf call-trace-count {
         type string;
         description "Count of calls traced";
       }
       leaf fpc-slot {
         type int32;
         description "FPC slot";
       }
       leaf pic-slot {
         type int32;
         description "PIC slot";
       }
     }
   }
   grouping virtual-chassis-diagnostic-information-block {
     container test-information {
       description "Details of the test";
       leaf test-name {
         type string;
         description "Name of the Device Reachability test";
       }
     }
     list current-test {
       description "Serial number of the test being performed";
       leaf test-number {
         type string;
         description "Serial Number of the test";
       }
     }
     list device-reachability-information {
       description "Device reachability statistics";
       leaf-list reachability-acknowledge {
         type string;
       }
       leaf connectivity-statistics-header {
         type string;
       }
       leaf session-information {
         type string;
       }
       leaf session-id {
         type uint32;
         description "Session ID";
       }
       leaf packet-response-information {
         type string;
       }
       leaf packet-count {
         type uint32;
         description "Total number of packets sent";
       }
       leaf packets-sent {
         type uint64;
       }
       leaf packets-received {
         type uint64;
       }
       leaf packets-sendfail {
         type uint32;
         description "Number of packets dropped";
       }
       leaf packet-breakup-information {
         type string;
       }
       leaf packets-unknown {
         type uint32;
         description "Number of unknown packets";
       }
       leaf packets-timedout {
         type uint32;
         description "Number of packets received after timeout";
       }
       leaf packets-duplicate-reply {
         type uint32;
         description "Number of duplicate reply packets";
       }
       leaf round-trip-information {
         type string;
       }
       leaf round-trip-time-minimum {
         type uint32;
         description "Minimum round trip time in seconds";
       }
       leaf round-trip-time-average {
         type uint32;
         description "Average round trip time in seconds";
       }
       leaf round-trip-time-maximum {
         type uint32;
         description "Minimum round trip time in seconds";
       }
       leaf test-interval {
         type string;
         description "Interval between successive tests";
       }
     }
     list virtual-chassis-diagnostic-error {
       leaf name {
         type string;
       }
     }
   }
 }
