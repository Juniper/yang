module junos-genstate-l2ng-l2ald-vlan-instance-information {
   yang-version 1;
   namespace "http://yang.juniper.net/junos/genstate/l2ng-l2ald-vlan-instance-information";
   prefix jgllvii;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ng-l2ald-vlan-instance-information";

   revision 2025-01-01 {
     description "Junos: 25.4R1.12";
   }

   grouping l2ng-l2ald-vlan-instance-information-top {
     description "Top-level grouping";
     container l2ng-l2ald-vlan-instance-information {
       description "Operational bridge instances that can be passed to netapp commands";
       list l2ng-l2ald-vlan-instance-group {
         leaf l2ng-l2rtb-mac-limit {
           type uint32;
           description "Maximum number of MAC addresses that can be learned on this routing instance";
         }
         leaf l2ng-l2rtb-local-macs-learned {
           type uint32;
           description "Number of configured static and dynamic MACs that are learned on this routing instance";
         }
         leaf l2ng-l2rtb-mac-ip-limit {
           type uint32;
           description "Maximum number of MAC+IP bindings that can be learned on this routing instance";
         }
         leaf l2ng-l2rtb-mac-ip-learned {
           type uint32;
           description "Number of MAC+IP bindings that are learned on this routing instance";
         }
         leaf l2ng-l2rtb-sequence-number {
           type uint32;
           description "Current routing instance sequence number";
         }
         leaf l2ng-l2rtb-name {
           type string;
           description "Name of the routing instance";
         }
         leaf l2ng-l2rtb-vlan-name {
           type string;
           description "Name of the bridging domain";
         }
         leaf l2ng-l2rtb-vlan-tag {
           type string;
         }
         list l2ng-l2rtb-vlan-member {
           key "l2ng-l2rtb-vlan-member-interface";
           leaf l2ng-l2rtb-vlan-member-interface {
             type string;
           }
           leaf l2ng-l2rtb-vlan-member-tagness {
             type string;
           }
           leaf l2ng-l2rtb-vlan-member-interface-mode {
             type string;
           }
           leaf l2ng-l2rtb-inter-switch-link {
             type string;
           }
           leaf l2ng-l2rtb-vlan-member-interface-guid {
             type uint64;
           }
         }
         leaf l2ng-l2rtb-instance-state {
           type string;
         }
         leaf l2ng-l2rtb-evpn-extension {
           type string;
         }
         leaf l2ng-l2rtb-pvlan-type {
           type string;
         }
         leaf l2ng-l2rtb-pvlan {
           type string;
         }
         leaf l2ng-l2rtb-instance-flags {
           type string;
         }
         leaf l2ng-l2rtb-vlan-internal-index {
           type string;
         }
         leaf l2ng-l2rtb-vlan-generation-index {
           type string;
         }
         leaf l2ng-l2rtb-origin {
           type string;
         }
         leaf l2ng-l2rtb-mac-aging-status {
           type string;
         }
         leaf l2ng-l2rtb-mac-aging-time {
           type uint32;
         }
         leaf l2ng-l2rtb-vlan-mac-move-limit {
           type uint32;
         }
         leaf l2ng-l2rtb-vlan-mac-move-action {
           type string;
         }
         leaf l2ng-vlan-unknown-unicast-nexthop {
           type string;
         }
         leaf l2ng-l2rtb-vlan-l3-interface {
           type string;
         }
         leaf l2ng-l2rtb-mac-ip-visible {
           type string;
         }
         leaf l2ng-l2rtb-vlan-vxlan-enabled {
           type string;
         }
         leaf l2ng-l2rtb-bridge-evpn-num-replicator {
           type uint32;
         }
         leaf l2ng-l2rtb-bridge-evpn-num-mh-ext-replicator {
           type uint32;
         }
         leaf l2ng-l2rtb-vlan-member-tagged-count {
           type uint32;
         }
         leaf l2ng-l2rtb-vlan-member-untagged-count {
           type uint32;
         }
         leaf l2ng-l2rtb-macs-learned {
           type uint32;
           description "Number of configured static and dynamic MACs that are learned on this routing instance";
         }
         list l2ng-l2rtb-pvlan-secondary-vlan {
           key "l2ng-l2rtb-secondary-vlan-id l2ng-l2rtb-secondary-vlan-name";
           leaf l2ng-l2rtb-secondary-vlan-id {
             type uint32;
           }
           leaf l2ng-l2rtb-secondary-vlan-name {
             type string;
           }
         }
         leaf l2ng-l2rtb-rtt-guid {
           type uint64;
         }
         leaf l2ng-l2rtb-vlan-guid {
           type uint64;
         }
       }
     }
   }
   augment "/jgs:genstate" {
     description "Adds l2ng-l2ald-vlan-instance-information to top-level genstate";
     uses l2ng-l2ald-vlan-instance-information-top;
   }
 }
