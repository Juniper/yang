module junos-genstate-l2ng-l2ald-iff-interface-information {
   yang-version 1;
   namespace "http://yang.juniper.net/junos/genstate/l2ng-l2ald-iff-interface-information";
   prefix jglliii;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for l2ng-l2ald-iff-interface-information";

   revision 2025-01-01 {
     description "Junos: 25.4R1.12";
   }

   grouping l2ng-l2ald-iff-interface-information-top {
     description "Top-level grouping";
     container l2ng-l2ald-iff-interface-information {
       description "Top-level container";
       list l2ng-l2ald-iff-interface-entry {
         key "l2iff-interface-name l2iff-interface-index l2iff-interface-ifd-index l2iff-interface-ifl-index";
         leaf l2iff-interface-rtt-name {
           type string;
           description "Routing Instance name";
         }
         leaf l2iff-interface-name {
           type string;
           description "Logical interface name";
         }
         leaf l2iff-interface-vlan-name {
           type string;
           description "BD name in compressed form";
         }
         leaf l2iff-interface-vlan-id {
           type string;
           description "Bridge domain VLAN";
         }
         leaf l2iff-interface-mac-limit {
           type uint32;
           description "Maximum number of MAC addresses that can be learned on this interface family";
         }
         leaf l2iff-interface-mac-ip-limit {
           type uint32;
           description "Maximum number of MAC+IP bindings that can be learned on this interface family";
         }
         leaf l2iff-interface-vlan-member-stp-state {
           type string;
           description "STP state for this IFBD";
         }
         leaf l2iff-interface-flags {
           type string;
           description "Attributes associated with this interface family";
         }
         leaf l2iff-interface-vlan-member-tagness {
           type string;
           description "Interface Taggness";
         }
         leaf l2iff-interface-index {
           type uint32;
           description "Interface family index";
         }
         leaf l2iff-interface-generation {
           type uint32;
           description "Layer 2 interface family creation time";
         }
         leaf l2iff-interface-rt-index {
           type uint32;
           description "Routing instance to which the interface family belongs";
         }
         leaf l2iff-interface-ifd-index {
           type uint32;
           description "Physical media to which the interface family belongs";
         }
         leaf l2iff-interface-ifl-index {
           type uint32;
           description "Logical interface to which the interface family belongs";
         }
         leaf l2iff-interface-af-value {
           type uint32;
           description "Address family to which the interface family belongs";
         }
         leaf l2iff-interface-sequence-number {
           type uint32;
           description "Current interface family sequence number";
         }
         leaf l2iff-interface-mac-sequence-number {
           type uint32;
           description "Current MAC address sequence number for this interface family";
         }
         leaf l2iff-interface-macs-learned {
           type uint32;
           description "Number of configured static and dynamic MACs that are learned on this interface family";
         }
         leaf l2iff-interface-config-smacs-learned {
           type uint32;
           description "Number of configured static MACs that are learned on this interface family";
         }
         leaf l2iff-interface-non-config-smacs-learned {
           type uint32;
           description "Number of non configured static MACs that are learned on this interface family";
         }
         leaf l2iff-interface-mac-ip-learned {
           type uint32;
           description "Number of configured static and dynamic MAC+IPs that are learned on this interface family";
         }
         leaf l2iff-interface-handle {
           type uint32;
           description "Handle associated with this interface family";
         }
         leaf l2iff-interface-config-mac-limit {
           type uint32;
           description "Maximum number of MAC addresses that is configured on this interface family";
         }
         leaf l2iff-interface-config-smac-count {
           type uint32;
           description "Number of static MAC addresses that is configured on this interface family";
         }
         leaf l2iff-interface-config-smac-applied {
           type uint32;
           description "Number of static MAC addresses that is successfully applied to MAC DB on this interface family";
         }
         leaf l2iff-interface-config-state {
           type string;
           description "Configured state attributes associated with this interface family";
         }
         leaf l2iff-interface-config-flags {
           type string;
           description "Configured attributes associated with this interface family";
         }
         leaf l2iff-interface-config-previous-flags {
           type string;
           description "Previous configured attributes associated with this interface family";
         }
         leaf l2iff-interface-config-smac-address {
           type jt:mac-addr;
           description "Configured static media access control address associated with this interface family";
         }
         leaf l2iff-interface-config-smac-vlan {
           type uint32;
           description "Configured VLAN ID for the static MAC associated with this interface family";
         }
         leaf l2iff-interface-config-smac-flags {
           type string;
           description "Configured static MAC attributes associated with this interface family";
         }
         leaf l2iff-interface-interface-type {
           type string;
           description "Type of interface (IFF/IFBD)";
         }
         leaf l2iff-interface-rtsock-write-errors {
           type uint32;
           description "Number of times kernel write has failed.";
         }
         leaf l2iff-interface-trunk-vlan {
           type uint32;
           description "Specify the incoming VLAN id which gets translated.";
         }
         leaf l2iff-interface-rewrite-op {
           type string;
           description "Configured rewrite operation.";
         }
         leaf l2iff-interface-vstp-index {
           type uint32;
           description "VSTP index";
         }
         leaf l2iff-interface-lr-name {
           type string;
           description "Logical router name";
         }
         leaf l2iff-interface-rbeb-mac-address {
           type jt:mac-addr;
           description "Media access control address of remote backbone edge bridge (BEB)";
         }
       }
     }
   }
   augment "/jgs:genstate" {
     description "Adds l2ng-l2ald-iff-interface-information to top-level genstate";
     uses l2ng-l2ald-iff-interface-information-top;
   }
 }
