module junos-genstate-stp-interface-information {
   yang-version 1;
   namespace "http://yang.juniper.net/junos/genstate/stp-interface-information";
   prefix jgsii;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for stp-interface-information";

   revision 2025-01-01 {
     description "Junos: 25.4R1.12";
   }

   grouping stp-interface-information-top {
     description "Top-level grouping";
     container stp-interface-information {
       description "Information about one or more Spanning Tree Protocol interfaces for one or more Spanning Tree Protocol instances";
       list stp-instance-information {
         key "routing-instance-name";
         leaf routing-instance-name {
           type string;
           description "Routing instance name";
         }
         list stp-instance {
           key "instance-id";
           leaf instance-id {
             type int32;
             description "STP instance ID";
           }
           leaf vlan-id {
             type int32;
             description "VLAN identifier";
           }
           container stp-interfaces {
             description "Information about one or more Spanning Tree Protocol interfaces";
             list stp-interface-entry {
               key "interface-name";
               leaf interface-name {
                 type string;
                 description "Name of interface";
               }
               leaf port-number {
                 type int32;
                 description "Port number";
               }
               leaf designated-port-number {
                 type int32;
                 description "Designated port number";
               }
               leaf designated-bridge-mac {
                 type string;
                 description "Media access control address of bridge";
               }
               leaf port-cost {
                 type uint32;
                 description "Port cost";
               }
               leaf port-state {
                 type string;
                 description "Port state";
               }
               leaf port-role {
                 type string;
                 description "Role of port";
               }
               leaf port-priority {
                 type int32;
                 description "Port priority";
               }
               leaf designated-port-priority {
                 type int32;
                 description "Designated port priority";
               }
               leaf designated-bridge-priority {
                 type int32;
                 description "Bridge priority";
               }
               leaf link-type {
                 type string;
                 description "Type of link";
               }
               leaf port-migrated-protocol {
                 type string;
                 description "Migrated protocol for port";
               }
               leaf boundary-port {
                 type string;
                 description "STP boundary port";
               }
             }
           }
         }
       }
     }
   }
   augment "/jgs:genstate" {
     description "Adds stp-interface-information to top-level genstate";
     uses stp-interface-information-top;
   }
 }
