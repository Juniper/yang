module junos-genstate-license-feature-list-information {
   yang-version 1;
   namespace "http://yang.juniper.net/junos/genstate/license-feature-list-information";
   prefix jglfli;

   import junos-genstate {
     prefix jgs;
     revision-date 2025-01-01;
   }

   import junos-common-types {
     prefix jt;
     revision-date 2025-01-01;
   }

   organization
     "Juniper Networks, Inc.";

   contact
     "Juniper Networks, Inc.

      1133 Innovation Way
      Sunnyvale, CA 94089

      +1 888 314-5822

      E-mail: yang-support@juniper.net";

   description "Junos genstate data model for license-feature-list-information";

   revision 2025-01-01 {
     description "Junos: 25.4R1.12";
   }

   grouping license-feature-list-information-top {
     description "Top-level grouping";
     container license-feature-list-information {
       description "Information about features applicable on this device";
       list feature-info {
         key "name";
         leaf feature-id {
           type int32;
           description "Feature Id";
         }
         leaf name {
           type string;
           description "Identifier for this object";
         }
       }
     }
   }
   augment "/jgs:genstate" {
     description "Adds license-feature-list-information to top-level genstate";
     uses license-feature-list-information-top;
   }
 }
