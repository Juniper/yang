/*
 * Copyright (c) 2019 Juniper Networks, Inc.
 * All rights reserved.
 */
 module junos-es-rpc-route {
   namespace "http://yang.juniper.net/junos-es/rpc/route";

   prefix route;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for route command(s)";

   revision 2019-01-01 {
     description "Junos: 18.2R3";
   }

   rpc get-route-information {
     description "Show routing table information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf destination {
         description "IP address and optional prefix length of destination";
         type jt:ipprefix-optional;
       }
       leaf all {
         description "Show all entries, including hidden entries";
         type empty;
       }
       leaf level {
         type enumeration {
           enum "terse" {
             description "Display terse output";
           }
           enum "brief" {
             description "Display brief output";
           }
           enum "detail" {
             description "Display detailed output";
           }
           enum "extensive" {
             description "Display extensive output";
           }
         }
       }
       leaf match {
         type enumeration {
           enum "best" {
             description "Show longest matching route";
           }
           enum "exact" {
             description "Show routes that match exactly";
           }
           enum "range" {
             description "Show all entries in prefix range";
           }
         }
       }
       leaf table {
         description "Name of routing table";
         type string;
       }
       leaf label {
         description "Label of entry in MPLS routing table";
         type union {
           type uint32;
           type string {
             pattern "<.*>|$.*";
           }
         }
       }
       leaf ccc {
         description "Name of entry in MPLS table with a circuit cross-connect interface";
         type string;
       }
       leaf inactive-prefix {
         description "Show inactive route destinations";
         type empty;
       }
       leaf inactive-path {
         description "Show inactive paths";
         type empty;
       }
       leaf active-path {
         description "Show active paths";
         type empty;
       }
       leaf private {
         description "Show private table routes";
         type empty;
       }
       leaf damping {
         description "Show entries subjected to particular kind of route damping";
         type enumeration {
           enum "suppressed" {
             description "Entries suppressed due to route damping";
           }
           enum "history" {
             description "Entries that are withdrawn but have history";
           }
           enum "decayed" {
             description "Entries that are decayed but not suppressed";
           }
         }
       }
       container output {
         leaf interface {
           description "Name of interface";
           type union {
             type jt:interface-unit;
             type string {
               pattern "<.*>|$.*";
             }
           }
         }
         leaf address {
           description "Address of interface";
           type string;
         }
       }
       leaf next-hop {
         description "IP address of next hop that is destination for entries";
         type jt:ipaddr;
       }
       leaf source-gateway {
         description "IP address of source router for entries";
         type jt:ipaddr;
       }
       leaf protocol {
         description "Name of protocol that is source for entries";
         type enumeration {
           enum "aggregate" {
             description "Locally generated aggregate route";
           }
           enum "bgp" {
             description "Border Gateway Protocol";
           }
           enum "direct" {
             description "Directly connected routes";
           }
           enum "dvmrp" {
             description "Distance Vector Multicast Routing Protocol";
           }
           enum "evpn" {
             description "EVPN";
           }
           enum "isis" {
             description "Intermediate System-to-Intermediate System";
           }
           enum "esis" {
             description "End System-to-Intermediate System";
           }
           enum "ldp" {
             description "Label Distribution Protocol";
           }
           enum "local" {
             description "Local system addresses";
           }
           enum "ospf" {
             description "Open Shortest Path First";
           }
           enum "ospf2" {
             description "Open Shortest Path First Version 2";
           }
           enum "ospf3" {
             description "Open Shortest Path First Version 3";
           }
           enum "pim" {
             description "Protocol Independent Multicast";
           }
           enum "mvpn" {
             description "BGP-MVPN Protocol";
           }
           enum "rip" {
             description "Routing Information Protocol";
           }
           enum "ripng" {
             description "Routing Information Protocol for IPv6";
           }
           enum "rsvp" {
             description "Resource Reservation Protocol";
           }
           enum "static" {
             description "Statically defined prefixes";
           }
           enum "arp" {
             description "Prefixes learned via ARP";
           }
           enum "frr" {
             description "Prefixes created by Host (Direct route) Fast reroute";
           }
           enum "mpls" {
             description "Multiprotocol Label Switching";
           }
           enum "ccc" {
             description "Circuit cross-connect";
           }
           enum "msdp" {
             description "Multicast Source Discovery Protocol";
           }
           enum "vpn" {
             description "Layer 3 virtual private network";
           }
           enum "l2vpn" {
             description "Layer 2 virtual private network";
           }
           enum "l2circuit" {
             description "Layer 2 circuit";
           }
           enum "rtarget" {
             description "Local route target VPN membership";
           }
           enum "spring-te" {
             description "SPRING Traffic-Engineered";
           }
           enum "tunnel" {
             description "Dynamic tunnel";
           }
           enum "flow" {
             description "Locally defined flow route";
           }
           enum "access" {
             description "Access route";
           }
           enum "access-internal" {
             description "Access-internal route";
           }
           enum "anchor" {
             description "Anchor route";
           }
           enum "bgp-static" {
             description "BGP static route";
           }
           enum "vpls" {
             description "Virtual Private LAN Service";
           }
         }
       }
       container evpn-esi-value {
         leaf esi {
           description "Filter evpn routes for a particular ESI, except evpn MAC routes";
           type string;
         }
       }
       container evpn-mac-address {
         leaf mac_address {
           description "Filter evpn mac routes for a particular MAC";
           type jt:mac-addr;
         }
       }
       container evpn-ethernet-tag-id {
         leaf ethernet-tag {
           description "Filter evpn routes for a particular Ethernet Tag ID";
           type union {
             type uint32;
             type string {
               pattern "<.*>|$.*";
             }
           }
         }
       }
       leaf advertising-protocol-name {
         description "Name of dynamic routing protocol";
         type enumeration {
           enum "bgp" {
             description "Border Gateway Protocol";
           }
           enum "dvmrp" {
             description "Distance Vector Multicast Routing Protocol";
           }
           enum "pim" {
             description "Protocol Independent Multicast";
           }
           enum "rip" {
             description "Routing Information Protocol";
           }
           enum "ripng" {
             description "Routing Information Protocol for IPv6";
           }
           enum "msdp" {
             description "Multicast Source Discovery Protocol";
           }
         }
       }
       leaf neighbor {
         description "IP address of neighbor (local for RIP and RIPng)";
         type jt:ipaddr;
       }
       leaf receive-protocol-name {
         description "Name of dynamic routing protocol";
         type enumeration {
           enum "bgp" {
             description "Border Gateway Protocol";
           }
           enum "rip" {
             description "Routing Information Protocol";
           }
           enum "ripng" {
             description "Routing Information Protocol for IPv6";
           }
           enum "dvmrp" {
             description "Distance Vector Multicast Routing Protocol";
           }
           enum "pim" {
             description "Protocol Independent Multicast";
           }
           enum "msdp" {
             description "Multicast Source Discovery Protocol";
           }
         }
       }
       leaf peer {
         description "IP address of neighbor";
         type jt:ipaddr;
       }
       leaf rd-prefix {
         description "Route distinguisher with ip prefix (rd:prefix)";
         type string;
       }
       leaf match-prefix {
         description "Regular expression to match formatted prefix";
         type string;
       }
       leaf aspath-regex {
         description "BGP AS path regular expression for entries to match";
         type string;
       }
       leaf-list community {
         ordered-by user;
         description "Identifier for community (can include wildcards)";
         type string;
       }
       leaf no-community {
         description "Show entries with no associated community";
         type empty;
       }
       leaf community-name {
         description "Name of configured community policy to match";
         type string;
       }
       leaf label-switched-path {
         description "Name of LSP tunnel associated with entries";
         type string {
           length "1 .. 64";
         }
       }
       leaf static-label-switched-path {
         description "Name of static LSP tunnel associated with entries";
         type string {
           length "1 .. 64";
         }
       }
       leaf hidden {
         description "Show hidden entries";
         type empty;
       }
       leaf validation-state {
         description "Show entries with a given validation state";
         type enumeration {
           enum "unverified" {
             description "Unverified route validation state";
           }
           enum "unknown" {
             description "Unknown route validation state";
           }
           enum "valid" {
             description "Valid route validation state";
           }
           enum "invalid" {
             description "Invalid route validation state";
           }
         }
       }
       leaf te-link-local-node-ip {
         description "Local node's IPv4 address in the traffic-engineering link";
         type string;
       }
       leaf te-link-local-node-iso {
         description "Local node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-remote-node-ip {
         description "Remote node's IPv4 address in the traffic-engineering link";
         type string;
       }
       leaf te-link-remote-node-iso {
         description "Remote node's ISO circuit ID in the traffic-engineering link";
         type string {
           junos:posix-pattern "^([[:xdigit:]]{1,4}[.]){3}[[:xdigit:]]{1,2}$";
           junos:pattern-message "Address must be of the form aaaa.bbbb.cccc.dd";
         }
       }
       leaf te-link-local-ip {
         description "Local IPv4 address of the traffic-engineering link";
         type jt:ipaddr;
       }
       leaf te-link-remote-ip {
         description "Remote IPv4 address of the traffic-engineering link";
         type jt:ipaddr;
       }
       leaf te-node-ip {
         description "IPv4 address of the traffic-engineering node";
         type string;
       }
       leaf te-node-iso {
         description "ISO circuit ID of the traffic-engineering node";
         type string {
           junos:posix-pattern "^([[:xdigit:]]{1,4}[.]){3}[[:xdigit:]]{1,2}$";
           junos:pattern-message "Address must be of the form aaaa.bbbb.cccc.dd";
         }
       }
       leaf te-ipv4-prefix-node-ip {
         description "Originator node's IPv4 address in the traffic-engineering prefix";
         type string;
       }
       leaf te-ipv4-prefix-node-iso {
         description "Originator node's ISO circuit ID in the traffic-engineering prefix";
         type string {
           junos:posix-pattern "^([[:xdigit:]]{1,4}[.]){3}[[:xdigit:]]{1,2}$";
           junos:pattern-message "Address must be of the form aaaa.bbbb.cccc.dd";
         }
       }
       leaf te-ipv4-prefix-ip {
         description "IPv4 address of the traffic-engineering prefix";
         type jt:ipaddr;
       }
       leaf output-queue {
         description "BGP output-queue for advertising protocol";
         type enumeration {
           enum "priority-1" {
             description "BGP output queue priority 1";
           }
           enum "priority-2" {
             description "BGP output queue priority 2";
           }
           enum "priority-3" {
             description "BGP output queue priority 3";
           }
           enum "priority-4" {
             description "BGP output queue priority 4";
           }
           enum "priority-5" {
             description "BGP output queue priority 5";
           }
           enum "priority-6" {
             description "BGP output queue priority 6";
           }
           enum "priority-7" {
             description "BGP output queue priority 7";
           }
           enum "priority-8" {
             description "BGP output queue priority 8";
           }
           enum "priority-9" {
             description "BGP output queue priority 9";
           }
           enum "priority-10" {
             description "BGP output queue priority 10";
           }
           enum "priority-11" {
             description "BGP output queue priority 11";
           }
           enum "priority-12" {
             description "BGP output queue priority 12";
           }
           enum "priority-13" {
             description "BGP output queue priority 13";
           }
           enum "priority-14" {
             description "BGP output queue priority 14";
           }
           enum "priority-15" {
             description "BGP output queue priority 15";
           }
           enum "priority-16" {
             description "BGP output queue priority 16";
           }
           enum "expedited" {
             description "BGP output queue expedited";
           }
         }
       }
       leaf display-client-data {
         description "Show client details";
         type empty;
       }
     }
     output {
       choice output_c {
         case output-tag {
           leaf output {
             type string;
           }
         }
         case actual-tag {
           anyxml route-information;
         }
         case multichassis-tag {
           anyxml multi-routing-engine-results;
         }
       }
     }
   }
   rpc get-forwarding-table-information {
     description "Show entries in all forwarding tables";
     input {
       uses command-forwarding;
       leaf level {
         type enumeration {
           enum "detail" {
             description "Display all routes";
           }
           enum "extensive" {
             description "Display extensive information about routes";
           }
         }
       }
       leaf multicast {
         description "Display multicast routes";
         type empty;
       }
       leaf family {
         description "Name of family";
         type enumeration {
           enum "inet" {
             description "IP version 4 (IPv4)";
           }
           enum "inet6" {
             description "IP version 6 (IPv6)";
           }
           enum "unix" {
             description "UNIX";
           }
           enum "iso" {
             description "International Standards Organization protocol";
           }
           enum "tnp" {
             description "Trivial Network Protocol";
           }
           enum "mpls" {
             description "Multiprotocol Label Switching";
           }
           enum "vpls" {
             description "Virtual private LAN service";
           }
           enum "bridge" {
             description "Bridge (Layer 2 switching)";
           }
           enum "evpn" {
             description "Ethernet Virtual Private LAN services";
           }
           enum "vlan-classification" {
             description "VLAN classification table";
           }
           enum "ethernet-switching" {
             description "Switch forwarding table";
           }
           enum "fibre-channel" {
             description "Fibre channel forwarding table";
           }
           enum "fmembers" {
             description "Fibre channel membership table";
           }
           enum "fabric-multicast" {
             description "Fabric multicast routing table";
           }
           enum "fabric-replication" {
             description "Fabric replication routing table";
           }
           enum "mcsnoop-inet" {
             description "Multicast Snooping INET";
           }
           enum "mcsnoop-inet6" {
             description "Multicast Snooping INET6";
           }
           enum "satellite-vpls" {
             description "Satellite VPLS";
           }
           enum "satellite-inet" {
             description "Multicast Satellite INET";
           }
           enum "satellite-inet6" {
             description "Multicast Satellite INET6";
           }
           enum "evpn-mcsnoop" {
             description "Multicast Snooping EVPN";
           }
           enum "evpn-mcsnoop-v6" {
             description "Multicast Snooping EVPN INET6";
           }
         }
       }
       leaf vpn {
         description "Name of VPN instance";
         type string;
       }
       leaf table {
         description "Name of routing table";
         type string;
       }
       leaf interface-name {
         description "Interface name";
         type string;
       }
       leaf vlan {
         description "VLAN name";
         type string;
       }
       leaf bridge-domain {
         description "Name of bridging domain";
         type string;
       }
       leaf summary {
         description "Display count of routes instead of details";
         type empty;
       }
       leaf matching {
         description "IP prefix and length for entries to match";
         type string;
       }
       leaf destination {
         description "Destination prefix";
         type string;
       }
       leaf learning-vlan-id {
         description "Learning VLAN";
         type string;
       }
       leaf label {
         description "Label for entries to match";
         type union {
           type uint32;
           type string {
             pattern "<.*>|$.*";
           }
         }
       }
       leaf ccc {
         description "Circuit cross-connect interface name for entries to match";
         type union {
           type jt:interface-name;
           type string {
             pattern "<.*>|$.*";
           }
         }
       }
       leaf all {
         description "Display all routing forwarding-tables";
         type empty;
       }
     }
     output {
       choice output_c {
         case output-tag {
           leaf output {
             type string;
           }
         }
         case actual-tag {
           anyxml forwarding-table-information;
         }
         case multichassis-tag {
           anyxml multi-routing-engine-results;
         }
       }
     }
   }
   rpc get-instance-information {
     description "Show routing instances information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf instance-name {
         description "Particular instance name";
         type string;
       }
     }
     output {
       choice output_c {
         case output-tag {
           leaf output {
             type string;
           }
         }
         case actual-tag {
           anyxml instance-information;
         }
         case multichassis-tag {
           anyxml multi-routing-engine-results;
         }
       }
     }
   }
   rpc get-operational-routing-instance-information {
     description "Show operational routing instances";
     output {
       choice output_c {
         case output-tag {
           leaf output {
             type string;
           }
         }
         case actual-tag {
           anyxml operational-routing-instance-information;
         }
         case multichassis-tag {
           anyxml multi-routing-engine-results;
         }
       }
     }
   }
   rpc get-localize-routing-instance-information {
     description "Show instances localization mapping";
     output {
       choice output_c {
         case output-tag {
           leaf output {
             type string;
           }
         }
         case actual-tag {
           anyxml localize-routing-instance-information;
         }
         case multichassis-tag {
           anyxml multi-routing-engine-results;
         }
       }
     }
   }
   rpc get-route-resolution-information {
     description "Show next-hop resolution database";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
           enum "extensive" {
             description "Display extensive output";
           }
         }
       }
       leaf prefix {
         description "IP prefix/length of destination";
         type string;
       }
       leaf table {
         description "Name of resolving table";
         type string;
       }
       leaf index {
         description "Index of resolution tree";
         type union {
           type uint32;
           type string {
             pattern "<.*>|$.*";
           }
         }
       }
     }
     output {
       choice output_c {
         case output-tag {
           leaf output {
             type string;
           }
         }
         case actual-tag {
           anyxml route-resolution-information;
         }
         case multichassis-tag {
           anyxml multi-routing-engine-results;
         }
       }
     }
   }
   rpc get-route-resolution-summary {
     description "Show summary of tree";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml route-resolution-information;
         }
         case multichassis-tag {
           anyxml multi-routing-engine-results;
         }
       }
     }
   }
   rpc get-route-summary-information {
     description "Show routing table statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf table {
         description "Name of routing table";
         type string;
       }
     }
     output {
       choice output_c {
         case output-tag {
           leaf output {
             type string;
           }
         }
         case actual-tag {
           anyxml route-summary-information;
         }
         case multichassis-tag {
           anyxml multi-routing-engine-results;
         }
       }
     }
   }
   rpc get-route-martians {
     description "Show martian networks";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf table {
         description "Name of routing table";
         type string;
       }
     }
     output {
       choice output_c {
         case output-tag {
           leaf output {
             type string;
           }
         }
         case actual-tag {
           anyxml route-information;
         }
         case multichassis-tag {
           anyxml multi-routing-engine-results;
         }
       }
     }
   }
   rpc get-route-cumulative {
     description "Show the cumulative routes in VRF table";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf vpn-family {
         type enumeration {
           enum "inet.0" {
             description "Display the inet.0 vrf instance";
           }
           enum "inet6.0" {
             description "Display the inet6.0 vrf instance";
           }
         }
         mandatory true;
       }
     }
     output {
       choice output_c {
         case output-tag {
           leaf output {
             type string;
           }
         }
         case actual-tag {
           anyxml route-information;
         }
         case multichassis-tag {
           anyxml multi-routing-engine-results;
         }
       }
     }
   }
   rpc get-route-rib-groups {
     description "Show group of routing tables";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
     }
     output {
       choice output_c {
         case output-tag {
           leaf output {
             type string;
           }
         }
         case actual-tag {
           anyxml route-information;
         }
         case multichassis-tag {
           anyxml multi-routing-engine-results;
         }
       }
     }
   }
   rpc get-route-snooping-information {
     description "Show routes for multicast snooping";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf destination {
         description "IP address and optional prefix length of destination";
         type jt:ipprefix-optional;
       }
       leaf all {
         description "Show all entries, including hidden entries";
         type empty;
       }
       leaf level {
         type enumeration {
           enum "terse" {
             description "Display terse output";
           }
           enum "brief" {
             description "Display brief output";
           }
           enum "detail" {
             description "Display detailed output";
           }
           enum "extensive" {
             description "Display extensive output";
           }
         }
       }
       leaf match {
         type enumeration {
           enum "best" {
             description "Show longest matching route";
           }
           enum "exact" {
             description "Show routes that match exactly";
           }
           enum "range" {
             description "Show all entries in prefix range";
           }
         }
       }
       leaf table {
         description "Name of routing table";
         type string;
       }
     }
     output {
       choice output_c {
         case output-tag {
           leaf output {
             type string;
           }
         }
         case actual-tag {
           anyxml route-information;
         }
         case multichassis-tag {
           anyxml multi-routing-engine-results;
         }
       }
     }
   }
   rpc get-route-snooping-summary {
     description "Show routing table statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml route-summary-information;
         }
         case multichassis-tag {
           anyxml multi-routing-engine-results;
         }
       }
     }
   }
   rpc get-rtexport-table-information {
     description "Show instance export information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf verbosity_level {
         default "brief";
         type enumeration {
           enum "brief" {
             description "Display brief output (default)";
           }
           enum "detail" {
             description "Display detailed output";
           }
         }
       }
       leaf table-name {
         description "Name of table";
         type string;
       }
     }
     output {
       choice output_c {
         case output-tag {
           leaf output {
             type string;
           }
         }
         case actual-tag {
           anyxml rtexport-table-information;
         }
         case multichassis-tag {
           anyxml multi-routing-engine-results;
         }
       }
     }
   }
   rpc get-rtexport-target-information {
     description "Show VPN routing and forwarding route target export information";
     input {
       leaf verbosity_level {
         default "brief";
         type enumeration {
           enum "brief" {
             description "Display brief output (default)";
           }
           enum "detail" {
             description "Display detailed output";
           }
         }
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf-list community {
         ordered-by user;
         description "Community to match (can include wildcards)";
         type string;
       }
     }
     output {
       choice output_c {
         case output-tag {
           leaf output {
             type string;
           }
         }
         case actual-tag {
           anyxml rtexport-target-information;
         }
         case multichassis-tag {
           anyxml multi-routing-engine-results;
         }
       }
     }
   }
   rpc get-rtexport-instance-information {
     description "Show instance configuration and runtime information";
     input {
       leaf verbosity_level {
         default "brief";
         type enumeration {
           enum "brief" {
             description "Display brief output (default)";
           }
           enum "detail" {
             description "Display detailed output";
           }
         }
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf instance-name {
         description "Name of instance";
         type string;
       }
     }
     output {
       choice output_c {
         case output-tag {
           leaf output {
             type string;
           }
         }
         case actual-tag {
           anyxml rtexport-instance-information;
         }
         case multichassis-tag {
           anyxml multi-routing-engine-results;
         }
       }
     }
   }
   rpc get-rtflow-dep-information {
     description "Show flow route validation tables";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         default "brief";
         type enumeration {
           enum "brief" {
             description "Display brief output (default)";
           }
           enum "detail" {
             description "Display detailed output";
           }
         }
       }
       leaf table {
         description "Name of unicast routing table";
         type string;
       }
       leaf destination {
         description "IP address and optional prefix length of destination";
         type jt:ipprefix-optional;
       }
     }
     output {
       choice output_c {
         case output-tag {
           leaf output {
             type string;
           }
         }
         case actual-tag {
           anyxml rtflow-dep-information;
         }
         case multichassis-tag {
           anyxml multi-routing-engine-results;
         }
       }
     }
   }
   rpc get-fib-localization-information {
     description "Show route localization information";
     input {
       uses command-forwarding;
       leaf detail {
         description "Show detailed output";
         type empty;
       }
     }
     output {
       choice output_c {
         case output-tag {
           leaf output {
             type string;
           }
         }
         case actual-tag {
           anyxml fib-localization-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
