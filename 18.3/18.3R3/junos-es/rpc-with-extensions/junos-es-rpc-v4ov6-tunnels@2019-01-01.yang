/*
 * Copyright (c) 2019 Juniper Networks, Inc.
 * All rights reserved.
 */
 module junos-es-rpc-v4ov6-tunnels {
   namespace "http://yang.juniper.net/junos-es/rpc/v4ov6-tunnels";

   prefix v4ov6-tunnels;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for v4ov6-tunnels command(s)";

   revision 2019-01-01 {
     description "Junos: 18.2R3";
   }

   rpc get-v4ov6-information {
     description "Show V4 over V6 tunnel information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
         }
       }
       leaf anti-spoof-ip {
         description "Filter based on Anti-spoof-IP";
         type jt:ipaddr;
       }
       leaf v6-source {
         description "Filter based on v6-source";
         type jt:ipaddr;
       }
       leaf v6-dest {
         description "Filter based on v6-dest";
         type jt:ipaddr;
       }
       leaf tcnh-index {
         description "Filter based on tcnh-index";
         type union {
           type uint32;
           type string {
             pattern "<.*>|$.*";
           }
         }
       }
     }
     output {
       choice output_c {
         case output-tag {
           leaf output {
             type string;
           }
         }
         case actual-tag {
           anyxml v4ov6-dynamic-tunnel;
         }
         case multichassis-tag {
           anyxml multi-routing-engine-results;
         }
       }
     }
   }
   rpc get-v4ov6-information-anchor-pfe {
     description "Filter based on anchor-pfe";
     input {
       leaf pfe-name {
         description "PFE anchored to v4ov6 tunnel";
         type string;
         mandatory true;
       }
       leaf level {
         type enumeration {
           enum "count" {
             description "Display count of v4ov6 tunnels per filter";
           }
         }
       }
     }
     output {
       choice output_c {
         case output-tag {
           leaf output {
             type string;
           }
         }
         case actual-tag {
           anyxml v4ov6-dynamic-tunnel-anchor-pfe;
         }
         case multichassis-tag {
           anyxml multi-routing-engine-results;
         }
       }
     }
   }
   rpc get-v4ov6-information-count {
     description "Count of v4ov6-tunnels";
     output {
       choice output_c {
         case output-tag {
           leaf output {
             type string;
           }
         }
         case actual-tag {
           anyxml v4ov6-information-count;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
