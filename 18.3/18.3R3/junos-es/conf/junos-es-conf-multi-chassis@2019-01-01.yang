/*
 * Copyright (c) 2019 Juniper Networks, Inc.
 * All rights reserved.
 */
 module junos-es-conf-multi-chassis {
   namespace "http://yang.juniper.net/junos-es/conf/multi-chassis";

   prefix jc-multi-chassis;

   import junos-common-types {
     prefix jt;
   }

   import junos-es-conf-root {
     prefix jc;
   }

   organization "Juniper Networks, Inc.";

   contact "yang-support@juniper.net";

   description "Junos multi-chassis configuration module";

   revision 2019-01-01 {
     description "Junos: 18.2R3";
   }

   augment /jc:configuration {
     uses multi-chassis-group;
   }
   augment /jc:configuration/jc:groups {
     uses multi-chassis-group;
   }
   grouping multi-chassis-group {
     container multi-chassis {
       presence "enable multi-chassis";
       description "Multi-chassis configuration";
       uses apply-advanced;
       container mc-lag {
         presence "enable mc-lag";
         description "Multi-chassis Lag configuration";
         uses apply-advanced;
         container consistency-check {
           presence "enable consistency-check";
           description "Consistency Check properties";
           uses apply-advanced;
           leaf comparison-delay-time {
             description "Time after which local and remote config are compared";
             units "seconds";
             type union {
               type string {
                 pattern "<.*>|$.*";
               }
               type uint32 {
                 range "5 .. 600";
               }
             }
           }
           container traceoptions {
             description "Trace options for MCLAG_CFGCHK";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             list flag {
               key name;
               ordered-by user;
               description "Trace flag information";
               leaf name {
                 type enumeration {
                   enum "error" {
                     description "Trace all errors";
                   }
                   enum "event" {
                     description "Trace all events";
                   }
                   enum "packet" {
                     description "Trace all packets";
                   }
                   enum "pipe" {
                     description "Trace pipe messages";
                   }
                   enum "pipe-detail" {
                     description "Trace pipe messages in detail";
                   }
                   enum "all" {
                     description "Trace everything";
                   }
                 }
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
