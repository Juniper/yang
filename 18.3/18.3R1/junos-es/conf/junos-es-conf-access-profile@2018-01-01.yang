/*
 * Copyright (c) 2018 Juniper Networks, Inc.
 * All rights reserved.
 */
 module junos-es-conf-access-profile {
   namespace "http://yang.juniper.net/junos-es/conf/access-profile";

   prefix jc-access-profile;

   import junos-common-types {
     prefix jt;
   }

   import junos-es-conf-root {
     prefix jc;
   }

   organization "Juniper Networks, Inc.";

   contact "yang-support@juniper.net";

   description "Junos access-profile configuration module";

   revision 2018-01-01 {
     description "Junos: 18.3R1.9";
   }

   augment /jc:configuration {
     uses access-profile-group;
   }
   augment /jc:configuration/jc:groups {
     uses access-profile-group;
   }
   grouping access-profile-group {
     container access-profile {
       description "Access profile for this instance";
       leaf access-profile-name {
         description "Profile name";
         type string;
       }
     }
   }
 }
