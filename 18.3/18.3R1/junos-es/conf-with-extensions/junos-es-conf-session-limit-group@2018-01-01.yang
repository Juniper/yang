/*
 * Copyright (c) 2018 Juniper Networks, Inc.
 * All rights reserved.
 */
 module junos-es-conf-session-limit-group {
   namespace "http://yang.juniper.net/junos-es/conf/session-limit-group";

   prefix jc-session-limit-group;

   import junos-common-ddl-extensions {
     prefix junos;
   }

   import junos-common-types {
     prefix jt;
   }

   import junos-es-conf-root {
     prefix jc;
   }

   organization "Juniper Networks, Inc.";

   contact "yang-support@juniper.net";

   description "Junos session-limit-group configuration module";

   revision 2018-01-01 {
     description "Junos: 18.3R1.9";
   }

   augment /jc:configuration {
     uses session-limit-group-group;
   }
   augment /jc:configuration/jc:groups {
     uses session-limit-group-group;
   }
   grouping session-limit-group-group {
     list session-limit-group {
       key name;
       ordered-by user;
       description "Session-limit-group configuration";
       leaf name {
         description "Name of the group";
         type string {
           length "1 .. 63";
           junos:posix-pattern "^[[:alnum:]][[:alnum:]_-]*$";
           junos:pattern-message "Must be a string beginning with a number or letter and consisting of letters, numbers, dashes and underscores.";
         }
       }
       leaf maximum-sessions {
         description "Maximum number of sessions per tunnel-group";
         type union {
           type uint32;
           type string {
             pattern "<.*>|$.*";
           }
         }
       }
     }
   }
 }
