/*
 * Copyright (c) 2018 Juniper Networks, Inc.
 * All rights reserved.
 */
 module junos-qfx-rpc-chassis {
   namespace "http://yang.juniper.net/junos-qfx/rpc/chassis";

   prefix chassis;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for chassis command(s)";

   revision 2018-01-01 {
     description "Junos: 18.3R1.9";
   }

   rpc get-uft-information {
     description "Show member's current UFT configuration";
     output {
       choice output_c {
         case output-tag {
           leaf output {
             type string;
           }
         }
         case actual-tag {
           anyxml uft-information;
         }
         case multichassis-tag {
           anyxml multi-routing-engine-results;
         }
       }
     }
   }
   rpc get-system-mode-information {
     description "Show member's current system-mode configuration";
     output {
       choice output_c {
         case output-tag {
           leaf output {
             type string;
           }
         }
         case actual-tag {
           anyxml system-mode-information;
         }
         case multichassis-tag {
           anyxml multi-routing-engine-results;
         }
       }
     }
   }
   rpc get-power-usage-information {
     description "Show Chassis Power Usages";
     output {
       choice output_c {
         case output-tag {
           leaf output {
             type string;
           }
         }
         case actual-tag {
           anyxml power-usage-information;
         }
         case multichassis-tag {
           anyxml multi-routing-engine-results;
         }
       }
     }
   }
   rpc get-alarm-information {
     description "Show alarm status";
     output {
       choice output_c {
         case output-tag {
           leaf output {
             type string;
           }
         }
         case actual-tag {
           anyxml alarm-information;
         }
         case multichassis-tag {
           anyxml multi-routing-engine-results;
         }
       }
     }
   }
   rpc get-fpc-alarm-information {
     description "Show alarm status for a FPC";
     input {
       leaf fpc-slot {
         description "Flexible PIC Controller slot number";
         type union {
           type string {
             pattern "<.*>|$.*";
           }
           type uint32;
         }
         mandatory true;
       }
     }
     output {
       choice output_c {
         case output-tag {
           leaf output {
             type string;
           }
         }
         case actual-tag {
           anyxml alarm-information;
         }
         case multichassis-tag {
           anyxml multi-routing-engine-results;
         }
       }
     }
   }
   rpc get-chassis-alarm-satellite-information {
     description "Show alarm status for satellite devices";
     input {
       leaf fpc-slot {
         description "Satellite slot number";
         type union {
           type string {
             pattern "<.*>|$.*";
           }
           type uint16 {
             range "65 .. 254";
           }
         }
       }
     }
     output {
       choice output_c {
         case output-tag {
           leaf output {
             type string;
           }
         }
         case actual-tag {
           anyxml chassis-alarm-satellite-information;
         }
         case multichassis-tag {
           anyxml multi-routing-engine-results;
         }
       }
     }
   }
   rpc get-chassis-errors {
     description "Show chassis errors";
     input {
       leaf error-id {
         description "Error identifier for the error to be cleared";
         type string {
           length "1 .. 255";
           junos:posix-pattern "^(/[^/ ]+/[0-9]+){4}/[^/ ]+$";
           junos:pattern-message "Invalid error identifier format";
         }
         mandatory true;
       }
       leaf fpc-slot {
         description "Slot number of FPC";
         type union {
           type string {
             pattern "<.*>|$.*";
           }
           type uint32;
         }
         mandatory true;
       }
     }
     output {
       choice output_c {
         case output-tag {
           leaf output {
             type string;
           }
         }
         case actual-tag {
           anyxml chassis-error-information;
         }
         case multichassis-tag {
           anyxml multi-routing-engine-results;
         }
       }
     }
   }
   rpc get-chassis-active-errors {
     description "Show active errors";
     input {
       leaf fpc-slot {
         description "Slot number of FPC";
         type union {
           type string {
             pattern "<.*>|$.*";
           }
           type uint32;
         }
       }
     }
     output {
       choice output_c {
         case output-tag {
           leaf output {
             type string;
           }
         }
         case actual-tag {
           anyxml chassis-active-error-information;
         }
         case multichassis-tag {
           anyxml multi-routing-engine-results;
         }
       }
     }
   }
   rpc get-active-error-information-detail {
     description "Show detailed output";
     input {
       leaf fpc-slot {
         description "Slot number of FPC";
         type union {
           type string {
             pattern "<.*>|$.*";
           }
           type uint32;
         }
       }
     }
     output {
       choice output_c {
         case output-tag {
           leaf output {
             type string;
           }
         }
         case actual-tag {
           anyxml chassis-errors-detail-information;
         }
         case multichassis-tag {
           anyxml multi-routing-engine-results;
         }
       }
     }
   }
   rpc get-chassis-beacon-information {
     description "Show beacon status";
     input {
       choice which-arg {
         case all {
           leaf all {
             description "Beacons in ON/OFF state";
             type enumeration {
               enum "off" {
                 description "Beacons in OFF state";
               }
               enum "on" {
                 description "Beacons in ON state";
               }
             }
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       choice output_c {
         case output-tag {
           leaf output {
             type string;
           }
         }
         case actual-tag {
           anyxml chassis-beacon-information;
         }
         case multichassis-tag {
           anyxml multi-routing-engine-results;
         }
       }
     }
   }
   rpc network-services {
     description "Show chassis network services";
     output {
       choice output_c {
         case output-tag {
           leaf output {
             type string;
           }
         }
         case actual-tag {
           anyxml network-services;
         }
         case multichassis-tag {
           anyxml multi-routing-engine-results;
         }
       }
     }
   }
   rpc get-craft-information {
     description "Show craft interface status";
     output {
       choice output_c {
         case output-tag {
           leaf output {
             type string;
           }
         }
         case actual-tag {
           anyxml craft-information;
         }
         case multichassis-tag {
           anyxml multi-routing-engine-results;
         }
       }
     }
   }
   rpc get-ethernet-switch-information {
     description "Show Ethernet switch information";
     input {
       uses command-forwarding;
       leaf ethernet-switch-type {
         description "Show Ethernet switch information";
         type enumeration {
           enum "get-ethernet-switch-cb-information" {
             description "Show Ethernet switch Control Board information";
           }
           enum "get-ethernet-switch-fpc-information" {
             description "Show Ethernet switch Front Card information";
           }
         }
         mandatory true;
       }
       leaf detail {
         description "Show Ethernet switch traffic statistics";
         type empty;
       }
       leaf port {
         description "Port number";
         type union {
           type string {
             pattern "<.*>|$.*";
           }
           type uint32 {
             range "1 .. 28";
           }
         }
       }
       leaf slot {
         description "Front card FPC slot number";
         type union {
           type string {
             pattern "<.*>|$.*";
           }
           type uint32 {
             range "0 .. 7";
           }
         }
       }
     }
     output {
       choice output_c {
         case output-tag {
           leaf output {
             type string;
           }
         }
         case actual-tag {
           anyxml ethernet-switch-information;
         }
         case multichassis-tag {
           anyxml multi-routing-engine-results;
         }
       }
     }
   }
   rpc get-chassis-zones-information {
     description "Show chassis cooling zones information";
     input {
       uses command-forwarding;
       leaf detail {
         description "Display detailed output";
         type empty;
       }
     }
     output {
       choice output_c {
         case output-tag {
           leaf output {
             type string;
           }
         }
         case actual-tag {
           anyxml chassis-zones-information;
         }
         case multichassis-tag {
           anyxml multi-routing-engine-results;
         }
       }
     }
   }
   rpc get-environment-information {
     description "Show component status and temperature, cooling system speeds";
     output {
       choice output_c {
         case output-tag {
           leaf output {
             type string;
           }
         }
         case actual-tag {
           anyxml environment-information;
         }
         case multichassis-tag {
           anyxml multi-routing-engine-results;
         }
       }
     }
   }
   rpc get-environment-sib-information {
     description "Show Switch Interface Board information";
     input {
       uses command-forwarding;
       leaf sib-slot {
         description "SIB slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-fan-information {
     description "Show fan status";
     input {
       uses command-forwarding;
       leaf slot {
         description "Fantray slot number";
         type union {
           type string {
             pattern "<.*>|$.*";
           }
           type uint32 {
             range "0 .. 6";
           }
         }
       }
     }
     output {
       choice output_c {
         case output-tag {
           leaf output {
             type string;
           }
         }
         case actual-tag {
           anyxml fan-information;
         }
         case multichassis-tag {
           anyxml multi-routing-engine-results;
         }
       }
     }
   }
   rpc get-environment-fpc-information {
     description "Show Flexible PIC Concentrator information";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-fpc-satellite-info {
     description "Show environment FPC details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-fpc-satellite-information;
         }
         case multichassis-tag {
           anyxml multi-routing-engine-results;
         }
       }
     }
   }
   rpc get-environment-cb-information {
     description "Show Control Board information";
     input {
       uses command-forwarding;
       leaf slot {
         description "CB slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-pem-information {
     description "Show Power Entry Module information";
     input {
       uses command-forwarding;
       leaf slot {
         description "PEM slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-pem-satellite-info {
     description "Show environment PEM details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-pem-satellite-information;
         }
         case multichassis-tag {
           anyxml multi-routing-engine-results;
         }
       }
     }
   }
   rpc get-environment-psm-information {
     description "Show Power Supply Module information";
     input {
       uses command-forwarding;
       leaf slot {
         description "PSM slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-re-information {
     description "Show Routing Engine information";
     input {
       uses command-forwarding;
       leaf slot {
         description "Routing Engine slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-re-satellite-info {
     description "Show environment routing engine details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-routing-engine-satellite-information;
         }
         case multichassis-tag {
           anyxml multi-routing-engine-results;
         }
       }
     }
   }
   rpc get-environment-service-node-information {
     description "Show Compute Node Environment information";
     input {
       leaf slot {
         description "Service node slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-satellite-information {
     description "Show environment details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-satellite-information;
         }
         case multichassis-tag {
           anyxml multi-routing-engine-results;
         }
       }
     }
   }
   rpc get-firmware-information {
     description "Show firmware and operating system version for components";
     input {
       uses command-forwarding;
       leaf fpc {
         description "Flexible PIC Controller slot number";
         type union {
           type string {
             pattern "<.*>|$.*";
           }
           type uint32;
         }
       }
     }
     output {
       choice output_c {
         case output-tag {
           leaf output {
             type string;
           }
         }
         case actual-tag {
           anyxml firmware-information;
         }
         case multichassis-tag {
           anyxml multi-routing-engine-results;
         }
       }
     }
   }
   rpc get-firmware-information-detail {
     description "Show detailed output";
     output {
       choice output_c {
         case output-tag {
           leaf output {
             type string;
           }
         }
         case actual-tag {
           anyxml hardware-version-information;
         }
         case multichassis-tag {
           anyxml multi-routing-engine-results;
         }
       }
     }
   }
   rpc get-chassis-firmware-satellite-information {
     description "Show FPC firmware details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-firmware-satellite-information;
         }
         case multichassis-tag {
           anyxml multi-routing-engine-results;
         }
       }
     }
   }
   rpc get-fpc-information {
     description "Show Flexible PIC Concentrator status";
     input {
       uses command-forwarding;
       leaf detail {
         description "Display detailed output";
         type empty;
       }
       leaf fpc-slot {
         description "FPC slot number";
         type union {
           type string {
             pattern "<.*>|$.*";
           }
           type uint32;
         }
       }
     }
     output {
       choice output_c {
         case output-tag {
           leaf output {
             type string;
           }
         }
         case actual-tag {
           anyxml fpc-information;
         }
         case multichassis-tag {
           anyxml multi-routing-engine-results;
         }
       }
     }
   }
   rpc get-pic-information {
     description "Show Physical Interface Cards installed in FPC";
     input {
       uses command-forwarding;
       leaf slot {
         description "FPC slot number";
         type union {
           type string {
             pattern "<.*>|$.*";
           }
           type uint32;
         }
       }
     }
     output {
       choice output_c {
         case output-tag {
           leaf output {
             type string;
           }
         }
         case actual-tag {
           anyxml fpc-information;
         }
         case multichassis-tag {
           anyxml multi-routing-engine-results;
         }
       }
     }
   }
   rpc get-fpc-port-information {
     description "Show Port status installed in FPC";
     input {
       leaf slot {
         description "FPC slot number";
         type union {
           type string {
             pattern "<.*>|$.*";
           }
           type uint32;
         }
       }
     }
     output {
       choice output_c {
         case output-tag {
           leaf output {
             type string;
           }
         }
         case actual-tag {
           anyxml fpc-port-information;
         }
         case multichassis-tag {
           anyxml multi-routing-engine-results;
         }
       }
     }
   }
   rpc get-fpc-error-information {
     description "Show ASIC errors on all the FPC's";
     input {
       uses command-forwarding;
       leaf fpc-slot {
         description "FPC slot number";
         type union {
           type string {
             pattern "<.*>|$.*";
           }
           type uint32;
         }
       }
       leaf detail {
         description "Display detailed output";
         type empty;
       }
       leaf scope {
         description "Error scope";
         type enumeration {
           enum "board" {
             description "Show board errors";
           }
           enum "pfe" {
             description "Show pfe errors";
           }
         }
       }
       leaf category {
         description "Error category";
         type enumeration {
           enum "functional" {
             description "Functional category errors";
           }
           enum "memory" {
             description "Memory category errors";
           }
           enum "io" {
             description "Io category errors";
           }
           enum "storage" {
             description "Storage category errors";
           }
           enum "switch" {
             description "Switch category errors";
           }
           enum "processing" {
             description "Processing category errors";
           }
         }
       }
     }
     output {
       choice output_c {
         case output-tag {
           leaf output {
             type string;
           }
         }
         case actual-tag {
           anyxml fpc-error-information;
         }
         case multichassis-tag {
           anyxml multi-routing-engine-results;
         }
       }
     }
   }
   rpc get-fpc-error-i2c {
     description "Display I2C error statistics";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml fpc-tvp-error-information;
         }
         case multichassis-tag {
           anyxml multi-routing-engine-results;
         }
       }
     }
   }
   rpc get-pic-detail {
     description "Show Physical Interface Card state, type, and uptime";
     input {
       uses command-forwarding;
       leaf fpc-slot {
         description "Slot number of FPC that houses PIC";
         type union {
           type string {
             pattern "<.*>|$.*";
           }
           type uint32;
         }
       }
       leaf pic-slot {
         description "PIC slot number";
         type union {
           type string {
             pattern "<.*>|$.*";
           }
           type int32;
         }
         mandatory true;
       }
     }
     output {
       choice output_c {
         case output-tag {
           leaf output {
             type string;
           }
         }
         case actual-tag {
           anyxml fpc-information;
         }
         case multichassis-tag {
           anyxml multi-routing-engine-results;
         }
       }
     }
   }
   rpc get-pic-transport-information {
     description "Show Physical Interface Card transport information";
     input {
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type int32;
         }
         mandatory true;
       }
     }
     output {
       choice output_c {
         case output-tag {
           leaf output {
             type string;
           }
         }
         case actual-tag {
           anyxml pic-transport-information;
         }
         case multichassis-tag {
           anyxml multi-routing-engine-results;
         }
       }
     }
   }
   rpc get-sib-information {
     description "Show Switch Interface Board status";
     input {
       uses command-forwarding;
       leaf detail {
         description "Display detailed output";
         type empty;
       }
       leaf slot {
         description "SIB slot number";
         type union {
           type string {
             pattern "<.*>|$.*";
           }
           type uint32;
         }
       }
     }
     output {
       choice output_c {
         case output-tag {
           leaf output {
             type string;
           }
         }
         case actual-tag {
           anyxml sib-information;
         }
         case multichassis-tag {
           anyxml multi-routing-engine-results;
         }
       }
     }
   }
   rpc get-sibs-errors {
     description "Show ASIC errors on sib";
     input {
       leaf sib-slot {
         description "SIB slot number";
         type union {
           type string {
             pattern "<.*>|$.*";
           }
           type uint32;
         }
       }
     }
     output {
       choice output_c {
         case output-tag {
           leaf output {
             type string;
           }
         }
         case actual-tag {
           anyxml sib-information;
         }
         case multichassis-tag {
           anyxml multi-routing-engine-results;
         }
       }
     }
   }
   rpc get-fm-fpc-state-information {
     description "Show summary fabric management FPC state from Routing Engine";
     input {
       uses command-forwarding;
       leaf slot {
         description "FPC slot number";
         type union {
           type string {
             pattern "<.*>|$.*";
           }
           type uint32;
         }
       }
     }
     output {
       choice output_c {
         case output-tag {
           leaf output {
             type string;
           }
         }
         case actual-tag {
           anyxml fm-fpc-state-information;
         }
         case multichassis-tag {
           anyxml multi-routing-engine-results;
         }
       }
     }
   }
   rpc get-fm-plane-location-information {
     description "Show fabric plane location";
     output {
       choice output_c {
         case output-tag {
           leaf output {
             type string;
           }
         }
         case actual-tag {
           anyxml fm-plane-location-information;
         }
         case multichassis-tag {
           anyxml multi-routing-engine-results;
         }
       }
     }
   }
   rpc get-fm-topology {
     description "Show fabric topology for plane";
     input {
       uses command-forwarding;
       leaf plane {
         description "Fabric plane number";
         type union {
           type string {
             pattern "<.*>|$.*";
           }
           type uint32;
         }
       }
     }
     output {
       choice output_c {
         case output-tag {
           leaf output {
             type string;
           }
         }
         case actual-tag {
           anyxml fm-topology;
         }
         case multichassis-tag {
           anyxml multi-routing-engine-results;
         }
       }
     }
   }
   rpc get-fm-plane-state-information {
     description "Show state of fabric management plane";
     input {
       uses command-forwarding;
       leaf display {
         type enumeration {
           enum "terse" {
             description "Show terse output";
           }
           enum "detail" {
             description "Show detail output";
           }
           enum "extensive" {
             description "Show extensive output";
           }
         }
       }
       leaf number {
         description "Fabric plane number";
         type union {
           type string {
             pattern "<.*>|$.*";
           }
           type uint32 {
             range "0 .. 4";
           }
         }
       }
     }
     output {
       choice output_c {
         case output-tag {
           leaf output {
             type string;
           }
         }
         case actual-tag {
           anyxml fm-plane-state-information;
         }
         case multichassis-tag {
           anyxml multi-routing-engine-results;
         }
       }
     }
   }
   rpc get-fm-state-information {
     description "Show summary fabric management state";
     output {
       choice output_c {
         case output-tag {
           leaf output {
             type string;
           }
         }
         case actual-tag {
           anyxml fm-state-information;
         }
         case multichassis-tag {
           anyxml multi-routing-engine-results;
         }
       }
     }
   }
   rpc get-fm-sib-state-information {
     description "Show summary fabric management SIB state from Routing Engine";
     input {
       uses command-forwarding;
       leaf slot {
         description "SIB slot number";
         type union {
           type string {
             pattern "<.*>|$.*";
           }
           type uint32;
         }
       }
     }
     output {
       choice output_c {
         case output-tag {
           leaf output {
             type string;
           }
         }
         case actual-tag {
           anyxml fm-sib-state-information;
         }
         case multichassis-tag {
           anyxml multi-routing-engine-results;
         }
       }
     }
   }
   rpc get-chassis-fabric-topology-information {
     description "Show fabric topology information";
     input {
       uses command-forwarding;
       leaf device {
         description "Device alias name or serial number";
         type string;
       }
       leaf slot {
         description "Slot number";
         type union {
           type string {
             pattern "<.*>|$.*";
           }
           type uint32 {
             range "0 .. 15";
           }
         }
       }
     }
     output {
       choice output_c {
         case output-tag {
           leaf output {
             type string;
           }
         }
         case actual-tag {
           anyxml chassis-fabric-information;
         }
         case multichassis-tag {
           anyxml multi-routing-engine-results;
         }
       }
     }
   }
   rpc get-chassis-fabric-spray-weight-information {
     description "Show fabric spray-weights";
     output {
       choice output_c {
         case output-tag {
           leaf output {
             type string;
           }
         }
         case actual-tag {
           anyxml chassis-fabric-spray-weight-information;
         }
         case multichassis-tag {
           anyxml multi-routing-engine-results;
         }
       }
     }
   }
   rpc get-chassis-fabric-link-information {
     description "Show data-center fabric links";
     input {
       leaf link-type {
         description "Link type";
         default "all";
         type enumeration {
           enum "up" {
             description "Up links";
           }
           enum "down" {
             description "Down links";
           }
           enum "error" {
             description "Error links";
           }
           enum "all" {
             description "All links";
           }
         }
       }
       leaf device {
         description "Device alias name or serial number";
         type string;
       }
       leaf slot {
         description "Slot number";
         type union {
           type string {
             pattern "<.*>|$.*";
           }
           type uint32 {
             range "0 .. 15";
           }
         }
       }
     }
     output {
       choice output_c {
         case output-tag {
           leaf output {
             type string;
           }
         }
         case actual-tag {
           anyxml chassis-fabric-information;
         }
         case multichassis-tag {
           anyxml multi-routing-engine-results;
         }
       }
     }
   }
   rpc get-chassis-fabric-information-device {
     description "Show chassis fabric devices running FM component";
     input {
       leaf device-id {
         description "Device alias name or serial number";
         type string;
       }
     }
     output {
       choice output_c {
         case output-tag {
           leaf output {
             type string;
           }
         }
         case actual-tag {
           anyxml chassis-fabric-information-device;
         }
         case multichassis-tag {
           anyxml multi-routing-engine-results;
         }
       }
     }
   }
   rpc get-chassis-fabric-connectivity-information {
     description "Show data-center fabric connectivity";
     input {
       leaf device {
         description "Device alias name or serial number";
         type string;
       }
       leaf slot {
         description "Slot number";
         type union {
           type string {
             pattern "<.*>|$.*";
           }
           type uint32 {
             range "0 .. 15";
           }
         }
       }
       leaf inter-chassis {
         description "Inter chassis fabric link connectivity details";
         type empty;
       }
       leaf intra-chassis {
         description "Intra chassis fabric link connectivity details";
         type empty;
       }
     }
     output {
       choice output_c {
         case output-tag {
           leaf output {
             type string;
           }
         }
         case actual-tag {
           anyxml chassis-fabric-connectivity-information;
         }
         case multichassis-tag {
           anyxml multi-routing-engine-results;
         }
       }
     }
   }
   rpc get-fm-fabric-reachability-information {
     description "Show current status of fabric reachability";
     input {
       uses command-forwarding;
       leaf detail {
         description "Show reachability output in detail";
         type empty;
       }
     }
     output {
       choice output_c {
         case output-tag {
           leaf output {
             type string;
           }
         }
         case actual-tag {
           anyxml fm-fabric-reachability-information;
         }
         case multichassis-tag {
           anyxml multi-routing-engine-results;
         }
       }
     }
   }
   rpc get-fm-degraded-fabric-state-information {
     description "Show degraded fabric state on all active planes";
     output {
       choice output_c {
         case output-tag {
           leaf output {
             type string;
           }
         }
         case actual-tag {
           anyxml fm-degraded-fabric-state-information;
         }
         case multichassis-tag {
           anyxml multi-routing-engine-results;
         }
       }
     }
   }
   rpc get-fm-sib-errors {
     description "Show Switch Interface Board errors";
     input {
       uses command-forwarding;
       leaf sib-slot {
         description "SIB slot number";
         type union {
           type string {
             pattern "<.*>|$.*";
           }
           type uint32;
         }
         mandatory true;
       }
     }
     output {
       choice output_c {
         case output-tag {
           leaf output {
             type string;
           }
         }
         case actual-tag {
           anyxml fm-fru-errors;
         }
         case multichassis-tag {
           anyxml multi-routing-engine-results;
         }
       }
     }
   }
   rpc get-fm-fpc-errors {
     description "Show Flexible PIC Controller errors";
     input {
       uses command-forwarding;
       leaf slot {
         description "FPC slot number";
         type union {
           type string {
             pattern "<.*>|$.*";
           }
           type uint32;
         }
         mandatory true;
       }
     }
     output {
       choice output_c {
         case output-tag {
           leaf output {
             type string;
           }
         }
         case actual-tag {
           anyxml fm-fru-errors;
         }
         case multichassis-tag {
           anyxml multi-routing-engine-results;
         }
       }
     }
   }
   rpc get-chassis-inventory {
     description "Show installed hardware components";
     input {
       uses command-forwarding;
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
       leaf fpc {
         description "Flexible PIC Controller slot number";
         type union {
           type string {
             pattern "<.*>|$.*";
           }
           type uint32;
         }
       }
     }
     output {
       choice output_c {
         case output-tag {
           leaf output {
             type string;
           }
         }
         case actual-tag {
           anyxml chassis-inventory;
         }
         case multichassis-tag {
           anyxml multi-routing-engine-results;
         }
       }
     }
   }
   rpc get-chassis-hardware-satellite-information {
     description "Show hardware details";
     input {
       leaf fpc-slot {
         description "Satellite slot number";
         type union {
           type string {
             pattern "<.*>|$.*";
           }
           type uint16 {
             range "65 .. 254";
           }
         }
       }
       leaf device-alias {
         description "Device alias";
         type string;
       }
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       choice output_c {
         case output-tag {
           leaf output {
             type string;
           }
         }
         case actual-tag {
           anyxml chassis-hardware-satellite-information;
         }
         case multichassis-tag {
           anyxml multi-routing-engine-results;
         }
       }
     }
   }
   rpc get-power-budget-information {
     description "Show power budget chassis information";
     output {
       choice output_c {
         case output-tag {
           leaf output {
             type string;
           }
         }
         case actual-tag {
           anyxml power-budget-information;
         }
         case multichassis-tag {
           anyxml multi-routing-engine-results;
         }
       }
     }
   }
   rpc get-chassis-mac-addresses {
     description "Show media access control addresses";
     output {
       choice output_c {
         case output-tag {
           leaf output {
             type string;
           }
         }
         case actual-tag {
           anyxml chassis-mac-addresses;
         }
         case multichassis-tag {
           anyxml multi-routing-engine-results;
         }
       }
     }
   }
   rpc get-route-engine-information {
     description "Show Routing Engine status";
     input {
       uses command-forwarding;
       leaf slot {
         description "Routing Engine slot number";
         type union {
           type string {
             pattern "<.*>|$.*";
           }
           type uint32;
         }
       }
     }
     output {
       choice output_c {
         case output-tag {
           leaf output {
             type string;
           }
         }
         case actual-tag {
           anyxml route-engine-information;
         }
         case multichassis-tag {
           anyxml multi-routing-engine-results;
         }
       }
     }
   }
   rpc get-bios-version-information {
     description "Show BIOS firmware version";
     output {
       choice output_c {
         case output-tag {
           leaf output {
             type string;
           }
         }
         case multichassis-tag {
           anyxml multi-routing-engine-results;
         }
       }
     }
   }
   rpc get-chassis-routing-engine-bios-satellite-info {
     description "Show routing engine bios details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-routing-engine-bios-satellite-information;
         }
         case multichassis-tag {
           anyxml multi-routing-engine-results;
         }
       }
     }
   }
   rpc get-chassis-routing-engine-errors {
     description "Show RE errors";
     output {
       choice output_c {
         case output-tag {
           leaf output {
             type string;
           }
         }
         case actual-tag {
           anyxml errors;
         }
         case multichassis-tag {
           anyxml multi-routing-engine-results;
         }
       }
     }
   }
   rpc get-chassis-routing-engine-satellite-information {
     description "Show routing engine details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-routing-engine-satellite-information;
         }
         case multichassis-tag {
           anyxml multi-routing-engine-results;
         }
       }
     }
   }
   rpc get-service-node-information {
     description "Show service node information";
     input {
       leaf slot {
         description "Service node slot number";
         type union {
           type string {
             pattern "<.*>|$.*";
           }
           type uint32 {
             range "0 .. 1";
           }
         }
       }
     }
     output {
       choice output_c {
         case output-tag {
           leaf output {
             type string;
           }
         }
         case actual-tag {
           anyxml service-node-information;
         }
         case multichassis-tag {
           anyxml multi-routing-engine-results;
         }
       }
     }
   }
   rpc get-tfeb-information {
     description "Show Compact Forwarding Engine Board status";
     output {
       choice output_c {
         case output-tag {
           leaf output {
             type string;
           }
         }
         case actual-tag {
           anyxml scb-information;
         }
         case multichassis-tag {
           anyxml multi-routing-engine-results;
         }
       }
     }
   }
   rpc get-chassis-fan-satellite-information {
     description "Show fan details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-fan-satellite-information;
         }
         case multichassis-tag {
           anyxml multi-routing-engine-results;
         }
       }
     }
   }
   rpc get-chassis-location {
     description "Show physical location of chassis";
     output {
       choice output_c {
         case output-tag {
           leaf output {
             type string;
           }
         }
         case actual-tag {
           anyxml chassis-location;
         }
         case multichassis-tag {
           anyxml multi-routing-engine-results;
         }
       }
     }
   }
   rpc get-temperature-threshold-information {
     description "Show chassis temperature threshold settings";
     input {
       uses command-forwarding;
       leaf fpc {
         description "Flexible PIC Controller slot number";
         type union {
           type string {
             pattern "<.*>|$.*";
           }
           type uint32;
         }
       }
     }
     output {
       choice output_c {
         case output-tag {
           leaf output {
             type string;
           }
         }
         case actual-tag {
           anyxml temperature-threshold-information;
         }
         case multichassis-tag {
           anyxml multi-routing-engine-results;
         }
       }
     }
   }
   rpc get-chassis-temp-thresholds-satellite-info {
     description "Show temperature thresholds details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-temperature-thresholds-satellite-information;
         }
         case multichassis-tag {
           anyxml multi-routing-engine-results;
         }
       }
     }
   }
   rpc get-power-management {
     description "Show power ratings for the router";
     output {
       choice output_c {
         case output-tag {
           leaf output {
             type string;
           }
         }
         case actual-tag {
           anyxml power-management-information;
         }
         case multichassis-tag {
           anyxml multi-routing-engine-results;
         }
       }
     }
   }
   rpc get-in-service-upgrade-status {
     description "Show In Service upgrade status";
     output {
       choice output_c {
         case output-tag {
           leaf output {
             type string;
           }
         }
         case actual-tag {
           anyxml in-service-upgrade-status;
         }
         case multichassis-tag {
           anyxml multi-routing-engine-results;
         }
       }
     }
   }
   rpc get-nonstop-upgrade-status {
     description "Show nonstop upgrade status";
     output {
       choice output_c {
         case output-tag {
           leaf output {
             type string;
           }
         }
         case actual-tag {
           anyxml in-service-upgrade-status;
         }
         case multichassis-tag {
           anyxml multi-routing-engine-results;
         }
       }
     }
   }
   rpc get-chassis-oss-map {
     description "Show Operation Supported System's translated model";
     output {
       choice output_c {
         case output-tag {
           leaf output {
             type string;
           }
         }
         case actual-tag {
           anyxml chassis-oss-map;
         }
         case multichassis-tag {
           anyxml multi-routing-engine-results;
         }
       }
     }
   }
   rpc security-uefi-variables {
     description "Show platform UEFI variables";
     output {
       choice output_c {
         case output-tag {
           leaf output {
             type string;
           }
         }
         case actual-tag {
           anyxml uefi-vars;
         }
         case multichassis-tag {
           anyxml multi-routing-engine-results;
         }
       }
     }
   }
   rpc get-lcd-information {
     description "Show LCD display";
     output {
       choice output_c {
         case output-tag {
           leaf output {
             type string;
           }
         }
         case actual-tag {
           anyxml craft-lcd-led-information;
         }
         case multichassis-tag {
           anyxml multi-routing-engine-results;
         }
       }
     }
   }
   rpc get-lcd-fpc-information {
     description "Show LCD display for FPC slot number";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml craft-lcd-led-information;
         }
         case multichassis-tag {
           anyxml multi-routing-engine-results;
         }
       }
     }
   }
   rpc get-lcd-menu-information {
     description "Show active LCD menu items";
     output {
       choice output_c {
         case output-tag {
           leaf output {
             type string;
           }
         }
         case actual-tag {
           anyxml lcd-information;
         }
         case multichassis-tag {
           anyxml multi-routing-engine-results;
         }
       }
     }
   }
   rpc get-led-information {
     description "Show LED status";
     output {
       choice output_c {
         case output-tag {
           leaf output {
             type string;
           }
         }
         case actual-tag {
           anyxml craft-lcd-led-information;
         }
         case multichassis-tag {
           anyxml multi-routing-engine-results;
         }
       }
     }
   }
   rpc get-led-fpc-information {
     description "Show LED status for FPC slot number";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml craft-lcd-led-information;
         }
         case multichassis-tag {
           anyxml multi-routing-engine-results;
         }
       }
     }
   }
   rpc get-chassis-led-satellite-information {
     description "Show led details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-led-satellite-information;
         }
         case multichassis-tag {
           anyxml multi-routing-engine-results;
         }
       }
     }
   }
   rpc get-chassis-satellite-information {
     description "Show Satellite Devices information";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
       leaf since {
         description "Show history since YYYY-MM-DD.HH:MM:SS";
         type jt:time;
       }
       leaf level {
         default "brief";
         type enumeration {
           enum "terse" {
             description "Display terse output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml satellite-information;
         }
         case multichassis-tag {
           anyxml multi-routing-engine-results;
         }
       }
     }
   }
   rpc get-chassis-satellite-unprovision-information {
     description "Display unprovisioned satellites";
     input {
       leaf system-id {
         description "Satellite system id";
         type jt:mac-addr;
       }
       leaf since {
         description "Show history since YYYY-MM-DD.HH:MM:SS";
         type jt:time;
       }
       leaf level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml satellite-information;
         }
         case multichassis-tag {
           anyxml multi-routing-engine-results;
         }
       }
     }
   }
   rpc get-chassis-satellite-statistics {
     description "Display device statistics information";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
     }
     output {
       choice output_c {
         case output-tag {
           leaf output {
             type string;
           }
         }
         case actual-tag {
           anyxml device-statistics;
         }
         case multichassis-tag {
           anyxml multi-routing-engine-results;
         }
       }
     }
   }
   rpc get-chassis-satellite-redundancy-group-info {
     description "Display multi-chassis cluster information";
     input {
       leaf since {
         description "Show history since YYYY-MM-DD.HH:MM:SS";
         type jt:time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-information;
         }
         case multichassis-tag {
           anyxml multi-routing-engine-results;
         }
       }
     }
   }
   rpc get-chassis-satellite-redundacy-grp-devices-info {
     description "Display satellite device information";
     input {
       leaf fpc-slot {
         description "Satellite slot number";
         type union {
           type string {
             pattern "<.*>|$.*";
           }
           type uint32 {
             range "65 .. 254";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-device-information;
         }
         case multichassis-tag {
           anyxml multi-routing-engine-results;
         }
       }
     }
   }
   rpc get-chassis-satellite-redundancy-grp-dev-history {
     description "Display device history information";
     input {
       leaf verbosity_level {
         default "brief";
         type enumeration {
           enum "brief" {
             description "Display brief output (default)";
           }
           enum "detail" {
             description "Display detailed output";
           }
           enum "extensive" {
             description "Display extensive output";
           }
         }
       }
       leaf serial-number {
         description "Device Serial Number";
         type string;
       }
       leaf global {
         description "Global history";
         type empty;
       }
     }
     output {
       choice output_c {
         case output-tag {
           leaf output {
             type string;
           }
         }
         case actual-tag {
           anyxml multi-chassis-cluster-device-history-information;
         }
         case multichassis-tag {
           anyxml multi-routing-engine-results;
         }
       }
     }
   }
   rpc get-chassis-satellite-redundacy-grp-if-info {
     description "Display satellite interface information";
     input {
       leaf interface-name {
         description "Name of interface";
         type union {
           type jt:interface-name;
           type string {
             pattern "<.*>|$.*";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-interface-information;
         }
         case multichassis-tag {
           anyxml multi-routing-engine-results;
         }
       }
     }
   }
   rpc get-chassis-satellite-extended-port-information {
     description "Display extended-port information";
     input {
       leaf interface-name {
         description "Interface name";
         type string;
       }
       leaf since {
         description "Show history since YYYY-MM-DD.HH:MM:SS";
         type jt:time;
       }
       leaf fpc-slot {
         description "Satellite slot number";
         type union {
           type string {
             pattern "<.*>|$.*";
           }
           type uint32 {
             range "65 .. 254";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml extended-port-information;
         }
         case multichassis-tag {
           anyxml multi-routing-engine-results;
         }
       }
     }
   }
   rpc get-chassis-satellite-upgrade-group-information {
     description "Display upgrade group information";
     input {
       leaf level {
         default "terse";
         type enumeration {
           enum "terse" {
             description "Display terse output (default)";
           }
           enum "brief" {
             description "Display brief output";
           }
           enum "detail" {
             description "Display detailed output";
           }
           enum "extensive" {
             description "Display extensive output";
           }
         }
       }
       leaf group-name {
         description "Upgrade group name";
         type string;
       }
     }
     output {
       choice output_c {
         case output-tag {
           leaf output {
             type string;
           }
         }
         case actual-tag {
           anyxml upgrade-group-information;
         }
         case multichassis-tag {
           anyxml multi-routing-engine-results;
         }
       }
     }
   }
   rpc get-chassis-satellite-neighbor-information {
     description "Display satellite adjacency information";
     input {
       leaf interface-name {
         description "Name of interface";
         type string;
       }
       leaf since {
         description "Show history since YYYY-MM-DD.HH:MM:SS";
         type jt:time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml adjacency-information;
         }
         case multichassis-tag {
           anyxml multi-routing-engine-results;
         }
       }
     }
   }
   rpc get-chassis-satellite-neighbor-statistics {
     description "Display adjacency statistics information";
     input {
       leaf interface-name {
         description "Name of interface";
         type string;
       }
     }
     output {
       choice output_c {
         case output-tag {
           leaf output {
             type string;
           }
         }
         case actual-tag {
           anyxml adjacency-statistics;
         }
         case multichassis-tag {
           anyxml multi-routing-engine-results;
         }
       }
     }
   }
   rpc get-chassis-satellite-interface-information {
     description "Display satellite protocol interface information";
     input {
       leaf verbosity_level {
         default "brief";
         type enumeration {
           enum "brief" {
             description "Display brief output (default)";
           }
           enum "detail" {
             description "Display detailed output";
           }
           enum "extensive" {
             description "Display extensive output";
           }
         }
       }
       leaf interface-name {
         description "Name of interface";
         type string;
       }
       leaf since {
         description "Show history since YYYY-MM-DD.HH:MM:SS";
         type jt:time;
       }
     }
     output {
       choice output_c {
         case output-tag {
           leaf output {
             type string;
           }
         }
         case actual-tag {
           anyxml satellite-interface-information;
         }
         case multichassis-tag {
           anyxml multi-routing-engine-results;
         }
       }
     }
   }
   rpc get-satellite-management-software-information {
     description "Show satellite software installed";
     input {
       leaf level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml satellite-software-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
