/*
 * Copyright (c) 2018 Juniper Networks, Inc.
 * All rights reserved.
 */
 module junos-nfx-rpc-l2circuit {
   namespace "http://yang.juniper.net/junos-nfx/rpc/l2circuit";

   prefix l2circuit;

   import junos-common-types {
     prefix jt;
   }

   organization "Juniper Networks, Inc.";

   contact "yang-support@juniper.net";

   description "Junos RPC YANG module for l2circuit command(s)";

   revision 2018-01-01 {
     description "Junos: 18.3R1.9";
   }

   rpc get-l2ckt-connection-information {
     description "Show the Layer 2 circuit connections";
     input {
       leaf logical-system {
         description "Name of logical system, or 'all'";
         type string {
         }
       }
       leaf neighbor {
         description "IP address of neighbor";
         default "all";
         type string;
       }
       leaf interface {
         description "Name of interface";
         default "all";
         type string;
       }
       leaf state {
         default "up-down";
         type enumeration {
           enum "down" {
             description "Display nonoperational connections";
           }
           enum "up" {
             description "Display operational connections";
           }
           enum "up-down" {
             description "Display both operational and nonoperational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and interface status (default)";
           }
           enum "summary" {
             description "Display summary output";
           }
         }
       }
     }
     output {
       choice output_c {
         case output-tag {
           leaf output {
             type string;
           }
         }
         case actual-tag {
           anyxml l2circuit-connection-information;
         }
         case multichassis-tag {
           anyxml multi-routing-engine-results;
         }
       }
     }
   }
   rpc get-l2ckt-pw-auto-sensing-information {
     description "Show the Layer 2 circuit PW auto-sensing information";
     input {
       leaf logical-system {
         description "Name of logical system, or 'all'";
         type string {
         }
       }
       leaf neighbor {
         description "IP address of neighbor";
         default "all";
         type string;
       }
       leaf vc-id {
         description "VC ID";
         default "all";
         type string;
       }
     }
     output {
       choice output_c {
         case output-tag {
           leaf output {
             type string;
           }
         }
         case actual-tag {
           anyxml l2circuit-pw-auto-sensing-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
