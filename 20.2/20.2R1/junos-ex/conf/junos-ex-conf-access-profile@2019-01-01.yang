/*
 * Copyright (c) 2020 Juniper Networks, Inc.
 * All rights reserved.
 */
 module junos-ex-conf-access-profile {
   namespace "http://yang.juniper.net/junos-ex/conf/access-profile";

   prefix jc-access-profile;

   import junos-common-types {
     prefix jt;
     revision-date 2019-01-01;
   }

   import junos-ex-conf-root {
     prefix jc;
     revision-date 2019-01-01;
   }

   organization "Juniper Networks, Inc.";

   contact "yang-support@juniper.net";

   description "Junos access-profile configuration module";

   revision 2019-01-01 {
     description "Junos: 20.2R1.9";
   }

   augment /jc:configuration {
     uses access-profile-group;
   }
   augment /jc:configuration/jc:groups {
     uses access-profile-group;
   }
   grouping access-profile-group {
     container access-profile {
       description "Access profile for this instance";
       leaf access-profile-name {
         description "Profile name";
         type string;
       }
     }
   }
 }
