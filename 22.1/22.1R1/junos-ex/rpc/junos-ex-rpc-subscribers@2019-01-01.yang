/*
 * Copyright (c) 2022 Juniper Networks, Inc.
 * All rights reserved.
 */
 module junos-ex-rpc-subscribers {
   namespace "http://yang.juniper.net/junos-ex/rpc/subscribers";

   prefix subscribers;

   import junos-common-types {
     prefix jt;
     revision-date 2019-01-01;
   }

   organization "Juniper Networks, Inc.";

   contact "yang-support@juniper.net";

   description "Junos RPC YANG module for subscribers command(s)";

   revision 2019-01-01 {
     description "Junos: 22.1R1.10";
   }

   rpc get-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "User name of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf agent-remote-identifier {
         description "Display summary for specified agent remote identifier";
         type string;
       }
       leaf aci-interface-set-name {
         description "Display summary for specified ACI interface set";
         type string;
       }
       leaf aggregation-interface-set-name {
         description "Display summary for specified aggregation interface set";
         type string;
       }
       leaf stacked-vlan-id {
         description "Stacked VLAN identifier of subscriber";
         type union {
           type string {
             pattern "<.*>|$.*";
           }
           type uint16 {
             range "1 .. 4094";
           }
         }
       }
       leaf vlan-id {
         description "VLAN identifier of subscriber";
         type union {
           type string {
             pattern "<.*>|$.*";
           }
           type uint16 {
             range "1 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type union {
           type uint64;
           type string {
             pattern "<.*>|$.*";
           }
         }
       }
       leaf accounting-statistics {
         description "Display accounting statistics for subscriber";
         type empty;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "l2ckt-pw" {
             description "L2CKT-PW clients only";
           }
           enum "gre" {
             description "GRE clients only";
           }
           enum "vlan-oob" {
             description "VLAN out-of-band clients only";
           }
           enum "dyn-ip" {
             description "Dynamic IP clients only";
           }
           enum "hag-tunnel" {
             description "HAG tunnel clients only";
           }
           enum "hag-bundle" {
             description "HAG bundle clients only";
           }
           enum "fixed-wireless-access" {
             description "Fixed Wireless Access clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output_c {
         case output-tag {
           leaf output {
             type string;
           }
         }
         case actual-tag {
           anyxml subscribers-information;
         }
         case multichassis-tag {
           anyxml multi-routing-engine-results;
         }
       }
     }
   }
   rpc get-subscribers-summary {
     description "Display subscriber summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf pic {
         description "Display full subscriber pic summary";
         type empty;
       }
       leaf slot {
         description "Display full subscriber slot summary";
         type empty;
       }
       leaf all {
         description "Display full subscriber summary";
         type empty;
       }
     }
     output {
       choice output_c {
         case output-tag {
           leaf output {
             type string;
           }
         }
         case actual-tag {
           anyxml subscribers-summary-information;
         }
         case multichassis-tag {
           anyxml multi-routing-engine-results;
         }
       }
     }
   }
   rpc get-subscribers-port-summary {
     description "Display full subscriber port summary";
     input {
       leaf extensive {
         description "Display full subscriber port detail";
         type empty;
       }
     }
     output {
       choice output_c {
         case output-tag {
           leaf output {
             type string;
           }
         }
         case actual-tag {
           anyxml subscribers-summary-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
