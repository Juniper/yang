/*
 * Copyright (c) 2022 Juniper Networks, Inc.
 * All rights reserved.
 */
 module junos-nfx-conf-security {
   namespace "http://yang.juniper.net/junos-nfx/conf/security";

   prefix jc-security;

   import junos-common-types {
     prefix jt;
     revision-date 2019-01-01;
   }

   import junos-nfx-conf-root {
     prefix jc;
     revision-date 2019-01-01;
   }

   organization "Juniper Networks, Inc.";

   contact "yang-support@juniper.net";

   description "Junos security configuration module";

   revision 2019-01-01 {
     description "Junos: 22.1R1.10";
   }

   augment /jc:configuration {
     uses security-group;
   }
   augment /jc:configuration/jc:groups {
     uses security-group;
   }
   grouping security-group {
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           container decryption-failures {
             presence "enable decryption-failures";
             description "No. of decryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container encryption-failures {
             presence "enable encryption-failures";
             description "No. of encryption failures before which an alarm needs to be raised";
             uses apply-advanced;
             leaf threshold {
               description "Threshold value [default is 1000]";
               default "1000";
               type union {
                 type string {
                   pattern "<.*>|$.*";
                 }
                 type uint32 {
                   range "1 .. 1000000000";
                 }
               }
             }
           }
           container ike-phase1-failures {
             presence "enable ike-phase1-failures";
             description "No. of IKE Phase-1 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           container ike-phase2-failures {
             presence "enable ike-phase2-failures";
             description "No. of IKE Phase-2 failures before which an alarm needs to be raised";
             uses apply-advanced;
             leaf threshold {
               description "Threshold value [default is 20]";
               default "20";
               type union {
                 type string {
                   pattern "<.*>|$.*";
                 }
                 type uint32 {
                   range "1 .. 1000000000";
                 }
               }
             }
           }
           leaf key-generation-self-test {
             description "Raise alarm for key generation self test failures";
             type empty;
           }
           leaf non-cryptographic-self-test {
             description "Raise alarm for non-cryptographic self test failures";
             type empty;
           }
           container policy {
             description "Raise alarm for flow policy violations";
             uses apply-advanced;
             container source-ip {
               presence "enable source-ip";
               description "Configure source address type of policy violation";
               uses apply-advanced;
               leaf threshold {
                 description "Number of source IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total source IP address number that can be done policy violation check concurrently";
                 default "1024";
                 type union {
                   type string {
                     pattern "<.*>|$.*";
                   }
                   type uint32 {
                     range "1 .. 10240";
                   }
                 }
               }
             }
             container destination-ip {
               presence "enable destination-ip";
               description "Configure destination address type of policy violation";
               uses apply-advanced;
               leaf threshold {
                 description "Number of destination IP address matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total destination IP address number that can be done policy violation check concurrently";
                 default "1024";
                 type union {
                   type string {
                     pattern "<.*>|$.*";
                   }
                   type uint32 {
                     range "1 .. 10240";
                   }
                 }
               }
             }
             container application {
               presence "enable application";
               description "Configure application type of policy violation";
               uses apply-advanced;
               leaf threshold {
                 description "Number of application matches to raise alarm";
                 default "1000";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total application number that can be done policy violation check concurrently";
                 default "1024";
                 type union {
                   type string {
                     pattern "<.*>|$.*";
                   }
                   type uint32 {
                     range "1 .. 10240";
                   }
                 }
               }
             }
             container policy-match {
               presence "enable policy-match";
               description "Configure policy type of policy violation";
               uses apply-advanced;
               leaf threshold {
                 description "Number of policy matches to raise alarm";
                 default "100";
                 type union {
                   type string {
                     pattern "<.*>|$.*";
                   }
                   type uint32 {
                     range "1 .. 4294967295";
                   }
                 }
               }
               leaf duration {
                 description "Time window matches must occur within";
                 default "1";
                 units "seconds";
                 type union {
                   type string {
                     pattern "<.*>|$.*";
                   }
                   type uint32 {
                     range "1 .. 3600";
                   }
                 }
               }
               leaf size {
                 description "Total concurrent number of policy check violations";
                 default "1024";
                 type union {
                   type string {
                     pattern "<.*>|$.*";
                   }
                   type uint32 {
                     range "1 .. 10240";
                   }
                 }
               }
             }
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
           leaf idp {
             description "Raise alarm for idp attack";
             type empty;
           }
         }
       }
       container log {
         description "Configure security log";
         uses log-object;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             type string {
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             type string;
           }
           uses apply-advanced;
           leaf rsa1-key {
             description "Base64 encoded RSA key (protocol version 1)";
             type string;
           }
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       container pki {
         description "PKI service configuration";
         presence "enable pki";
         uses security-pki;
       }
       container distribution-profile {
         description "IPSec Tunnels distribution profile";
         uses apply-advanced;
         list profile-entity {
           key name;
           ordered-by user;
           description "IPSec Tunnels distribution profile container";
           uses security-distribution-profile;
         }
         leaf fat-core {
           description "Power Mode IPSec fat-tunnel mode";
           type empty;
         }
       }
       container ike {
         description "IKE configuration";
         uses security-ike;
       }
       container ipsec {
         description "IPSec configuration";
         uses security-ipsec-vpn;
       }
       container group-vpn {
         description "Group VPN configuration";
         uses security-group-vpn;
       }
       container ipsec-policy {
         description "IPSec policy configuration";
         uses security-ipsec-policies;
       }
       container idp {
         description "Configure IDP";
         list idp-policy {
           key name;
           ordered-by user;
           description "Configure IDP policy";
           uses idp-policy-type;
         }
         leaf active-policy {
           description "Set active policy";
           status deprecated;
           type string;
         }
         leaf default-policy {
           description "Set active policy";
           type string;
         }
         list custom-attack {
           key name;
           ordered-by user;
           description "Configure custom attacks";
           uses custom-attack-type;
         }
         list custom-attack-group {
           key name;
           ordered-by user;
           description "Configure custom attack groups";
           uses custom-attack-group-type;
         }
         list dynamic-attack-group {
           key name;
           ordered-by user;
           description "Configure dynamic attack groups";
           uses dynamic-attack-group-type;
         }
         container traceoptions {
           description "Trace options for idp services";
           uses idpd-traceoptions-type;
         }
         container security-package {
           description "Security package options";
           uses apply-advanced;
           leaf url {
             description "URL of Security package download";
             type string;
           }
           leaf source-address {
             description "Source address to be used for sending download request";
             type jt:ipv4addr;
           }
           leaf proxy-profile {
             description "Proxy profile of security package download";
             type string {
               length "1 .. 64";
             }
           }
           leaf routing-instance {
             description "Routing instance for security-package download";
             type string;
           }
           container install {
             presence "enable install";
             description "Configure install command";
             uses apply-advanced;
             leaf ignore-version-check {
               description "Skip version check  when attack database gets installed";
               type empty;
             }
             leaf ignore-appid-failure {
               description "Continue idp installation even if appid installation fails";
               type empty;
             }
           }
           container automatic {
             presence "enable automatic";
             description "Scheduled download and update";
             uses apply-advanced;
             leaf start-time {
               description "Start time (YYYY-MM-DD.HH:MM:SS)";
               type jt:time;
             }
             leaf interval {
               description "Interval";
               units "hours";
               type union {
                 type string {
                   pattern "<.*>|$.*";
                 }
                 type uint32 {
                   range "1 .. 336";
                 }
               }
             }
             leaf download-timeout {
               description "Maximum time for download to complete";
               status deprecated;
               default "1";
               units "minutes";
               type union {
                 type string {
                   pattern "<.*>|$.*";
                 }
                 type uint32 {
                   range "1 .. 60";
                 }
               }
             }
             choice enable-disable {
               case case_1 {
                 leaf enable {
                   description "Enable";
                   type empty;
                 }
               }
             }
           }
         }
         container sensor-configuration {
           description "IDP Sensor Configuration";
           container log {
             description "IDP Log Configuration";
             uses apply-advanced;
             leaf cache-size {
               description "Log cache size";
               type union {
                 type string {
                   pattern "<.*>|$.*";
                 }
                 type uint32;
               }
             }
             container suppression {
               presence "enable suppression";
               description "Log suppression";
               uses apply-advanced;
               choice enable-disable {
                 case case_1 {
                   leaf disable {
                     description "Disable log suppression";
                     type empty;
                   }
                 }
               }
               choice include-destination-address-choice {
                 leaf include-destination-address {
                   description "Include destination address while performing a log suppression";
                   type empty;
                 }
                 leaf no-include-destination-address {
                   description "Don't include destination address while performing a log suppression";
                   type empty;
                 }
               }
               leaf start-log {
                 description "Suppression start log";
                 type union {
                   type string {
                     pattern "<.*>|$.*";
                   }
                   type uint32;
                 }
               }
               leaf max-logs-operate {
                 description "Maximum logs can be operate on";
                 type union {
                   type string {
                     pattern "<.*>|$.*";
                   }
                   type uint32;
                 }
               }
               leaf max-time-report {
                 description "Time after suppressed logs will be reported";
                 type union {
                   type string {
                     pattern "<.*>|$.*";
                   }
                   type uint32;
                 }
               }
             }
           }
           container packet-log {
             description "IDP Packetlog Configuration";
             uses apply-advanced;
             container total-memory {
               description "Total memory unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             container max-sessions {
               description "Max num of sessions in unit(%)";
               uses apply-advanced;
               leaf percentage-value {
                 type union {
                   type string {
                     pattern "<.*>|$.*";
                   }
                   type uint32;
                 }
               }
               leaf per-logical-domain {
                 type union {
                   type string {
                     pattern "<.*>|$.*";
                   }
                   type uint32;
                 }
               }
             }
             leaf threshold-logging-interval {
               description "Interval of logs for max limit session/memory reached in minutes";
               type union {
                 type string {
                   pattern "<.*>|$.*";
                 }
                 type uint32;
               }
             }
             leaf source-address {
               description "Source IP address used to transport packetlog to a host";
               type jt:ipv4addr;
             }
             container host {
               description "Destination host to send packetlog to";
               uses apply-advanced;
               leaf ipaddr {
                 description "IP address";
                 type jt:ipv4addr;
               }
               leaf port {
                 description "UDP port number";
                 type union {
                   type uint16;
                   type string {
                     pattern "<.*>|$.*";
                   }
                 }
               }
             }
             leaf ssl-profile-name {
               description "SSL initiation profile name to be used for packetlog";
               type string {
                 length "1 .. 127";
               }
             }
           }
           container application-identification {
             presence "enable application-identification";
             description "Application identification";
             uses apply-advanced;
             choice enable-disable {
               case case_1 {
                 leaf disable {
                   description "Disable application identification";
                   type empty;
                 }
               }
             }
             choice application-system-cache-choice {
               leaf application-system-cache {
                 description "Application system cache";
                 type empty;
               }
               leaf no-application-system-cache {
                 description "Don't application system cache";
                 type empty;
               }
             }
             leaf max-tcp-session-packet-memory {
               description "Max TCP session memory";
               status deprecated;
               type union {
                 type string {
                   pattern "<.*>|$.*";
                 }
                 type uint32;
               }
             }
             leaf max-udp-session-packet-memory {
               description "Max UDP session memory";
               status deprecated;
               type union {
                 type string {
                   pattern "<.*>|$.*";
                 }
                 type uint32;
               }
             }
             leaf max-sessions {
               description "Max sessions that can run AI at the same time";
               status deprecated;
               type union {
                 type string {
                   pattern "<.*>|$.*";
                 }
                 type uint32;
               }
             }
             leaf max-packet-memory {
               description "Max packet memory";
               status deprecated;
               type union {
                 type string {
                   pattern "<.*>|$.*";
                 }
                 type uint32;
               }
             }
             leaf max-packet-memory-ratio {
               description "Max packet memory ratio";
               type union {
                 type string {
                   pattern "<.*>|$.*";
                 }
                 type uint32;
               }
             }
             leaf max-reass-packet-memory-ratio {
               description "Max reass packet memory ratio";
               status deprecated;
               type union {
                 type string {
                   pattern "<.*>|$.*";
                 }
                 type uint32;
               }
             }
             leaf application-system-cache-timeout {
               description "Application system cache timeout";
               type union {
                 type string {
                   pattern "<.*>|$.*";
                 }
                 type uint32;
               }
             }
           }
           container flow {
             description "Flow configuration";
             uses apply-advanced;
             choice log-errors-choice {
               leaf log-errors {
                 description "Flow log errors";
                 type empty;
               }
               leaf no-log-errors {
                 description "Don't flow log errors";
                 type empty;
               }
             }
             choice allow-icmp-without-flow-choice {
               leaf allow-icmp-without-flow {
                 description "Allow icmp without flow";
                 status deprecated;
                 type empty;
               }
               leaf no-allow-icmp-without-flow {
                 description "Don't allow icmp without flow";
                 status deprecated;
                 type empty;
               }
             }
             leaf hash-table-size {
               description "Flow hash table size";
               type union {
                 type string {
                   pattern "<.*>|$.*";
                 }
                 type uint32;
               }
             }
             leaf reject-timeout {
               description "Flow reject timeout";
               type union {
                 type string {
                   pattern "<.*>|$.*";
                 }
                 type uint32;
               }
             }
             leaf max-timers-poll-ticks {
               description "Maximum timers poll ticks";
               type union {
                 type string {
                   pattern "<.*>|$.*";
                 }
                 type uint32;
               }
             }
             leaf fifo-max-size {
               description "Maximum fifo size";
               type union {
                 type string {
                   pattern "<.*>|$.*";
                 }
                 type uint32;
               }
             }
             leaf udp-anticipated-timeout {
               description "Maximum udp anticipated timeout";
               type union {
                 type string {
                   pattern "<.*>|$.*";
                 }
                 type uint32;
               }
             }
             leaf allow-nonsyn-connection {
               description "Allow TCP non-syn connection";
               type empty;
             }
             leaf drop-on-limit {
               description "Drop connections on exceeding resource limits";
               type empty;
             }
             leaf drop-on-failover {
               description "Drop traffic on HA failover sessions";
               type empty;
             }
             leaf drop-if-no-policy-loaded {
               description "Drop all traffic till IDP policy gets loaded";
               type empty;
             }
             leaf max-sessions-offset {
               description "Maximum session offset limit percentage";
               type union {
                 type string {
                   pattern "<.*>|$.*";
                 }
                 type uint32;
               }
             }
             leaf min-objcache-limit-lt {
               description "Memory lower threshold limit percentage";
               type union {
                 type string {
                   pattern "<.*>|$.*";
                 }
                 type uint32;
               }
             }
             leaf min-objcache-limit-ut {
               description "Memory upper threshold limit percentage";
               type union {
                 type string {
                   pattern "<.*>|$.*";
                 }
                 type uint32;
               }
             }
             leaf session-steering {
               description "Session steering for session anticipation";
               type empty;
             }
             leaf idp-bypass-cpu-usg-overload {
               description "Enable IDP bypass of sessions/packets on CPU usage overload";
               type empty;
             }
             leaf idp-bypass-cpu-threshold {
               description "Threshold of CPU usage in percentage for IDP bypass";
               default "85";
               type union {
                 type string {
                   pattern "<.*>|$.*";
                 }
                 type uint32;
               }
             }
             leaf idp-bypass-cpu-tolerance {
               description "Tolerance of CPU usage in percentage for IDP bypass";
               default "5";
               type union {
                 type string {
                   pattern "<.*>|$.*";
                 }
                 type uint32;
               }
             }
             leaf intel-inspect-enable {
               description "Minimizes IDP processing during system overload";
               type empty;
             }
             leaf intel-inspect-cpu-usg-threshold {
               description "CPU usage threshold percentage for intelligent inspection";
               default "80";
               type union {
                 type string {
                   pattern "<.*>|$.*";
                 }
                 type uint32;
               }
             }
             leaf intel-inspect-cpu-usg-tolerance {
               description "CPU usage tolerance percentage for intelligent inspection";
               default "5";
               type union {
                 type string {
                   pattern "<.*>|$.*";
                 }
                 type uint32;
               }
             }
             leaf intel-inspect-free-mem-threshold {
               description "Free memory threshold percentage for intelligent inspection";
               default "15";
               type union {
                 type string {
                   pattern "<.*>|$.*";
                 }
                 type uint32;
               }
             }
             leaf intel-inspect-mem-tolerance {
               description "Memory tolerance percentage for intelligent inspection";
               default "5";
               type union {
                 type string {
                   pattern "<.*>|$.*";
                 }
                 type uint32;
               }
             }
             leaf intel-inspect-disable-content-decompress {
               description "Disables payload content decompression";
               type empty;
             }
             leaf intel-inspect-session-bytes-depth {
               description "Session bytes scanning depth";
               default "0";
               type union {
                 type string {
                   pattern "<.*>|$.*";
                 }
                 type uint32;
               }
             }
             leaf-list intel-inspect-protocols {
               ordered-by user;
               description "Protocols to be processed in Intelligent Inspection mode";
               type string;
             }
             leaf-list intel-inspect-signature-severity {
               ordered-by user;
               description "Signature severities to be considered for IDP processing";
               type enumeration {
                 enum "minor" {
                 }
                 enum "major" {
                 }
                 enum "critical" {
                 }
               }
             }
           }
           container re-assembler {
             description "Re-assembler configuration";
             uses apply-advanced;
             choice drop-on-syn-in-window-choice {
               leaf drop-on-syn-in-window {
                 description "Drop session when SYN is seen in the window";
                 type empty;
               }
               leaf no-drop-on-syn-in-window {
                 description "Don't drop session when SYN is seen in the window";
                 type empty;
               }
             }
             choice ignore-memory-overflow-choice {
               leaf ignore-memory-overflow {
                 description "Ignore memory overflow";
                 type empty;
               }
               leaf no-ignore-memory-overflow {
                 description "Don't ignore memory overflow";
                 type empty;
               }
             }
             choice ignore-reassembly-memory-overflow-choice {
               leaf ignore-reassembly-memory-overflow {
                 description "Ignore packet reassembly memory overflow";
                 type empty;
               }
               leaf no-ignore-reassembly-memory-overflow {
                 description "Don't ignore packet reassembly memory overflow";
                 type empty;
               }
             }
             leaf ignore-reassembly-overflow {
               description "Ignore global reassembly overflow";
               type empty;
             }
             leaf max-packet-mem {
               description "Maximum packet memory";
               status deprecated;
               type union {
                 type string {
                   pattern "<.*>|$.*";
                 }
                 type uint32;
               }
             }
             leaf max-flow-mem {
               description "Maximum flow memory";
               type union {
                 type string {
                   pattern "<.*>|$.*";
                 }
                 type uint32;
               }
             }
             leaf max-packet-mem-ratio {
               description "Maximum packet memory ratio";
               type union {
                 type string {
                   pattern "<.*>|$.*";
                 }
                 type uint32;
               }
             }
             leaf action-on-reassembly-failure {
               description "Select the action on reassembly failures";
               default "drop";
               type enumeration {
                 enum "ignore" {
                   description "No action is taken.";
                 }
                 enum "drop" {
                   description "Drop the packet.";
                 }
                 enum "drop-session" {
                   description "Drop the session.";
                 }
               }
             }
             choice tcp-error-logging-choice {
               leaf tcp-error-logging {
                 description "Enable logging on tcp errors";
                 type empty;
               }
               leaf no-tcp-error-logging {
                 description "Don't enable logging on tcp errors";
                 type empty;
               }
             }
             leaf max-synacks-queued {
               description "Maximum syn-acks queued with different SEQ numbers ";
               type union {
                 type string {
                   pattern "<.*>|$.*";
                 }
                 type uint32;
               }
             }
             choice force-tcp-window-checks-choice {
               leaf force-tcp-window-checks {
                 description "Force TCP window checks if uni-directional policy is configured";
                 type empty;
               }
               leaf no-force-tcp-window-checks {
                 description "Don't force TCP window checks if uni-directional policy is configured";
                 type empty;
               }
             }
           }
           container ips {
             description "Ips configuration";
             uses apply-advanced;
             choice process-override-choice {
               leaf process-override {
                 description "Process override";
                 type empty;
               }
               leaf no-process-override {
                 description "Don't process override";
                 type empty;
               }
             }
             choice detect-shellcode-choice {
               leaf detect-shellcode {
                 description "Detect shellcode";
                 type empty;
               }
               leaf no-detect-shellcode {
                 description "Don't detect shellcode";
                 type empty;
               }
             }
             choice process-ignore-s2c-choice {
               leaf process-ignore-s2c {
                 description "Process ignore s2c";
                 type empty;
               }
               leaf no-process-ignore-s2c {
                 description "Don't process ignore s2c";
                 type empty;
               }
             }
             choice ignore-regular-expression-choice {
               leaf ignore-regular-expression {
                 description "Ignore regular expression";
                 type empty;
               }
               leaf no-ignore-regular-expression {
                 description "Don't ignore regular expression";
                 type empty;
               }
             }
             leaf process-port {
               description "Process port";
               type union {
                 type string {
                   pattern "<.*>|$.*";
                 }
                 type uint32;
               }
             }
             leaf fifo-max-size {
               description "Maximum fifo size";
               type union {
                 type string {
                   pattern "<.*>|$.*";
                 }
                 type uint32;
               }
             }
             leaf log-supercede-min {
               description "Minimum log supercede";
               type union {
                 type string {
                   pattern "<.*>|$.*";
                 }
                 type uint32;
               }
             }
             leaf content-decompression-max-memory-kb {
               description "Maximum memory usage in kilo bytes";
               type union {
                 type string {
                   pattern "<.*>|$.*";
                 }
                 type uint32;
               }
             }
             leaf content-decompression-max-ratio {
               description "Maximum decompression ratio supported";
               type union {
                 type string {
                   pattern "<.*>|$.*";
                 }
                 type uint32;
               }
             }
             leaf session-pkt-depth {
               description "Session pkt scanning depth";
               type union {
                 type string {
                   pattern "<.*>|$.*";
                 }
                 type uint32;
               }
             }
           }
           container global {
             description "Global configuration";
             uses apply-advanced;
             choice enable-packet-pool-choice {
               leaf enable-packet-pool {
                 description "Enable packet pool";
                 type empty;
               }
               leaf no-enable-packet-pool {
                 description "Don't enable packet pool";
                 type empty;
               }
             }
             leaf log-xff-header {
               description "Log xff header";
               type empty;
             }
             choice enable-all-qmodules-choice {
               leaf enable-all-qmodules {
                 description "Enable all qmodules";
                 type empty;
               }
               leaf no-enable-all-qmodules {
                 description "Don't enable all qmodules";
                 type empty;
               }
             }
             choice policy-lookup-cache-choice {
               leaf policy-lookup-cache {
                 description "Policy lookup cache";
                 type empty;
               }
               leaf no-policy-lookup-cache {
                 description "Don't policy lookup cache";
                 type empty;
               }
             }
             leaf memory-limit-percent {
               description "Memory limit percentage";
               type union {
                 type string {
                   pattern "<.*>|$.*";
                 }
                 type uint32;
               }
             }
             leaf disable-idp-processing {
               description "Flag to disable IDP processing";
               type empty;
             }
             leaf intelligent-offload {
               description "Intelligently offload the flow";
               type enumeration {
                 enum "disable" {
                   description "Disable flow offload";
                 }
                 enum "conservative" {
                   description "Increases scrutiny of flows prior to offload";
                 }
               }
             }
           }
           container detector {
             description "Detector Configuration";
             uses apply-advanced;
             list protocol-name {
               key name;
               ordered-by user;
               description "Apropriate help string";
               uses proto-object;
             }
           }
           container ssl-inspection {
             description "SSL inspection";
             uses apply-advanced;
             leaf sessions {
               description "Number of SSL sessions to inspect";
               default "10000";
               type union {
                 type string {
                   pattern "<.*>|$.*";
                 }
                 type uint32;
               }
             }
             leaf session-id-cache-timeout {
               description "Timeout value for SSL session ID cache";
               default "600";
               units "seconds";
               type union {
                 type string {
                   pattern "<.*>|$.*";
                 }
                 type uint32;
               }
             }
             leaf maximum-cache-size {
               description "Maximum SSL session ID cache size";
               default "100000";
               units "sessions";
               type union {
                 type string {
                   pattern "<.*>|$.*";
                 }
                 type uint32;
               }
             }
             leaf cache-prune-chunk-size {
               description "Number of cache entries to delete when pruning SSL session ID cache";
               default "100";
               type union {
                 type string {
                   pattern "<.*>|$.*";
                 }
                 type uint32;
               }
             }
             leaf key-protection {
               description "Enable SSL key protection";
               type empty;
             }
           }
           leaf disable-low-memory-handling {
             description "Do not abort IDP operations under low memory condition";
             type empty;
           }
           container high-availability {
             description "High availability configuration";
             uses apply-advanced;
             leaf no-policy-cold-synchronization {
               description "Disable policy cold synchronization";
               type empty;
             }
           }
           container security-configuration {
             description "IDP security configuration";
             uses apply-advanced;
             leaf protection-mode {
               description "Enable security protection mode";
               type enumeration {
                 enum "datacenter" {
                   description "Security protection mode for datacenter";
                 }
                 enum "datacenter-full" {
                   description "Full security protection mode for datacenter";
                 }
                 enum "perimeter" {
                   description "Security protection mode for perimeter";
                 }
                 enum "perimeter-full" {
                   description "Full security protection mode for perimeter";
                 }
               }
             }
           }
         }
         leaf max-sessions {
           description "Max number of IDP sessions";
           type union {
             type uint32;
             type string {
               pattern "<.*>|$.*";
             }
           }
         }
         list logical-system {
           key name;
           ordered-by user;
           description "Configure max IDP sessions for the logial system";
           uses logical-system-type;
         }
         list tenant-system {
           key name;
           ordered-by user;
           description "Configure max IDP sessions for the tenant";
           uses tenant-system-type;
         }
         uses apply-advanced;
         container processes {
           description "Configure IDP Processes";
           uses apply-advanced;
         }
       }
       list address-book {
         key name;
         ordered-by user;
         description "Security address book";
         max-elements 4096;
         uses named-address-book-type;
       }
       container alg {
         description "Configure ALG security options";
         uses alg-object;
       }
       container application-firewall {
         presence "enable application-firewall";
         description "Configure application-firewall rule-sets";
         status deprecated;
         uses apply-advanced;
         container traceoptions {
           description "Rule-sets Tracing Options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container block-message {
             description "Block message settings";
             uses apply-advanced;
             container type {
               description "Type of block message desired";
               uses apply-advanced;
               choice type-choice {
                 case case_1 {
                   container custom-text {
                     description "Custom defined block message";
                     uses apply-advanced;
                     leaf content {
                       description "Content of custom-text";
                       type string {
                         length "1 .. 511";
                       }
                     }
                   }
                 }
                 case case_2 {
                   container custom-redirect-url {
                     description "Custom redirect URL server";
                     uses apply-advanced;
                     leaf content {
                       description "URL of block message";
                       type string {
                         length "1 .. 1023";
                       }
                     }
                   }
                 }
               }
             }
           }
         }
         list rule-sets {
           key name;
           ordered-by user;
           description "Configure application-firewall rule-sets";
           leaf name {
             description "Application firewall rule-set name";
             type string {
               length "1 .. 63";
             }
           }
           uses apply-advanced;
           list rule {
             key name;
             ordered-by user;
             description "Rule";
             uses appfw_rule_type;
           }
           container default-rule {
             presence "enable default-rule";
             description "Specify default rule for a rule-set";
             uses apply-advanced;
             choice action {
               case case_1 {
                 leaf permit {
                   description "Permit packets";
                   type empty;
                 }
               }
               case case_2 {
                 container deny {
                   presence "enable deny";
                   description "Deny packets";
                   uses apply-advanced;
                   leaf block-message {
                     description "Block message";
                     type empty;
                   }
                 }
               }
               case case_3 {
                 container reject {
                   presence "enable reject";
                   description "Reject packets";
                   uses apply-advanced;
                   leaf block-message {
                     description "Block message";
                     type empty;
                   }
                 }
               }
             }
           }
           leaf profile {
             description "Profile for block message";
             type string;
           }
         }
         container nested-application {
           presence "enable nested-application";
           description "Configure nested application dynamic lookup";
           status deprecated;
           uses apply-advanced;
           container dynamic-lookup {
             presence "enable dynamic-lookup";
             description "Configure dynamic lookup";
             uses apply-advanced;
             leaf enable {
               description "Enable dynamic lookup";
               type empty;
             }
           }
         }
       }
       container application-tracking {
         presence "enable application-tracking";
         description "Application tracking configuration";
         uses apply-advanced;
         leaf disable {
           description "Disable Application tracking";
           type empty;
         }
         choice update-interval {
           case case_1 {
             leaf first-update-interval {
               description "Interval when the first update message is sent";
               units "minutes";
               type union {
                 type uint32;
                 type string {
                   pattern "<.*>|$.*";
                 }
               }
             }
           }
           case case_2 {
             leaf first-update {
               description "Generate Application tracking initial message when a session is created";
               status deprecated;
               type empty;
             }
           }
         }
         leaf session-update-interval {
           description "Frequency in which Application tracking update messages are generated";
           units "minutes";
           type union {
             type uint32;
             type string {
               pattern "<.*>|$.*";
             }
           }
         }
         leaf log-session-create {
           description "Generate Application tracking session create log";
           type empty;
         }
         leaf log-session-close {
           description "Generate Application tracking session close log";
           type empty;
         }
         leaf no-volume-updates {
           description "Disable session volume update log";
           type empty;
         }
       }
       container utm {
         description "Content security service configuration";
         uses apply-advanced;
         container traceoptions {
           description "Trace options for utm";
           uses utm-traceoptions;
         }
         container application-proxy {
           description "Application proxy settings";
           uses apply-advanced;
           container traceoptions {
             description "Trace options for application proxy";
             uses utm-apppxy-traceoptions;
           }
         }
         container ipc {
           description "IPC settings";
           uses apply-advanced;
           container traceoptions {
             description "Trace options for IPC";
             uses utm-ipc-traceoptions;
           }
         }
         container custom-objects {
           description "Custom-objects settings";
           uses apply-advanced;
           container category-package {
             description "Category package download and install options";
             uses apply-advanced;
             leaf url {
               description "HTTPS URL of category package download";
               type string;
             }
             leaf proxy-profile {
               description "Proxy profile";
               type string {
                 length "1 .. 64";
               }
             }
             leaf routing-instance {
               description "Routing instance name";
               type string;
             }
             container automatic {
               description "Scheduled download and install";
               uses apply-advanced;
               leaf start-time {
                 description "Start time (YYYY-MM-DD.HH:MM:SS)";
                 type jt:time;
               }
               leaf interval {
                 description "Interval in hours";
                 default "168";
                 type union {
                   type string {
                     pattern "<.*>|$.*";
                   }
                   type uint32 {
                     range "1 .. 336";
                   }
                 }
               }
               leaf enable {
                 description "Enable automatic download and install";
                 type empty;
               }
             }
           }
           list mime-pattern {
             key name;
             ordered-by user;
             description "Configure mime-list object";
             uses mime-list-type;
           }
           list filename-extension {
             key name;
             ordered-by user;
             description "Configure extension-list object";
             status deprecated;
             uses extension-list-type;
           }
           list url-pattern {
             key name;
             ordered-by user;
             description "Configure url-list object";
             uses url-list-type;
           }
           list custom-url-category {
             key name;
             ordered-by user;
             description "Configure category-list object";
             uses category-list-type;
           }
           list protocol-command {
             key name;
             ordered-by user;
             description "Configure command-list object";
             status deprecated;
             uses command-list-type;
           }
           list custom-message {
             key name;
             ordered-by user;
             description "Configure custom-message object";
             uses custom-message-type;
           }
         }
         container default-configuration {
           description "Global default UTM configurations";
           uses apply-advanced;
           container anti-virus {
             description "Configure anti-virus feature";
             uses default-anti-virus-feature;
           }
           container web-filtering {
             description "Configure web-filtering feature";
             uses default-webfilter-feature;
           }
           container anti-spam {
             description "Configure anti-spam feature";
             uses default-anti-spam-feature;
           }
           container content-filtering {
             description "Configure content filtering feature";
             uses default-content-filtering-feature;
           }
         }
         container feature-profile {
           description "Feature-profile settings";
           uses apply-advanced;
           container anti-virus {
             description "Configure anti-virus feature";
             uses anti-virus-feature;
           }
           container web-filtering {
             description "Configure web-filtering feature";
             uses webfilter-feature;
           }
           container anti-spam {
             description "Configure anti-spam feature";
             uses anti-spam-feature;
           }
           container content-filtering {
             description "Configure content filtering feature";
             status deprecated;
             uses content-filtering-feature;
           }
         }
         list utm-policy {
           key name;
           ordered-by user;
           description "Configure profile ";
           uses profile-setting;
         }
       }
       container dynamic-address {
         presence "enable dynamic-address";
         description "Configure security dynamic address";
         uses apply-advanced;
         container traceoptions {
           description "Security dynamic address tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "configuration" {
                   description "Configuration details";
                 }
                 enum "control" {
                   description "Daemon control message";
                 }
                 enum "ipc" {
                   description "IPC message sending and receiving";
                 }
                 enum "ip-entry" {
                   description "IP entry management";
                 }
                 enum "file-retrieval" {
                   description "File retrieval";
                 }
                 enum "lookup" {
                   description "Lookup detail";
                 }
                 enum "all" {
                   description "Trace everything";
                 }
               }
             }
           }
         }
         list feed-server {
           key name;
           ordered-by user;
           description "Security dynamic address feed-server";
           leaf name {
             description "Security dynamic address feed-server name";
             type string {
               length "1 .. 16";
             }
           }
           uses apply-advanced;
           leaf description {
             description "Text description of feed-server";
             type string {
               length "1 .. 900";
             }
           }
           choice hostname-or-url {
             case case_1 {
               leaf hostname {
                 description "Hostname or IP address of feed-server";
                 type string {
                   length "1 .. 256";
                 }
               }
             }
             case case_2 {
               leaf url {
                 description "URL,example:example.url.com;1.1.1.1/<folder-or-file-path>;Browser can verify its validity";
                 type string {
                   length "1 .. 256";
                 }
               }
             }
           }
           leaf update-interval {
             description "Interval to retrieve update";
             default "300";
             units "seconds";
             type union {
               type string {
                 pattern "<.*>|$.*";
               }
               type uint32 {
                 range "30 .. 4294967295";
               }
             }
           }
           leaf hold-interval {
             description "Time to keep IP entry when update failed";
             default "86400";
             units "seconds";
             type union {
               type string {
                 pattern "<.*>|$.*";
               }
               type uint32 {
                 range "0 .. 4294967295";
               }
             }
           }
           leaf tls-profile {
             description "TLS profile";
             type string;
           }
           container validate-certificate-attributes {
             description "Validate some certificate attributes";
             uses apply-advanced;
             leaf subject-or-subject-alternative-names {
               description "One of them must match feed server host name";
               type empty;
             }
           }
           list feed-name {
             key name;
             ordered-by user;
             description "Feed name in feed-server";
             leaf name {
               description "Security dynamic address feed name in feed-server";
               type string {
                 length "1 .. 240";
               }
             }
             uses apply-advanced;
             leaf description {
               description "Text description of feed in feed-server";
               type string {
                 length "1 .. 900";
               }
             }
             leaf path {
               description "Path of feed, appended to feed-server to form a complete URL";
               type string {
                 length "1 .. 1024";
               }
             }
             leaf update-interval {
               description "Interval to retrieve update";
               units "seconds";
               type union {
                 type string {
                   pattern "<.*>|$.*";
                 }
                 type uint32 {
                   range "30 .. 4294967295";
                 }
               }
             }
             leaf hold-interval {
               description "Time to keep IP entry when update failed";
               units "seconds";
               type union {
                 type string {
                   pattern "<.*>|$.*";
                 }
                 type uint32 {
                   range "0 .. 4294967295";
                 }
               }
             }
           }
         }
         list address-name {
           key name;
           ordered-by user;
           description "Security dynamic address name";
           leaf name {
             description "Security dynamic address name";
             type string {
               length "1 .. 240";
             }
           }
           uses apply-advanced;
           leaf description {
             description "Text description of dynamic address";
             type string {
               length "1 .. 900";
             }
           }
           container profile {
             presence "enable profile";
             description "Information to categorize feed data into this dynamic address";
             uses apply-advanced;
             list feed-name {
               key name;
               ordered-by user;
               description "Name of feed in feed-server for this dynamic address";
               max-elements 1;
               leaf name {
                 description "Name of feed in feed-server which is mapped to this dynamic address";
                 type string {
                   length "1 .. 240";
                 }
               }
               uses apply-advanced;
             }
             list category {
               key name;
               ordered-by user;
               description "Name of category";
               max-elements 1;
               leaf name {
                 description "Name of category";
                 type string {
                   length "1 .. 32";
                 }
               }
               uses apply-advanced;
               leaf feed {
                 description "Name of feed under category";
                 type string {
                   length "1 .. 32";
                 }
               }
               list property {
                 key name;
                 ordered-by user;
                 description "Property to match";
                 max-elements 3;
                 leaf name {
                   description "Name of property";
                   type string {
                     length "1 .. 32";
                   }
                 }
                 uses apply-advanced;
                 choice property-value {
                   case case_1 {
                     list string {
                       key name;
                       ordered-by user;
                       description "Value type is strings";
                       max-elements 256;
                       leaf name {
                         description "String value";
                         type string {
                           length "1 .. 32";
                         }
                       }
                       uses apply-advanced;
                     }
                   }
                 }
               }
             }
           }
           leaf session-scan {
             description "Trigger session scan when the IP address is added";
             type empty;
           }
         }
         container session-scan {
           presence "enable session-scan";
           description "Trigger session scan for all the dynamic addresses";
           uses apply-advanced;
           leaf hold-interval {
             description "Time interval before the session scan request";
             default "10";
             units "seconds";
             type union {
               type string {
                 pattern "<.*>|$.*";
               }
               type uint32 {
                 range "1 .. 3600";
               }
             }
           }
         }
       }
       container remote-access {
         description "Configure remote access";
         uses apply-advanced;
         container global-options {
           description "Global remote-access configuration";
           uses apply-advanced;
           leaf auth-token-valid-time {
             description "Authentication token valid time (seconds) :default 60";
             default "60";
             units "seconds";
             type union {
               type string {
                 pattern "<.*>|$.*";
               }
               type uint32 {
                 range "1 .. 300";
               }
             }
           }
           leaf config-file-size {
             description "Set the Config file buffer size (default size 5120 bytes)";
             default "5120";
             units "bytes";
             type union {
               type string {
                 pattern "<.*>|$.*";
               }
               type uint32 {
                 range "5120 .. 10240";
               }
             }
           }
         }
         list profile {
           key name;
           ordered-by user;
           description "Remote access profile";
           uses remote-access-profile-config;
         }
         list client-config {
           key name;
           ordered-by user;
           description "Remote-access client configuration";
           uses remote-access-client-config;
         }
         container traceoptions {
           description "Remote-access trace configuration";
           uses remote-access-traceoptions;
         }
         leaf default-profile {
           description "Configure default profile";
           type string;
         }
       }
       container dynamic-application {
         presence "enable dynamic-application";
         description "Configure dynamic-application";
         uses apply-advanced;
         container traceoptions {
           description "Dynamic application tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         list profile {
           key name;
           ordered-by user;
           description "Configure application-firewall profile";
           leaf name {
             description "Surf control integrated profile name";
             type string {
               length "1 .. 63";
             }
           }
           uses apply-advanced;
           container redirect-message {
             description "Redirect message settings";
             uses apply-advanced;
             container type {
               description "Type of redirect message desired";
               uses apply-advanced;
               choice type-choice {
                 case case_1 {
                   container custom-text {
                     description "Custom defined text block message";
                     uses apply-advanced;
                     leaf content {
                       description "Content of custom-text";
                       type string {
                         length "1 .. 511";
                       }
                     }
                   }
                 }
                 case case_2 {
                   container redirect-url {
                     description "Custom redirect URL server";
                     uses apply-advanced;
                     leaf content {
                       description "URL of block message";
                       type string {
                         length "1 .. 1023";
                       }
                     }
                   }
                 }
               }
             }
           }
         }
       }
       container softwires {
         description "Configure softwire feature";
         uses softwires-object;
       }
       container forwarding-options {
         description "Security-forwarding-options configuration";
         uses apply-advanced;
         container family {
           description "Security forwarding-options for family";
           uses apply-advanced;
           container inet6 {
             description "Family IPv6";
             uses apply-advanced;
             leaf mode {
               description "Forwarding mode";
               type enumeration {
                 enum "packet-based" {
                   description "Enable packet-based forwarding";
                 }
                 enum "flow-based" {
                   description "Enable flow-based forwarding";
                 }
                 enum "drop" {
                   description "Disable forwarding";
                 }
               }
             }
           }
           container mpls {
             description "Family MPLS";
             uses apply-advanced;
             leaf mode {
               description "Forwarding mode";
               type enumeration {
                 enum "packet-based" {
                   description "Enable packet-based forwarding";
                 }
                 enum "flow-based" {
                   description "Enable flow-based forwarding for mpls";
                 }
               }
             }
           }
           container iso {
             description "Family ISO";
             uses apply-advanced;
             leaf mode {
               description "Forwarding mode";
               type enumeration {
                 enum "packet-based" {
                   description "Enable packet-based forwarding";
                 }
               }
             }
           }
         }
         list mirror-filter {
           key name;
           ordered-by user;
           description "Security mirror filters";
           max-elements 15;
           uses mirror-filter-type;
         }
         list secure-wire {
           key name;
           description "Secure-wire cross connections";
           uses secure-wire-type;
         }
         container mode {
           description "Tap or sniffer mode";
           uses apply-advanced;
           container tap {
             description "Tap mode";
             uses apply-advanced;
             leaf-list interface {
               ordered-by user;
               description "Tap enabled interface";
               type union {
                 type jt:interface-name;
                 type string {
                   pattern "<.*>|$.*";
                 }
               }
             }
             container inspect-pass-through-tunnel {
               description "Inspect pass-through tunnel";
               uses apply-advanced;
               leaf ipip {
                 description "IPIP";
                 type empty;
               }
               leaf gre {
                 description "GRE";
                 type empty;
               }
             }
           }
         }
         container receive-side-scaling {
           description "Receive side scaling";
           uses apply-advanced;
           container software-rss {
             description "Software RSS options";
             uses apply-advanced;
             leaf mode {
               description "Mode of Software RSS";
               default "automatic";
               type enumeration {
                 enum "automatic" {
                   description "Auto select Software RSS mode (default)";
                 }
                 enum "enable" {
                   description "Software RSS would be enabled";
                 }
                 enum "disable" {
                   description "Software RSS would be disabled";
                 }
               }
             }
             leaf io-thread-number {
               description "Software-RSS IO thread number";
               type union {
                 type string {
                   pattern "<.*>|$.*";
                 }
                 type uint32 {
                   range "1 .. 8";
                 }
               }
             }
           }
           container nic-rss {
             description "NIC RSS options";
             uses apply-advanced;
             leaf mode {
               description "Mode of NIC RSS";
               type enumeration {
                 enum "disable" {
                   description "NIC RSS would be disabled";
                 }
               }
             }
           }
         }
         container security-service {
           description "Security service actions when memory resource is in shortage";
           uses apply-advanced;
           leaf fail-open {
             description "Packet will bypass all the application services ";
             type empty;
           }
         }
         container resource-manager {
           description "Manage the resource for special usage";
           uses apply-advanced;
           container cpu {
             description "The CPU resource";
             uses apply-advanced;
             leaf re {
               description "The count of vCPUs assigned to RE (default is 1)";
               type union {
                 type string {
                   pattern "<.*>|$.*";
                 }
                 type uint32 {
                   range "2 .. 3";
                 }
               }
             }
           }
         }
         leaf no-allow-dataplane-sleep {
           description "Disable dataplane sleep";
           type empty;
         }
         container services-offload {
           description "Service offload option";
           uses apply-advanced;
           leaf disable {
             description "Disable services-offload";
             type empty;
           }
         }
       }
       container advanced-services {
         description "Advanced services configuration";
         uses apply-advanced;
         container data-plane {
           description "Data plane configuration";
           uses apply-advanced;
           container memory {
             description "Data plane memory configuration";
             uses apply-advanced;
             leaf low {
               description "Reduce data plane memory";
               type empty;
             }
           }
         }
       }
       container flow {
         description "FLOW configuration";
         uses apply-advanced;
         leaf enhanced-routing-mode {
           description "Enable enhanced route scaling";
           type empty;
         }
         container traceoptions {
           description "Trace options for flow services";
           uses flow-traceoptions-object;
         }
         leaf pending-sess-queue-length {
           description "Maximum queued length per pending session";
           default "normal";
           type enumeration {
             enum "normal" {
               description "Normal number of sessions queued";
             }
             enum "moderate" {
               description "Allow more queued sessions than normal";
             }
             enum "high" {
               description "Maximum number of queued sessions";
             }
           }
         }
         container enable-reroute-uniform-link-check {
           description "Enable reroute check with uniform link";
           uses apply-advanced;
           leaf nat {
             description "Enable NAT check";
             type empty;
           }
         }
         leaf allow-dns-reply {
           description "Allow unmatched incoming DNS reply packet";
           type empty;
         }
         leaf route-change-timeout {
           description "Timeout value for route change to nonexistent route";
           default "30";
           units "seconds";
           type union {
             type string {
               pattern "<.*>|$.*";
             }
             type uint32 {
               range "6 .. 1800";
             }
           }
         }
         leaf nh-resolve-timeout {
           description "Timeout value for nexthop resolve";
           default "10000";
           units "milliseconds";
           type union {
             type string {
               pattern "<.*>|$.*";
             }
             type uint32 {
               range "1 .. 20000";
             }
           }
         }
         leaf multicast-nh-resolve-retry {
           description "Retry count for nexthop resolve";
           default "0";
           type union {
             type string {
               pattern "<.*>|$.*";
             }
             type uint32 {
               range "0 .. 20";
             }
           }
         }
         leaf syn-flood-protection-mode {
           description "TCP SYN flood protection mode";
           default "syn-cookie";
           type enumeration {
             enum "syn-cookie" {
               description "Enable SYN cookie protection";
             }
             enum "syn-proxy" {
               description "Enable SYN proxy protection";
             }
           }
         }
         leaf allow-embedded-icmp {
           description "Allow embedded ICMP packets not matching a session to pass through";
           type empty;
         }
         leaf mcast-buffer-enhance {
           description "Allow to hold more packets during multicast session creation";
           type empty;
         }
         leaf strict-packet-order {
           description "Maintain arrival ordering when packets departing";
           type empty;
         }
         leaf allow-reverse-ecmp {
           description "Allow reverse ECMP route lookup";
           type empty;
         }
         leaf no-local-favor-ecmp {
           description "Not prefer local node in HA ECMP route lookup";
           type empty;
         }
         leaf sync-icmp-session {
           description "Allow icmp sessions to sync to peer node";
           type empty;
         }
         leaf ipsec-performance-acceleration {
           description "Accelerate the IPSec traffic performance";
           type empty;
         }
         leaf gre-performance-acceleration {
           description "Accelerate the GRE traffic performance";
           type empty;
         }
         container aging {
           description "Aging configuration";
           uses apply-advanced;
           leaf early-ageout {
             description "Delay before device declares session invalid";
             default "20";
             units "seconds";
             type union {
               type string {
                 pattern "<.*>|$.*";
               }
               type uint32 {
                 range "1 .. 65535";
               }
             }
           }
           leaf low-watermark {
             description "Percentage of session-table capacity at which aggressive aging-out ends";
             default "100";
             units "percent";
             type union {
               type string {
                 pattern "<.*>|$.*";
               }
               type uint32 {
                 range "0 .. 100";
               }
             }
           }
           leaf high-watermark {
             description "Percentage of session-table capacity at which aggressive aging-out starts";
             default "100";
             units "percent";
             type union {
               type string {
                 pattern "<.*>|$.*";
               }
               type uint32 {
                 range "0 .. 100";
               }
             }
           }
         }
         container ethernet-switching {
           description "Ethernet-switching configuration for flow";
           uses apply-advanced;
           leaf block-non-ip-all {
             description "Block all non-IP and non-ARP traffic including broadcast/multicast";
             type empty;
           }
           leaf bypass-non-ip-unicast {
             description "Allow all non-IP (including unicast) traffic";
             type empty;
           }
           container no-packet-flooding {
             presence "enable no-packet-flooding";
             description "Stop IP flooding, send ARP/ICMP to trigger MAC learning";
             uses apply-advanced;
             leaf no-trace-route {
               description "Don't send ICMP to trigger MAC learning";
               type empty;
             }
           }
           leaf bpdu-vlan-flooding {
             description "Set 802.1D BPDU flooding based on VLAN";
             type empty;
           }
         }
         container tcp-mss {
           description "TCP maximum segment size configuration";
           uses apply-advanced;
           container all-tcp {
             description "Enable MSS override for all packets";
             uses apply-advanced;
             leaf mss {
               description "MSS value";
               type union {
                 type string {
                   pattern "<.*>|$.*";
                 }
                 type uint32 {
                   range "64 .. 65535";
                 }
               }
             }
           }
           container ipsec-vpn {
             presence "enable ipsec-vpn";
             description "Enable MSS override for all packets entering IPSec tunnel";
             uses apply-advanced;
             leaf mss {
               description "MSS value";
               default "1320";
               type union {
                 type string {
                   pattern "<.*>|$.*";
                 }
                 type uint32 {
                   range "64 .. 65535";
                 }
               }
             }
           }
           container gre-in {
             presence "enable gre-in";
             description "Enable MSS override for all GRE packets coming out of an IPSec tunnel";
             uses apply-advanced;
             leaf mss {
               description "MSS value";
               default "1320";
               type union {
                 type string {
                   pattern "<.*>|$.*";
                 }
                 type uint32 {
                   range "64 .. 65535";
                 }
               }
             }
           }
           container gre-out {
             presence "enable gre-out";
             description "Enable MSS override for all GRE packets entering an IPsec tunnel";
             uses apply-advanced;
             leaf mss {
               description "MSS value";
               default "1320";
               type union {
                 type string {
                   pattern "<.*>|$.*";
                 }
                 type uint32 {
                   range "64 .. 65535";
                 }
               }
             }
           }
         }
         container tcp-session {
           description "Transmission Control Protocol session configuration";
           uses apply-advanced;
           leaf rst-invalidate-session {
             description "Immediately end session on receipt of reset (RST) segment";
             type empty;
           }
           leaf fin-invalidate-session {
             description "Immediately end session on receipt of fin (FIN) segment";
             type empty;
           }
           leaf rst-sequence-check {
             description "Check sequence number in reset (RST) segment";
             type empty;
           }
           leaf no-syn-check {
             description "Disable creation-time SYN-flag check";
             type empty;
           }
           leaf strict-syn-check {
             description "Enable strict syn check";
             type empty;
           }
           leaf no-syn-check-in-tunnel {
             description "Disable creation-time SYN-flag check for tunnel packets";
             type empty;
           }
           leaf no-sequence-check {
             description "Disable sequence-number checking";
             type empty;
           }
           leaf aggressive-tcp-ack {
             description "Enable aggressive TCP ACK, root lsys only";
             type empty;
           }
           leaf tcp-initial-timeout {
             description "Timeout for TCP session when initialization fails";
             default "20";
             units "seconds";
             type union {
               type string {
                 pattern "<.*>|$.*";
               }
               type uint32 {
                 range "4 .. 300";
               }
             }
           }
           leaf maximum-window {
             description "Maximum TCP proxy scaled receive window, default 256K bytes";
             default "256K";
             type enumeration {
               enum "64K" {
                 description "64K bytes receive window";
               }
               enum "128K" {
                 description "128K bytes receive window";
               }
               enum "256K" {
                 description "256K bytes receive window";
               }
               enum "512K" {
                 description "512K bytes receive window";
               }
               enum "1M" {
                 description "1M bytes receive window";
               }
             }
           }
           container time-wait-state {
             presence "enable time-wait-state";
             description "Session timeout value in time-wait state, default 150 seconds";
             uses apply-advanced;
             choice session-age-option {
               case case_1 {
                 leaf session-ageout {
                   description "Allow session to ageout using service based timeout values";
                   type empty;
                 }
               }
               case case_2 {
                 leaf session-timeout {
                   description "Configure session timeout value for time-wait state";
                   units "seconds";
                   type union {
                     type string {
                       pattern "<.*>|$.*";
                     }
                     type uint32 {
                       range "2 .. 600";
                     }
                   }
                 }
               }
             }
             leaf apply-to-half-close-state {
               description "Apply time-wait-state timeout to half-close state";
               type empty;
             }
           }
         }
         leaf force-ip-reassembly {
           description "Force to reassemble ip fragments";
           type empty;
         }
         leaf preserve-incoming-fragment-size {
           description "Preserve incoming fragment size for egress MTU";
           type empty;
         }
         leaf fragment-limit {
           description "Maximum number of fragments allowed for a packet";
           default "0";
           type union {
             type string {
               pattern "<.*>|$.*";
             }
             type uint32 {
               range "0 .. 250";
             }
           }
         }
         leaf fragment-reassembly-timeout {
           description "Re-assembly timeout (seconds) for fragments of a packet";
           default "0";
           units "seconds";
           type union {
             type string {
               pattern "<.*>|$.*";
             }
             type uint32 {
               range "0 .. 60";
             }
           }
         }
         container log {
           description "Enable log";
           uses apply-advanced;
           leaf dropped-icmp-packet {
             description "Log dropped ICMPv4 packet";
             type empty;
           }
           leaf dropped-illegal-packet {
             description "Log dropped illegal packet";
             type empty;
           }
         }
         container advanced-options {
           description "Flow config advanced options";
           uses apply-advanced;
           leaf drop-matching-reserved-ip-address {
             description "Drop matching reserved source IP address";
             type empty;
           }
           leaf drop-matching-link-local-address {
             description "Drop matching link local address";
             type empty;
           }
           leaf reverse-route-packet-mode-vr {
             description "Allow reverse route lookup with packet mode vr";
             type empty;
           }
         }
         container load-distribution {
           description "Flow config SPU load distribution";
           uses apply-advanced;
           container session-affinity {
             description "SPU load distribution based on the service anchor SPU";
             uses apply-advanced;
             leaf ipsec {
               description "IPsec service";
               type empty;
             }
           }
         }
         container packet-log {
           description "Configure flow packet log";
           uses apply-advanced;
           leaf enable {
             description "Enable log for dropped packet";
             type empty;
           }
           leaf throttle-interval {
             description "Interval should be configured as a power of two";
             default "1024";
             units "milliseconds";
             type union {
               type string {
                 pattern "<.*>|$.*";
               }
               type uint32 {
                 range "0 .. 32768";
               }
             }
           }
           list packet-filter {
             key name;
             ordered-by user;
             description "Configure packet log filter";
             max-elements 64;
             uses flow-filter-type;
           }
         }
         leaf power-mode-disable {
           description "Disable power mode express path processing";
           type empty;
         }
         leaf power-mode-ipsec-qat {
           description "Enable qat in power mode ipsec processing";
           type empty;
         }
       }
       container firewall-authentication {
         description "Firewall authentication parameters";
         uses apply-advanced;
         container traceoptions {
           description "Data-plane firewall authentication tracing options";
           uses apply-advanced;
           list flag {
             key name;
             ordered-by user;
             description "Events to include in trace output";
             leaf name {
               type enumeration {
                 enum "authentication" {
                   description "Data-plane firewall authentication events";
                 }
                 enum "proxy" {
                   description "Data-plane firewall authentication proxy events";
                 }
                 enum "all" {
                   description "All events";
                 }
               }
             }
             choice level {
               case case_1 {
                 leaf terse {
                   description "Include terse amount of output in trace";
                   type empty;
                 }
               }
               case case_2 {
                 leaf detail {
                   description "Include detailed amount of output in trace";
                   type empty;
                 }
               }
               case case_3 {
                 leaf extensive {
                   description "Include extensive amount of output in trace";
                   type empty;
                 }
               }
             }
           }
         }
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         list ids-option {
           key name;
           description "Configure ids-option";
           uses ids-option-type;
         }
         container traceoptions {
           description "Trace options for Network Security Screen";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list white-list {
           key name;
           description "Set of IP addresses for white list";
           max-elements 32;
           uses ids-wlist-type;
         }
       }
       container nat {
         description "Configure Network Address Translation";
         uses nat-object;
       }
       container forwarding-process {
         description "Configure security forwarding-process options";
         uses apply-advanced;
         leaf enhanced-services-mode {
           description "Enable enhanced application services mode";
           type empty;
         }
         container application-services {
           description "Configure application service options";
           uses apply-advanced;
           leaf maximize-alg-sessions {
             description "Maximize ALG session capacity";
             type empty;
           }
           leaf maximize-persistent-nat-capacity {
             description "Increase persistent NAT capacity by reducing maximum flow sessions";
             type empty;
           }
           container maximize-cp-sessions {
             presence "enable maximize-cp-sessions";
             description "Maximize CP session capacity";
             status deprecated;
             uses apply-advanced;
           }
           leaf session-distribution-mode {
             description "Session distribution mode";
             status deprecated;
             type enumeration {
               enum "normal" {
                 description "Normal mode";
                 status deprecated;
               }
               enum "hash-based" {
                 description "Hash mode";
                 status deprecated;
               }
             }
           }
           leaf enable-gtpu-distribution {
             description "Enable GTP-U distribution";
             type empty;
           }
           leaf packet-ordering-mode {
             description "Packet ordering mode";
             type enumeration {
               enum "hardware" {
                 description "Hardware mode";
               }
               enum "software" {
                 description "Software mode";
               }
             }
           }
           container maximize-idp-sessions {
             presence "enable maximize-idp-sessions";
             description "Run security services in dedicated processes to maximize IDP session capacity";
             uses apply-advanced;
             container weight {
               description "Adjust the weighting of the resources available for idp";
               uses apply-advanced;
               choice weight {
                 case case_1 {
                   leaf equal {
                     description "Equal resources to IDP and firewall";
                     status deprecated;
                     type empty;
                   }
                 }
                 case case_2 {
                   container idp {
                     presence "enable idp";
                     description "IDP has more resources than firewall";
                     uses apply-advanced;
                   }
                 }
                 case case_3 {
                   leaf firewall {
                     description "Firewall has more resources than IDP";
                     type empty;
                   }
                 }
               }
             }
             leaf inline-tap {
               description "Configure IDP in inline tap mode";
               type empty;
             }
           }
           leaf inline-fpga-crypto {
             description "Disable inline FPGA crypto";
             type enumeration {
               enum "disabled" {
                 description "Disable inline FPGA crypto";
               }
               enum "enabled" {
                 description "Enable inline FPGA crypto";
               }
             }
           }
         }
       }
       container policies {
         description "Configure Network Security Policies";
         presence "enable policies";
         uses policy-object-type;
       }
       container tcp-encap {
         presence "enable tcp-encap";
         description "Configure TCP Encapsulation.";
         uses apply-advanced;
         container traceoptions {
           description "Trace options for TCP encapsulation service";
           uses ragw-traceoptions;
         }
         list profile {
           key name;
           ordered-by user;
           description "Configure profile.";
           leaf name {
             description "Profile name identifier.";
             type string {
               length "1 .. 64";
             }
           }
           uses apply-advanced;
           leaf ssl-profile {
             description "SSL Termination profile";
             type string;
           }
           leaf log {
             description "Enable logging for remote-access";
             type empty;
           }
         }
         container global-options {
           description "Global settings for TCP encapsulation";
           leaf enable-tunnel-tracking {
             description "Track ESP tunnels";
             type empty;
           }
         }
       }
       container resource-manager {
         description "Configure resource manager security options";
         uses apply-advanced;
         container traceoptions {
           description "Traceoptions for resource manager";
           uses apply-advanced;
           list flag {
             key name;
             ordered-by user;
             description "Resource manager objects and events to include in trace";
             leaf name {
               type enumeration {
                 enum "client" {
                   description "Trace resource manager client";
                 }
                 enum "group" {
                   description "Trace resource manager group";
                 }
                 enum "resource" {
                   description "Trace resource manager resource";
                 }
                 enum "gate" {
                   description "Trace resource manager created gates";
                 }
                 enum "session" {
                   description "Trace resource manager created session";
                 }
                 enum "chassis cluster" {
                   description "Trace resource manager's chassis cluster events";
                 }
                 enum "messaging" {
                   description "Trace resource manager messaging";
                 }
                 enum "service pinhole" {
                   description "Trace resource manager created service pinholes";
                 }
                 enum "error" {
                   description "Trace all resource manager errors";
                 }
                 enum "all" {
                   description "Trace all resource manager objects and events";
                 }
               }
             }
             choice level {
               case case_1 {
                 leaf terse {
                   description "Set trace verbosity level to terse";
                   type empty;
                 }
               }
               case case_2 {
                 leaf detail {
                   description "Set trace verbosity level to detail";
                   type empty;
                 }
               }
               case case_3 {
                 leaf extensive {
                   description "Set trace verbosity level to extensive";
                   type empty;
                 }
               }
             }
           }
         }
         container services-memory {
           presence "enable services-memory";
           description "Manage services memory resources";
           uses apply-advanced;
           container match {
             presence "enable match";
             uses apply-advanced;
             leaf threshold {
               description "Service Memory Threshold";
               type union {
                 type string {
                   pattern "<.*>|$.*";
                 }
                 type int32 {
                   range "1 .. 100";
                 }
               }
             }
           }
           container then {
             presence "enable then";
             description "Action to take if the conditions are matched";
             uses apply-advanced;
             leaf fail-close {
               description "Enable fail-close";
               type empty;
             }
             leaf fail-open {
               description "Enable fail-open";
               type empty;
             }
             leaf drop-flows {
               description "Enable drop-flows";
               type empty;
             }
             leaf log {
               description "Enable logs";
               type empty;
             }
             leaf alarm {
               description "Enable Alarm";
               type empty;
             }
           }
         }
         container session-memory {
           presence "enable session-memory";
           description "Manage session memory resources";
           uses apply-advanced;
           container match {
             presence "enable match";
             uses apply-advanced;
             leaf threshold {
               description "Session Memory Threshold";
               type union {
                 type string {
                   pattern "<.*>|$.*";
                 }
                 type int32 {
                   range "1 .. 100";
                 }
               }
             }
           }
           container then {
             presence "enable then";
             description "Action to take if the conditions are matched";
             uses apply-advanced;
             container session-aggressive-ageout {
               presence "enable session-aggressive-ageout";
               description "Session ageout configuration";
               uses apply-advanced;
               leaf early-ageout {
                 description "Delay before device declares session invalid";
                 type union {
                   type string {
                     pattern "<.*>|$.*";
                   }
                   type int32 {
                     range "1 .. 65535";
                   }
                 }
               }
             }
             leaf log {
               description "Enable logs";
               type empty;
             }
             leaf alarm {
               description "Enable alarms";
               type empty;
             }
             leaf drop-flows {
               description "Enable drop-flows";
               type empty;
             }
           }
         }
         container cpu {
           presence "enable cpu";
           description "Manage cpu resources";
           uses apply-advanced;
           leaf disable-management {
             description "Disable Resource Manager CPU Management";
             type empty;
           }
           container match {
             presence "enable match";
             uses apply-advanced;
             leaf threshold {
               description "CPU Useage Threshold";
               type union {
                 type string {
                   pattern "<.*>|$.*";
                 }
                 type int32 {
                   range "1 .. 100";
                 }
               }
             }
           }
           container then {
             presence "enable then";
             description "Action to take if the conditions are matched";
             uses apply-advanced;
             leaf drop-flows {
               description "Enable drop-flows";
               type empty;
             }
             leaf drop-cps {
               description "Enable drop-cps";
               type empty;
             }
             leaf log {
               description "Enable logs";
               type empty;
             }
             leaf alarm {
               description "Enable drop-alarm";
               type empty;
             }
             leaf max-session-setup-rate {
               description "Maximum number of session creations allowed per second";
               type union {
                 type string {
                   pattern "<.*>|$.*";
                 }
                 type int32 {
                   range "0 .. 65535";
                 }
               }
             }
           }
         }
       }
       container analysis {
         description "Configure security analysis";
         uses apply-advanced;
         leaf no-report {
           description "Stops security analysis reporting";
           type empty;
         }
       }
       container traceoptions {
         description "Network security daemon tracing options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "routing-socket" {
                 description "Trace routing socket events";
               }
               enum "compilation" {
                 description "Trace compilation events";
               }
               enum "operational-command" {
                 description "Trace show or clear security commands via log file uspinfo.log";
               }
               enum "all" {
                 description "Trace everything";
               }
             }
           }
         }
         leaf rate-limit {
           description "Limit the incoming rate of trace messages";
           default "0";
           type union {
             type string {
               pattern "<.*>|$.*";
             }
             type uint32 {
               range "0 .. 4294967295";
             }
           }
         }
       }
       container datapath-debug {
         description "Datapath debug options";
         uses apply-advanced;
         container traceoptions {
           description "End to end debug trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container capture-file {
           description "Packet capture options";
           leaf filename {
             description "Capture file name";
             type string;
           }
           leaf format {
             description "Capture file format";
             type enumeration {
               enum "pcap" {
                 description "PCAP capture format";
               }
             }
           }
           leaf size {
             description "Maximum file size";
             type string;
           }
           leaf files {
             description "Maximum number of files";
             type union {
               type string {
                 pattern "<.*>|$.*";
               }
               type uint32 {
                 range "1 .. 10";
               }
             }
           }
           choice world-readable-choice {
             leaf world-readable {
               description "Allow any user to read packet-capture files";
               type empty;
             }
             leaf no-world-readable {
               description "Don't allow any user to read packet-capture files";
               type empty;
             }
           }
         }
         leaf maximum-capture-size {
           description "Max packet capture length";
           default "68";
           units "bytes";
           type union {
             type string {
               pattern "<.*>|$.*";
             }
             type uint32 {
               range "68 .. 10000";
             }
           }
         }
         list action-profile {
           key name;
           ordered-by user;
           description "Action profile definitions";
           uses e2e-action-profile;
         }
         list packet-filter {
           key name;
           ordered-by user;
           description "Packet filter configuration";
           max-elements 4;
           uses end-to-end-debug-filter;
         }
       }
       container user-identification {
         description "Configure user-identification";
         uses apply-advanced;
         container traceoptions {
           description "User-identification Tracing Options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace everything";
                 }
               }
             }
           }
         }
         list authentication-source {
           key name;
           description "Configure user-identification authentication-source";
           uses authentication-source-type;
         }
       }
       container zones {
         description "Zone configuration";
         uses apply-advanced;
         container functional-zone {
           presence "enable functional-zone";
           description "Functional zone";
           container management {
             presence "enable management";
             description "Host for out of band management interfaces";
             uses apply-advanced;
             list interfaces {
               key name;
               ordered-by user;
               description "Interfaces that are part of this zone";
               uses zone-interface-list-type;
             }
             leaf screen {
               description "Name of ids option object applied to the zone";
               type string {
                 length "1 .. 64";
               }
             }
             container host-inbound-traffic {
               description "Allowed system services & protocols";
               uses zone_host_inbound_traffic_t;
             }
             leaf description {
               description "Text description of zone";
               type string {
                 length "1 .. 900";
               }
             }
           }
         }
         list security-zone {
           key name;
           ordered-by user;
           description "Security zones";
           uses security-zone-type;
         }
       }
       leaf advanced-connection-tracking-timeout {
         description "System wide timeout value in seconds for advanced-connection-tracking entries";
         type union {
           type uint32;
           type string {
             pattern "<.*>|$.*";
           }
         }
       }
       container advance-policy-based-routing {
         presence "enable advance-policy-based-routing";
         description "Configure Network Security APBR Policies";
         uses apply-advanced;
         container traceoptions {
           description "Advance policy based routing tracing options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "lookup" {
                   description "Trace lookup events";
                 }
                 enum "compilation" {
                   description "Rule-sets compilation events";
                 }
                 enum "ipc" {
                   description "Inter-process communication events";
                 }
                 enum "all" {
                   description "Trace everything";
                 }
               }
             }
           }
         }
         container tunables {
           description "Configure advance policy based routing tunables";
           uses apply-advanced;
           leaf max-route-change {
             description "Maximum route change";
             default "1";
             type union {
               type string {
                 pattern "<.*>|$.*";
               }
               type uint32 {
                 range "0 .. 5";
               }
             }
           }
           leaf drop-on-zone-mismatch {
             description "Drop session if zone mismatches";
             type empty;
           }
           leaf no-l3l4-app-lookup {
             description "Ignore the look up for L3L4 custom app in APBR.";
             type empty;
           }
           leaf enable-logging {
             description "Enable AppTrack logging";
             type empty;
           }
         }
         list profile {
           key name;
           ordered-by user;
           description "Configure advance-policy-based-routing profile";
           leaf name {
             description "Advance policy based routing profile name";
             type string {
               length "1 .. 63";
             }
           }
           uses apply-advanced;
           list rule {
             key name;
             ordered-by user;
             description "Specify an advance policy based routing rule";
             uses apbr_rule_type;
           }
         }
         list active-probe-params {
           key name;
           ordered-by user;
           description "Active probe's settings";
           leaf name {
             description "Active probe setting name";
             type string {
               length "1 .. 63";
             }
           }
           uses apply-advanced;
           container settings {
             description "Settings";
             uses appqoe-probe-params;
           }
         }
         list metrics-profile {
           key name;
           ordered-by user;
           description "Configure metric profiles";
           leaf name {
             description "Profile name";
             type string {
               length "1 .. 63";
             }
           }
           uses apply-advanced;
           container sla-threshold {
             description "Configure SLA metric threshold";
             uses appqoe_sla_metric_profile;
           }
         }
         list underlay-interface {
           key name;
           ordered-by user;
           description "Underlay interface setting";
           status deprecated;
           leaf name {
             description "Underlay Interface name";
             type union {
               type jt:interface-device;
               type string {
                 pattern "<.*>|$.*";
               }
             }
           }
           uses apply-advanced;
           list unit {
             key name;
             description "One of more logical interface unit-numbers";
             leaf name {
               description "Unit number";
               type union {
                 type string {
                   pattern "<.*>|$.*";
                 }
                 type uint32 {
                   range "0 .. 1073741823";
                 }
               }
             }
             uses apply-advanced;
             leaf link-type {
               description "Link type of the interface";
               default "IP";
               type enumeration {
                 enum "IP" {
                   description "Select IP as the link-type";
                 }
                 enum "MPLS" {
                   description "Select MPLS as the link-type";
                 }
               }
             }
             leaf priority {
               description "Configure the priority for selecting this link";
               default "255";
               type union {
                 type string {
                   pattern "<.*>|$.*";
                 }
                 type uint8 {
                   range "1 .. 255";
                 }
               }
             }
             leaf speed {
               description "Speed of this link in Mbps";
               default "1000";
               type union {
                 type string {
                   pattern "<.*>|$.*";
                 }
                 type uint32 {
                   range "1 .. 1000000";
                 }
               }
             }
           }
         }
         list interface {
           key name;
           ordered-by user;
           description "Interface setting";
           leaf name {
             description "Interface name";
             type union {
               type jt:interface-device;
               type string {
                 pattern "<.*>|$.*";
               }
             }
           }
           uses apply-advanced;
           list unit {
             key name;
             description "One of more logical interface unit-numbers";
             leaf name {
               description "Unit number";
               type union {
                 type string {
                   pattern "<.*>|$.*";
                 }
                 type uint32 {
                   range "0 .. 1073741823";
                 }
               }
             }
             uses apply-advanced;
             leaf link-tag {
               description "Configure link-tag. Default is IP";
               type string {
                 length "1 .. 63";
               }
             }
             leaf priority {
               description "Configure the priority for selecting this link";
               default "255";
               type union {
                 type string {
                   pattern "<.*>|$.*";
                 }
                 type uint8 {
                   range "1 .. 255";
                 }
               }
             }
             leaf multipath-bandwidth {
               description "Bandwidth of this link in Mbps";
               default "1000";
               type union {
                 type string {
                   pattern "<.*>|$.*";
                 }
                 type uint32 {
                   range "1 .. 1000000";
                 }
               }
             }
             leaf weight {
               description "Configure the weight for selecting this link";
               default "1";
               type union {
                 type string {
                   pattern "<.*>|$.*";
                 }
                 type uint8 {
                   range "1 .. 255";
                 }
               }
             }
           }
         }
         list overlay-path {
           key name;
           ordered-by user;
           description "List of overlay paths";
           leaf name {
             description "Create a single instance of overlay path";
             type string {
               length "1 .. 63";
             }
           }
           uses apply-advanced;
           container tunnel-path {
             description "Tunnel start & end ip addresses";
             presence "enable tunnel-path";
             uses appqoe-probe-path;
           }
           container probe-path {
             description "Probe start & end ip addresses";
             presence "enable probe-path";
             uses appqoe-probe-path;
           }
         }
         list destination-path-group {
           key name;
           ordered-by user;
           description "Group of tunnels to a particular destination";
           leaf name {
             description "Destination group name";
             type string {
               length "1 .. 63";
             }
           }
           uses apply-advanced;
           container probe-routing-instance {
             presence "enable probe-routing-instance";
             description "Set routing instance for the probe-path";
             uses apply-advanced;
             leaf routing-instance-name {
               description "Name of routing instance";
               type string;
             }
           }
           container inline-gre-encap {
             presence "enable inline-gre-encap";
             description "Enable inline GRE encapsulation";
           }
           container active-probe-properties {
             presence "enable active-probe-properties";
             description "Additional applicable properties for the destination path group";
             uses apply-advanced;
             leaf active-probe-only {
               description "Enable active probing only to the destination path group";
               type empty;
             }
           }
           list overlay-path {
             key name;
             ordered-by user;
             description "List of paths";
             max-elements 20;
             leaf name {
               description "Name of Overlay Path";
               type string;
             }
             uses apply-advanced;
           }
         }
         container sla-options {
           presence "enable sla-options";
           description "Global SLA options";
           uses apply-advanced;
           container local-route-switch {
             presence "enable local-route-switch";
             description "Enable/disable Automatic local route switching";
             status deprecated;
             uses apply-advanced;
             leaf switch-type {
               type enumeration {
                 enum "enabled" {
                   description "Enable";
                 }
                 enum "disabled" {
                   description "Disable";
                 }
               }
             }
           }
           container log {
             presence "enable log";
             description "Choose the logging mechanism";
             uses apply-advanced;
             leaf log-options {
               type enumeration {
                 enum "disabled" {
                   description "Disable logging";
                 }
                 enum "syslog" {
                   description "Choose syslog";
                 }
               }
             }
           }
           container log-type {
             presence "enable log-type";
             description "Choose the logging mechanism";
             status deprecated;
             uses apply-advanced;
             leaf log {
               type enumeration {
                 enum "disabled" {
                   description "Disable logging";
                 }
                 enum "syslog" {
                   description "Choose syslog";
                 }
               }
             }
           }
           container max-passive-probe-limit {
             presence "enable max-passive-probe-limit";
             description "Set max passive probe limits";
             uses apply-advanced;
             container number-of-probes {
               presence "enable number-of-probes";
               description "Number of passive probes to be sent";
               uses apply-advanced;
               leaf probes {
                 description "Number of probes";
                 default "5000";
                 type union {
                   type string {
                     pattern "<.*>|$.*";
                   }
                   type uint32 {
                     range "10 .. 5000";
                   }
                 }
               }
             }
             container interval {
               presence "enable interval";
               description "Interval within which to send";
               uses apply-advanced;
               leaf refresh-interval {
                 description "Interval in milli seconds";
                 default "500";
                 type union {
                   type string {
                     pattern "<.*>|$.*";
                   }
                   type uint32 {
                     range "500 .. 1000";
                   }
                 }
               }
             }
           }
           leaf dynamic-load-balancer {
             description "Enable dynamic load balancer";
             type empty;
           }
         }
         list sla-rule {
           key name;
           ordered-by user;
           description "Create SLA rule";
           leaf name {
             description "Set rule name";
             type string {
               length "1 .. 63";
             }
           }
           uses apply-advanced;
           container link-preferences {
             presence "enable link-preferences";
             description "Configure the link preferences";
             uses apply-advanced;
             leaf preferred-tag {
               description "Configure the link-tag preference";
               type string {
                 length "1 .. 63";
               }
             }
             leaf affinity {
               description "Configure the link-tag affinity";
               type enumeration {
                 enum "strict" {
                   description "Strict link-tag affinity";
                 }
               }
             }
           }
           leaf preferred-link-type {
             description "Configure the link-type preference";
             status deprecated;
             type enumeration {
               enum "IP" {
                 description "IP link-type preference";
                 status deprecated;
               }
               enum "MPLS" {
                 description "MPLS link-type preference";
                 status deprecated;
               }
               enum "Any" {
                 description "Any link-type preference";
                 status deprecated;
               }
             }
           }
           leaf link-type-affinity {
             description "Configure the link-type affinity";
             status deprecated;
             type enumeration {
               enum "strict" {
                 description "Strict link-type affinity";
                 status deprecated;
               }
             }
           }
           container switch-idle-time {
             presence "enable switch-idle-time";
             description "Idle timeout period where no SLA violation will be detected once path switch has happened";
             uses apply-advanced;
             leaf timeout {
               description "Idle timeout period (in seconds)";
               default "60";
               type union {
                 type string {
                   pattern "<.*>|$.*";
                 }
                 type uint32 {
                   range "5 .. 300";
                 }
               }
             }
           }
           container metrics-profile {
             presence "enable metrics-profile";
             description "Set metrics profile for the SLA";
             uses apply-advanced;
             leaf metrics-profile-name {
               description "Metrics Profile name";
               type string;
             }
           }
           container active-probe-params {
             presence "enable active-probe-params";
             description "Set Probe params for the overlay-path";
             uses apply-advanced;
             leaf probe-params-name {
               description "Probe parameter's name";
               type string;
             }
           }
           leaf type {
             description "Choose type of SLA";
             type enumeration {
               enum "saas" {
                 description "Choose SaaS probing for the SLA";
               }
             }
           }
           container passive-probe-params {
             presence "enable passive-probe-params";
             description "Passive probe settings";
             uses apply-advanced;
             container sampling-percentage {
               presence "enable sampling-percentage";
               description "Mininmum percentage of Sessions to be evaluated for the application";
               uses apply-advanced;
               leaf percentage {
                 description "Percentage";
                 default "5";
                 type union {
                   type string {
                     pattern "<.*>|$.*";
                   }
                   type uint32 {
                     range "1 .. 100";
                   }
                 }
               }
             }
             container violation-count {
               presence "enable violation-count";
               description "Number of SLA violations within sampling period to be considered as a violation";
               status deprecated;
               uses apply-advanced;
               leaf count {
                 description "Violation Count";
                 default "5";
                 type union {
                   type string {
                     pattern "<.*>|$.*";
                   }
                   type uint32 {
                     range "1 .. 32";
                   }
                 }
               }
             }
             container sampling-period {
               presence "enable sampling-period";
               description "Time period in which the sampling is done";
               uses apply-advanced;
               leaf period {
                 description "Period (in milli-sec)";
                 default "5000";
                 type union {
                   type string {
                     pattern "<.*>|$.*";
                   }
                   type uint32 {
                     range "2000 .. 60000";
                   }
                 }
               }
             }
             container sla-export-factor {
               presence "enable sla-export-factor";
               description "Enabled sampling window based SLA exporting";
               uses apply-advanced;
               leaf factor {
                 description "No of sampling windows after which to report";
                 default "500";
                 type union {
                   type string {
                     pattern "<.*>|$.*";
                   }
                   type uint32 {
                     range "5 .. 1000";
                   }
                 }
               }
             }
             container type {
               presence "enable type";
               description "Choose type of SLA measurement";
               uses apply-advanced;
               leaf type-val {
                 type enumeration {
                   enum "book-ended" {
                     description "Choose custom method of probing within WAN link";
                   }
                 }
               }
             }
             container sampling-frequency {
               presence "enable sampling-frequency";
               description "Sampling frequency settings";
               uses apply-advanced;
               container interval {
                 presence "enable interval";
                 description "Time based sampling interval";
                 uses apply-advanced;
                 leaf sampling-interval {
                   description "Interval in milli seconds";
                   default "100";
                   type union {
                     type string {
                       pattern "<.*>|$.*";
                     }
                     type uint32 {
                       range "0 .. 500";
                     }
                   }
                 }
               }
               container ratio {
                 presence "enable ratio";
                 description "1:N based sampling ratio";
                 uses apply-advanced;
                 leaf sampling-ratio {
                   description "Value of N";
                   default "200";
                   type union {
                     type string {
                       pattern "<.*>|$.*";
                     }
                     type uint32 {
                       range "0 .. 10000";
                     }
                   }
                 }
               }
             }
           }
           container multipath-rule {
             description "Set AppBased Multipath Routing action";
             uses apply-advanced;
             leaf multipath-rule-name {
               description "Multipath action parameter's name";
               type string;
             }
           }
           container violation-count {
             presence "enable violation-count";
             description "Number of SLA violations within sampling period to be considered as a violation";
             uses apply-advanced;
             leaf count {
               description "Violation Count";
               default "5";
               type union {
                 type string {
                   pattern "<.*>|$.*";
                 }
                 type uint32 {
                   range "1 .. 32";
                 }
               }
             }
           }
         }
         list multipath-rule {
           key name;
           ordered-by user;
           description "APP based MULTIPATH Route Action's settings";
           leaf name {
             description "Multipath rule name";
             type string {
               length "1 .. 63";
             }
           }
           uses apply-advanced;
           leaf number-of-paths {
             description "No. of Paths in Multipath";
             default "2";
             type union {
               type string {
                 pattern "<.*>|$.*";
               }
               type uint32 {
                 range "2 .. 16";
               }
             }
           }
           leaf bandwidth-limit {
             description "Bandwidth limit (bps) on slowest link to avoid saturation (%)";
             default "50";
             type union {
               type string {
                 pattern "<.*>|$.*";
               }
               type uint32 {
                 range "1 .. 100";
               }
             }
           }
           leaf enable-reverse-wing {
             description "Packet copy enabled in reverse direction flow";
             type empty;
           }
           leaf-list application {
             ordered-by user;
             type string;
           }
           leaf-list application-group {
             ordered-by user;
             description "Specify dynamic application group name to match";
             type string;
           }
           leaf-list link-type {
             ordered-by user;
             description "List of underlay interface user defined link types";
             type string {
               length "1 .. 63";
             }
           }
           leaf-list link-preferences {
             ordered-by user;
             description "List of interface for link preferences";
             type union {
               type jt:interface-name;
               type string {
                 pattern "<.*>|$.*";
               }
             }
           }
         }
         list policy {
           key name;
           ordered-by user;
           description "Define a policy context from this zone";
           leaf name {
             description "Source zone";
             type string {
               length "1 .. 63";
             }
           }
           uses apply-advanced;
           list policy {
             key name;
             ordered-by user;
             description "Define security policy in specified zone-to-zone direction";
             uses sla_policy_type;
           }
         }
       }
       container gtp {
         description "GPRS tunneling protocol configuration";
         uses gtp-object;
       }
       container sctp {
         description "GPRS stream control transmission protocol configuration";
         presence "enable sctp";
         uses sctp-object;
       }
       container ngfw {
         description "Next generation unified L4/L7 firewall";
         uses apply-advanced;
         container default-profile {
           description "Unified L4/L7 firewall default profile configuration";
           uses apply-advanced;
           container ssl-proxy {
             presence "enable ssl-proxy";
             description "SSL proxy services";
             uses apply-advanced;
             leaf profile-name {
               description "Specify SSL proxy service profile name";
               type string;
             }
           }
           container application-traffic-control {
             description "Application traffic control services";
             uses jsf_application_traffic_control_rule_set_type;
           }
         }
       }
       container tunnel-inspection {
         presence "enable tunnel-inspection";
         description "Security tunnel-inspection";
         uses apply-advanced;
         list inspection-profile {
           key name;
           ordered-by user;
           description "Security tunnel-inspection profile";
           max-elements 256;
           uses tunnel-inspection-profile-type;
         }
         list vni {
           key name;
           ordered-by user;
           description "Security tunnel inspection vni";
           max-elements 4096;
           uses tunnel-inspection-vni-type;
         }
         container traceoptions {
           description "Trace options for Network Security tunnel-inspection";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container l3vpn {
         presence "enable l3vpn";
         uses apply-advanced;
         container traceoptions {
           description "Trace options for Network Security Vrf-group";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list vrf-group {
           key name;
           description "Configure vrf group";
           uses vrf-group-type;
         }
       }
       container cloud {
         presence "enable cloud";
         description "Configure Cloud security options";
         uses apply-advanced;
         container aws {
           description "Configure AWS security options";
           uses aws-object;
         }
         container high-availability {
           description "Configure AWS HA";
           uses ha-object;
         }
         container traceoptions {
           description "Configure cloudagent trace options";
           uses apply-advanced;
           container file {
             description "Trace file information";
             leaf filename {
               description "Name of file in which to write trace information";
               type string {
                 length "1 .. 64";
               }
             }
           }
           container level {
             description "Trace level";
             uses apply-advanced;
             choice level {
               case case_1 {
                 leaf error {
                   description "Error messages";
                   type empty;
                 }
               }
               case case_2 {
                 leaf brief {
                   description "Brief messages";
                   type empty;
                 }
               }
               case case_3 {
                 leaf detail {
                   description "Detail messages";
                   type empty;
                 }
               }
             }
           }
         }
       }
       container macsec {
         description "MAC Security configuration";
         uses security-macsec;
       }
     }
   }
   grouping alg-object {
     uses apply-advanced;
     container traceoptions {
       description "ALG trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Set level of tracing output";
         default "brief";
         type enumeration {
           enum "brief" {
             description "Brief messages";
           }
           enum "detail" {
             description "Detail messages";
           }
           enum "extensive" {
             description "Extensive messages";
           }
           enum "verbose" {
             description "Verbose messages";
           }
         }
       }
     }
     container alg-manager {
       description "Configure ALG-MANAGER";
       leaf clear-dont-frag-bit {
         description "Enable ALG clear DF(don't frag) bit in IP header";
         type empty;
       }
       container traceoptions {
         description "ALG-MANAGER trace options";
         uses apply-advanced;
         list flag {
           key name;
           ordered-by user;
           description "ALG-MANAGER trace flags";
           leaf name {
             type enumeration {
               enum "all" {
                 description "Trace everything";
               }
             }
           }
           choice level {
             case case_1 {
               leaf extensive {
                 description "Set trace verbosity level to extensive";
                 type empty;
               }
             }
           }
         }
       }
     }
     container alg-support-lib {
       description "Configure ALG-SUPPORT-LIB";
       container traceoptions {
         description "ALG-SUPPORT-LIB trace options";
         uses apply-advanced;
         list flag {
           key name;
           ordered-by user;
           description "ALG-SUPPORT-LIB trace flags";
           leaf name {
             type enumeration {
               enum "all" {
                 description "Trace everything";
               }
             }
           }
           choice level {
             case case_1 {
               leaf extensive {
                 description "Set trace verbosity level to extensive";
                 type empty;
               }
             }
           }
         }
       }
     }
     container dns {
       description "Configure DNS ALG";
       uses apply-advanced;
       leaf disable {
         description "Disable DNS ALG";
         type empty;
       }
       leaf maximum-message-length {
         description "Set maximum message length";
         default "512";
         units "bytes";
         type union {
           type string {
             pattern "<.*>|$.*";
           }
           type uint32 {
             range "512 .. 8192";
           }
         }
       }
       leaf oversize-message-drop {
         description "Drop oversized DNS packets";
         type empty;
       }
       container doctoring {
         description "Configure DNS ALG doctoring";
         uses apply-advanced;
         choice type {
           case case_1 {
             leaf none {
               description "Disable all DNS ALG Doctoring";
               type empty;
             }
           }
           case case_2 {
             leaf sanity-check {
               description "Perform only DNS ALG sanity checks";
               type empty;
             }
           }
         }
       }
       container traceoptions {
         description "DNS ALG trace options";
         uses apply-advanced;
         list flag {
           key name;
           ordered-by user;
           description "DNS ALG trace flags";
           leaf name {
             type enumeration {
               enum "all" {
                 description "Trace everything";
               }
             }
           }
           choice level {
             case case_1 {
               leaf extensive {
                 description "Set trace verbosity level to extensive";
                 type empty;
               }
             }
           }
         }
       }
     }
     container ftp {
       description "Configure FTP ALG";
       leaf disable {
         description "Disable FTP ALG";
         type empty;
       }
       leaf ftps-extension {
         description "Enable secure FTP and FTP-ssl protocols";
         type empty;
       }
       leaf line-break-extension {
         description "Enable CR+LF line termination";
         type empty;
       }
       leaf allow-mismatch-ip-address {
         description "Pass FTP packets with mismatched ip address headers and payload";
         type empty;
       }
       container traceoptions {
         description "FTP ALG trace options";
         uses apply-advanced;
         list flag {
           key name;
           ordered-by user;
           description "FTP ALG trace flags";
           leaf name {
             type enumeration {
               enum "all" {
                 description "Trace everything";
               }
             }
           }
           choice level {
             case case_1 {
               leaf extensive {
                 description "Set trace verbosity level to extensive";
                 type empty;
               }
             }
           }
         }
       }
     }
     container h323 {
       presence "enable h323";
       description "Configure H.323 ALG";
       uses apply-advanced;
       leaf disable {
         description "Disable H.323 ALG";
         type empty;
       }
       leaf endpoint-registration-timeout {
         description "Timeout for endpoints";
         default "64800";
         units "seconds";
         type union {
           type string {
             pattern "<.*>|$.*";
           }
           type uint32 {
             range "10 .. 65535";
           }
         }
       }
       leaf media-source-port-any {
         description "Permit media from any source port on the endpoint";
         type empty;
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Configure Message flood ALG options";
           uses apply-advanced;
           container gatekeeper {
             description "Set options for gatekeeper messages";
             leaf threshold {
               description "Message flood gatekeeper threshold";
               default "1000";
               units "messages per second";
               type union {
                 type string {
                   pattern "<.*>|$.*";
                 }
                 type uint32 {
                   range "1 .. 50000";
                 }
               }
             }
           }
         }
       }
       container dscp-rewrite {
         description "DSCP code rewrite";
         uses apply-advanced;
         leaf code-point {
           description "Set dscp codepoint 6-bit string";
           type string {
           }
         }
       }
       container traceoptions {
         description "H.323 ALG trace options";
         uses apply-advanced;
         list flag {
           key name;
           ordered-by user;
           description "H.323 ALG trace flags";
           leaf name {
             type enumeration {
               enum "q931" {
                 description "Enable tracing for Q.931 processing";
               }
               enum "h245" {
                 description "Enable tracing for H.245 processing";
               }
               enum "ras" {
                 description "Enable tracing for RAS processing";
               }
               enum "h225-asn1" {
                 description "Enable tracing for H.225 ASN.1 processing";
               }
               enum "h245-asn1" {
                 description "Enable tracing for H.245 ASN.1 processing";
               }
               enum "ras-asn1" {
                 description "Enable tracing for RAS ASN.1 processing";
               }
               enum "chassis-cluster" {
                 description "Enable tracing for H.323 chassis cluster functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container mgcp {
       presence "enable mgcp";
       description "Configure MGCP ALG";
       uses apply-advanced;
       leaf disable {
         description "Disable MGCP ALG";
         type empty;
       }
       leaf inactive-media-timeout {
         description "Set inactive media timeout";
         default "120";
         units "seconds";
         type union {
           type string {
             pattern "<.*>|$.*";
           }
           type uint32 {
             range "10 .. 2550";
           }
         }
       }
       leaf transaction-timeout {
         description "Set transaction timeout";
         default "30";
         units "seconds";
         type union {
           type string {
             pattern "<.*>|$.*";
           }
           type uint32 {
             range "3 .. 50";
           }
         }
       }
       leaf maximum-call-duration {
         description "Set maximum call duration";
         default "720";
         units "minutes";
         type union {
           type string {
             pattern "<.*>|$.*";
           }
           type uint32 {
             range "3 .. 720";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container message-flood {
           description "Set message flood ALG options";
           leaf threshold {
             description "Message flood threshold";
             default "100";
             units "messages per second per MG";
             type union {
               type string {
                 pattern "<.*>|$.*";
               }
               type uint32 {
                 range "2 .. 50000";
               }
             }
           }
         }
         container connection-flood {
           description "Set connection flood options";
           leaf threshold {
             description "Connection flood threshold";
             default "10";
             units "connection requests per second per MG";
             type union {
               type string {
                 pattern "<.*>|$.*";
               }
               type uint32 {
                 range "2 .. 10000";
               }
             }
           }
         }
       }
       container dscp-rewrite {
         description "DSCP code rewrite";
         uses apply-advanced;
         leaf code-point {
           description "Set dscp codepoint 6-bit string";
           type string {
           }
         }
       }
       container traceoptions {
         description "MGCP ALG trace options";
         uses apply-advanced;
         list flag {
           key name;
           ordered-by user;
           description "MGCP ALG trace flags";
           leaf name {
             type enumeration {
               enum "call" {
                 description "Enable tracing for MGCP call processing";
               }
               enum "decode" {
                 description "Enable tracing for MGCP decoder operations";
               }
               enum "error" {
                 description "Enable tracing for MGCP processing errors";
               }
               enum "chassis-cluster" {
                 description "Enable tracing for MGCP chassis cluster functions";
               }
               enum "nat" {
                 description "Enable tracing for MGCP Network Address Translation (NAT) processing";
               }
               enum "packet" {
                 description "Enable tracing for MGCP protocol packet processing";
               }
               enum "rm" {
                 description "Enable tracing MGCP Resource Management (Resmgr) functions";
               }
               enum "all" {
                 description "Trace everything";
               }
             }
           }
           choice level {
             case case_1 {
               leaf extensive {
                 description "Set trace verbosity level to extensive";
                 type empty;
               }
             }
           }
         }
       }
     }
     container msrpc {
       description "Configure MSRPC ALG";
       leaf disable {
         description "Disable MSRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "MSRPC ALG trace options";
         uses apply-advanced;
         list flag {
           key name;
           ordered-by user;
           description "MSRPC ALG trace flags";
           leaf name {
             type enumeration {
               enum "all" {
                 description "Trace everything";
               }
             }
           }
           choice level {
             case case_1 {
               leaf extensive {
                 description "Set trace verbosity level to extensive";
                 type empty;
               }
             }
           }
         }
       }
     }
     container sunrpc {
       description "Configure SUNRPC ALG";
       leaf disable {
         description "Disable SUNRPC ALG";
         type empty;
       }
       leaf group-max-usage {
         description "Set maximum group usage percentage, default 80";
         default "80";
         type union {
           type string {
             pattern "<.*>|$.*";
           }
           type uint32 {
             range "10 .. 100";
           }
         }
       }
       leaf map-entry-timeout {
         description "Set entry timeout, default 8hour";
         default "480";
         units "minutes";
         type union {
           type string {
             pattern "<.*>|$.*";
           }
           type uint32 {
             range "5 .. 4320";
           }
         }
       }
       container traceoptions {
         description "SUNRPC ALG trace options";
         uses apply-advanced;
         list flag {
           key name;
           ordered-by user;
           description "SUNRPC ALG trace flags";
           leaf name {
             type enumeration {
               enum "all" {
                 description "Trace everything";
               }
             }
           }
           choice level {
             case case_1 {
               leaf extensive {
                 description "Set trace verbosity level to extensive";
                 type empty;
               }
             }
           }
         }
       }
     }
     container rsh {
       presence "enable rsh";
       description "Configure RSH ALG";
       uses apply-advanced;
       leaf disable {
         description "Disable RSH ALG";
         type empty;
       }
       container traceoptions {
         description "RSH ALG trace options";
         uses apply-advanced;
         list flag {
           key name;
           ordered-by user;
           description "RSH ALG trace flags";
           leaf name {
             type enumeration {
               enum "all" {
                 description "Trace everything";
               }
             }
           }
           choice level {
             case case_1 {
               leaf extensive {
                 description "Set trace verbosity level to extensive";
                 type empty;
               }
             }
           }
         }
       }
     }
     container rtsp {
       presence "enable rtsp";
       description "Configure RTSP ALG";
       leaf disable {
         description "Disable RTSP ALG";
         type empty;
       }
       container traceoptions {
         description "RTSP ALG trace options";
         uses apply-advanced;
         list flag {
           key name;
           ordered-by user;
           description "RTSP ALG trace flags";
           leaf name {
             type enumeration {
               enum "all" {
                 description "Trace everything";
               }
             }
           }
           choice level {
             case case_1 {
               leaf extensive {
                 description "Set trace verbosity level to extensive";
                 type empty;
               }
             }
           }
         }
       }
     }
     container sccp {
       presence "enable sccp";
       description "Configure SCCP ALG";
       uses apply-advanced;
       leaf disable {
         description "Disable SCCP ALG";
         type empty;
       }
       leaf inactive-media-timeout {
         description "Set inactive media timeout";
         default "120";
         units "seconds";
         type union {
           type string {
             pattern "<.*>|$.*";
           }
           type uint32 {
             range "10 .. 600";
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container call-flood {
           description "Configure call flood thresholds";
           leaf threshold {
             description "Calls per second per client";
             default "20";
             type union {
               type string {
                 pattern "<.*>|$.*";
               }
               type uint32 {
                 range "2 .. 1000";
               }
             }
           }
         }
       }
       container dscp-rewrite {
         description "DSCP code rewrite";
         uses apply-advanced;
         leaf code-point {
           description "Set dscp codepoint 6-bit string";
           type string {
           }
         }
       }
       container traceoptions {
         description "SCCP ALG trace options";
         uses apply-advanced;
         list flag {
           key name;
           ordered-by user;
           description "SCCP ALG trace flags";
           leaf name {
             type enumeration {
               enum "call" {
                 description "Enable tracing SCCP call processing";
               }
               enum "cli" {
                 description "Enable tracing SCCP cli processing";
               }
               enum "decode" {
                 description "Enable tracing for SCCP decoder operations";
               }
               enum "error" {
                 description "Enable tracing for SCCP processing errors";
               }
               enum "chassis-cluster" {
                 description "Enable tracing for SCCP chassis cluster functions";
               }
               enum "init" {
                 description "Enable tracing for SCCP initialization errors";
               }
               enum "nat" {
                 description "Enable tracing for SCCP Network Address Translation (NAT) processing";
               }
               enum "rm" {
                 description "Enable tracing SCCP Resource Management (Resmgr) functions";
               }
               enum "all" {
                 description "Trace everything";
               }
             }
           }
           choice level {
             case case_1 {
               leaf extensive {
                 description "Set trace verbosity level to extensive";
                 type empty;
               }
             }
           }
         }
       }
     }
     container sip {
       presence "enable sip";
       description "Configure SIP ALG";
       uses apply-advanced;
       leaf disable {
         description "Disable SIP ALG";
         type empty;
       }
       leaf inactive-media-timeout {
         description "Set inactive media timeout";
         default "120";
         units "seconds";
         type union {
           type string {
             pattern "<.*>|$.*";
           }
           type uint16 {
             range "10 .. 2550";
           }
         }
       }
       leaf maximum-call-duration {
         description "Set maximum call duration 0 or 3..720";
         default "720";
         units "minutes";
         type union {
           type uint32;
           type string {
             pattern "<.*>|$.*";
           }
         }
       }
       leaf t1-interval {
         description "Set T1 interval";
         default "500";
         units "milliseconds";
         type union {
           type string {
             pattern "<.*>|$.*";
           }
           type uint32 {
             range "500 .. 5000";
           }
         }
       }
       leaf t4-interval {
         description "Set T4 interval";
         default "5";
         units "seconds";
         type union {
           type string {
             pattern "<.*>|$.*";
           }
           type uint32 {
             range "5 .. 10";
           }
         }
       }
       leaf c-timeout {
         description "Set C timeout";
         default "3";
         units "minutes";
         type union {
           type string {
             pattern "<.*>|$.*";
           }
           type uint32 {
             range "3 .. 10";
           }
         }
       }
       leaf disable-call-id-hiding {
         description "Disable translation of host IP in Call-ID header";
         status deprecated;
         type empty;
       }
       leaf bulk-call-mode {
         description "Enable SIP distribution session in bulk mode";
         type empty;
       }
       leaf enable-call-distribution {
         description "Enable Call-id-based SIP call distribution between SPUs";
         type empty;
       }
       leaf retain-hold-resource {
         description "Retain SDP resources during call hold";
         type empty;
       }
       container hide-via-headers {
         description "Hide via headers options";
         uses apply-advanced;
         leaf disable {
           description "Disable hide via headers function";
           type empty;
         }
       }
       list distribution-ip {
         key name;
         ordered-by user;
         description "Configure SIP distribute server IPV6 or IPV4 ip";
         leaf name {
           description "Distribution IP address";
           type jt:ipaddr;
         }
         uses apply-advanced;
         container distribute-to {
           description "Distribute sip packet";
           uses apply-advanced;
           container fpc {
             description "FPC card number";
             uses apply-advanced;
             leaf slot {
               description "FPC slot number";
               type union {
                 type string {
                   pattern "<.*>|$.*";
                 }
                 type uint32 {
                   range "0 .. 127";
                 }
               }
             }
             container pic {
               description "PIC card number";
               uses apply-advanced;
               leaf slot {
                 description "Physical Interface Card number";
                 type union {
                   type string {
                     pattern "<.*>|$.*";
                   }
                   type uint32 {
                     range "0 .. 11";
                   }
                 }
               }
             }
           }
         }
       }
       container application-screen {
         description "Configure application screens";
         uses apply-advanced;
         container unknown-message {
           description "Configure ALG action on receiving an unknown message";
           uses apply-advanced;
           leaf permit-nat-applied {
             description "Permit unknown messages on packets that are NATed";
             type empty;
           }
           leaf permit-routed {
             description "Permit unknown messages on routed packets";
             type empty;
           }
         }
         container protect {
           description "Configure Protect options";
           uses apply-advanced;
           container deny {
             presence "enable deny";
             description "Protect deny options";
             uses apply-advanced;
             choice deny-choice {
               case case_1 {
                 list destination-ip {
                   key name;
                   ordered-by user;
                   description "List of protected destination server IP";
                   leaf name {
                     description "Protected destination server IPv4 or IPv6 entry";
                     type jt:ipprefix;
                   }
                   uses apply-advanced;
                 }
               }
               case case_2 {
                 leaf all {
                   description "Enable attack protection for all servers";
                   type empty;
                 }
               }
             }
             leaf timeout {
               description "Timeout value for SIP INVITE attack table entry";
               default "5";
               units "seconds";
               type union {
                 type string {
                   pattern "<.*>|$.*";
                 }
                 type uint32 {
                   range "1 .. 3600";
                 }
               }
             }
           }
         }
       }
       container dscp-rewrite {
         description "DSCP code rewrite";
         uses apply-advanced;
         leaf code-point {
           description "Set dscp codepoint 6-bit string";
           type string {
           }
         }
       }
       container traceoptions {
         description "SIP ALG trace options";
         uses apply-advanced;
         list flag {
           key name;
           ordered-by user;
           description "SIP ALG trace flags";
           leaf name {
             type enumeration {
               enum "call" {
                 description "Enable tracing for SIP call processing";
               }
               enum "chassis-cluster" {
                 description "Enable tracing for SIP chassis cluster functions";
               }
               enum "nat" {
                 description "Enable tracing for SIP Network Address Translation (NAT) processing";
               }
               enum "parser" {
                 description "Enable tracing for SIP parser operations";
               }
               enum "rm" {
                 description "Enable tracing SIP Resource Management (Resmgr) functions";
               }
               enum "all" {
                 description "Trace everything";
               }
             }
           }
           choice level {
             case case_1 {
               leaf terse {
                 description "Set trace verbosity level to terse";
                 type empty;
               }
             }
             case case_2 {
               leaf detail {
                 description "Set trace verbosity level to detail";
                 type empty;
               }
             }
             case case_3 {
               leaf extensive {
                 description "Set trace verbosity level to extensive";
                 type empty;
               }
             }
           }
         }
       }
     }
     container sql {
       presence "enable sql";
       description "Configure SQL ALG";
       leaf disable {
         description "Disable SQL ALG";
         type empty;
       }
       container traceoptions {
         description "SQL ALG trace options";
         uses apply-advanced;
         list flag {
           key name;
           ordered-by user;
           description "SQL ALG trace flags";
           leaf name {
             type enumeration {
               enum "all" {
                 description "Trace everything";
               }
             }
           }
           choice level {
             case case_1 {
               leaf extensive {
                 description "Set trace verbosity level to extensive";
                 type empty;
               }
             }
           }
         }
       }
     }
     container talk {
       description "Configure Talk ALG";
       leaf disable {
         description "Disable Talk ALG";
         type empty;
       }
       container traceoptions {
         description "TALK ALG trace options";
         uses apply-advanced;
         list flag {
           key name;
           ordered-by user;
           description "TALK ALG trace flags";
           leaf name {
             type enumeration {
               enum "all" {
                 description "Trace everything";
               }
             }
           }
           choice level {
             case case_1 {
               leaf extensive {
                 description "Set trace verbosity level to extensive";
                 type empty;
               }
             }
           }
         }
       }
     }
     container tftp {
       description "Configure TFTP ALG";
       leaf disable {
         description "Disable TFTP ALG";
         type empty;
       }
       container traceoptions {
         description "TFTP ALG trace options";
         uses apply-advanced;
         list flag {
           key name;
           ordered-by user;
           description "TFTP ALG trace flags";
           leaf name {
             type enumeration {
               enum "all" {
                 description "Trace everything";
               }
             }
           }
           choice level {
             case case_1 {
               leaf extensive {
                 description "Set trace verbosity level to extensive";
                 type empty;
               }
             }
           }
         }
       }
     }
     container pptp {
       description "Configure PPTP ALG";
       leaf disable {
         description "Disable PPTP ALG";
         type empty;
       }
       container traceoptions {
         description "PPTP ALG trace options";
         uses apply-advanced;
         list flag {
           key name;
           ordered-by user;
           description "PPTP ALG trace flags";
           leaf name {
             type enumeration {
               enum "all" {
                 description "Trace everything";
               }
             }
           }
           choice level {
             case case_1 {
               leaf extensive {
                 description "Set trace verbosity level to extensive";
                 type empty;
               }
             }
           }
         }
       }
     }
     container ike-esp-nat {
       description "Configure IKE-ESP ALG with NAT";
       uses apply-advanced;
       leaf enable {
         description "Enable IKE-ESP ALG";
         type empty;
       }
       leaf esp-gate-timeout {
         description "Set ESP gate timeout";
         default "5";
         units "seconds";
         type union {
           type string {
             pattern "<.*>|$.*";
           }
           type uint32 {
             range "2 .. 30";
           }
         }
       }
       leaf esp-session-timeout {
         description "Set ESP session timeout";
         default "1800";
         units "seconds";
         type union {
           type string {
             pattern "<.*>|$.*";
           }
           type uint32 {
             range "60 .. 2400";
           }
         }
       }
       leaf state-timeout {
         description "Set ALG state timeout";
         default "14400";
         units "seconds";
         type union {
           type string {
             pattern "<.*>|$.*";
           }
           type uint32 {
             range "180 .. 86400";
           }
         }
       }
       container traceoptions {
         description "IKE-ESP ALG trace options";
         uses apply-advanced;
         list flag {
           key name;
           ordered-by user;
           description "IKE-ESP ALG trace flags";
           leaf name {
             type enumeration {
               enum "all" {
                 description "Trace everything";
               }
             }
           }
           choice level {
             case case_1 {
               leaf extensive {
                 description "Set trace verbosity level to extensive";
                 type empty;
               }
             }
           }
         }
       }
     }
     container twamp {
       presence "enable twamp";
       description "Configure TWAMP ALG";
       uses apply-advanced;
       container traceoptions {
         description "TWAMP ALG trace options";
         uses apply-advanced;
         list flag {
           key name;
           ordered-by user;
           description "TWAMP ALG trace flags";
           leaf name {
             type enumeration {
               enum "all" {
                 description "Trace everything";
               }
             }
           }
           choice level {
             case case_1 {
               leaf extensive {
                 description "Trace verbosity level to extensive";
                 type empty;
               }
             }
           }
         }
       }
     }
   }
   grouping anti-spam-feature {
     description "Anti-spam feature";
     uses apply-advanced;
     container sbl {
       description "SBL settings";
       presence "enable sbl";
       uses sbl-type;
     }
   }
   grouping anti-virus-feature {
     description "Anti-virus feature";
     uses apply-advanced;
     container mime-whitelist {
       description "Anti-virus MIME whitelist";
       status deprecated;
       uses apply-advanced;
       leaf list {
         description "MIME list";
         type string;
       }
       leaf exception {
         description "Exception settings for MIME white list";
         type string;
       }
     }
     leaf url-whitelist {
       description "Anti-virus URL white list";
       status deprecated;
       type string;
     }
     leaf type {
       description "Anti-virus engine type";
       status deprecated;
       type enumeration {
         enum "sophos-engine" {
           description "Anti-virus sophos-engine";
           status deprecated;
         }
         enum "avira-engine" {
           description "Anti-virus avira-engine";
           status deprecated;
         }
         enum "anti-virus-none" {
           status deprecated;
         }
       }
     }
     list profile {
       key name;
       ordered-by user;
       description "Anti-virus profile";
       leaf name {
         description "Anti-virus profile name";
         type string {
           length "1 .. 29";
         }
       }
       uses apply-advanced;
       container fallback-options {
         description "Anti-virus fallback options";
         presence "enable fallback-options";
         uses av-fallback-settings;
       }
       container notification-options {
         description "Anti-virus notification options";
         presence "enable notification-options";
         uses anti-virus-notification-options;
       }
       container mime-whitelist {
         description "Anti-virus MIME whitelist";
         uses apply-advanced;
         leaf list {
           description "MIME list";
           type string;
         }
         leaf exception {
           description "Exception settings for MIME white list";
           type string;
         }
       }
       leaf url-whitelist {
         description "Anti-virus URL white list";
         type string;
       }
     }
     container traceoptions {
       description "Trace options for anti-virus feature";
       status deprecated;
       uses anti-virus-traceoptions;
     }
     container sophos-engine {
       description "Anti-virus sophos-engine";
       status deprecated;
       uses apply-advanced;
       container server {
         description "SAV and Anti-Spam first hop DNS server";
         status deprecated;
         uses apply-advanced;
         leaf ip {
           description "SAV and Anti-Spam first hop DNS server ip";
           type jt:ipaddr;
         }
         leaf routing-instance {
           description "Routing instance name";
           type string;
         }
         leaf source-address {
           description "Source ip address used to connect server";
           type jt:ipaddr;
         }
       }
       leaf sxl-timeout {
         description "Sxl sophos anti-virus engine timeout";
         status deprecated;
         units "seconds";
         type union {
           type string {
             pattern "<.*>|$.*";
           }
           type uint32 {
             range "1 .. 5";
           }
         }
       }
       leaf sxl-retry {
         description "Sxl sophos anti-virus engine query retry (number of times)";
         status deprecated;
         type union {
           type string {
             pattern "<.*>|$.*";
           }
           type uint32 {
             range "0 .. 5";
           }
         }
       }
       container pattern-update {
         description "Anti-virus sophos-engine pattern update";
         presence "enable pattern-update";
         status deprecated;
         uses anti-virus-pattern-update;
       }
       list profile {
         key name;
         ordered-by user;
         description "Anti-virus sophos-engine profile";
         status deprecated;
         leaf name {
           description "Anti-virus sophos-engine profile name";
           type string {
             length "1 .. 29";
           }
         }
         uses apply-advanced;
         container fallback-options {
           description "Anti-virus sophos-engine fallback options";
           presence "enable fallback-options";
           uses av-fallback-settings;
         }
         container scan-options {
           description "Anti-virus sophos-engine scan options";
           presence "enable scan-options";
           uses sophos-scan-options;
         }
         container trickling {
           description "Anti-virus trickling";
           presence "enable trickling";
           uses anti-virus-trickling;
         }
         container notification-options {
           description "Anti-virus notification options";
           presence "enable notification-options";
           uses anti-virus-notification-options;
         }
         container mime-whitelist {
           description "Anti-virus MIME whitelist";
           uses apply-advanced;
           leaf list {
             description "MIME list";
             type string;
           }
           leaf exception {
             description "Exception settings for MIME white list";
             type string;
           }
         }
         leaf url-whitelist {
           description "Anti-virus URL white list";
           type string;
         }
       }
     }
   }
   grouping anti-virus-notification-options {
     description "Anti-virus notification options";
     uses apply-advanced;
     container virus-detection {
       presence "enable virus-detection";
       description "Virus detection notification";
       uses apply-advanced;
       leaf type {
         description "Virus detection notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-block {
       presence "enable fallback-block";
       description "Fallback block notification";
       uses apply-advanced;
       leaf type {
         description "Fallback block notification type";
         type enumeration {
           enum "protocol-only" {
             description "Notification in protocol level only";
           }
           enum "message" {
             description "Notification in message";
           }
         }
       }
       choice notify-mail-sender-choice {
         leaf notify-mail-sender {
           description "Notify mail sender";
           type empty;
         }
         leaf no-notify-mail-sender {
           description "Don't notify mail sender";
           type empty;
         }
       }
       leaf custom-message {
         description "Custom message for notification";
         type string {
           length "1 .. 512";
         }
       }
       leaf custom-message-subject {
         description "Custom message subject for notification";
         type string {
           length "1 .. 255";
         }
       }
     }
     container fallback-non-block {
       presence "enable fallback-non-block";
       description "Fallback non block notification";
       uses apply-advanced;
       choice notify-mail-recipient-choice {
         leaf notify-mail-recipient {
           description "Notify mail recipient";
           type empty;
         }
         leaf no-notify-mail-recipient {
           description "Don't notify mail recipient";
           type empty;
         }
       }
       leaf custom-message {
         description "Custom message for notification";
         type string {
           length "1 .. 512";
         }
       }
       leaf custom-message-subject {
         description "Custom message subject for notification";
         type string {
           length "1 .. 255";
         }
       }
     }
   }
   grouping anti-virus-pattern-update {
     description "Anti-virus pattern update";
     uses apply-advanced;
     container email-notify {
       presence "enable email-notify";
       description "Virus pattern file updated notification";
       uses apply-advanced;
       leaf admin-email {
         description "Admin emails to be notified about pattern file update";
         type string {
           length "1 .. 255";
         }
       }
       leaf custom-message {
         description "Custom message for notification";
         type string {
           length "1 .. 512";
         }
       }
       leaf custom-message-subject {
         description "Custom message subject for notification";
         type string {
           length "1 .. 255";
         }
       }
     }
     leaf url {
       description "Server URL";
       type string {
         length "1 .. 256";
       }
     }
     leaf proxy-profile {
       description "Proxy profile";
       type string {
         length "1 .. 64";
       }
     }
     leaf routing-instance {
       description "Routing instance name";
       type string;
     }
     leaf interval {
       description "Interval in minutes to check the update";
       type union {
         type string {
           pattern "<.*>|$.*";
         }
         type uint32 {
           range "10 .. 10080";
         }
       }
     }
     leaf start-time {
       description "Start time (YYYY-MM-DD.HH:MM:SS)";
       type jt:time;
     }
     leaf no-autoupdate {
       description "Don't automatically update anti-virus pattern";
       type empty;
     }
   }
   grouping anti-virus-traceoptions {
     description "Trace options for anti-virus feature";
     uses apply-advanced;
     list flag {
       key name;
       ordered-by user;
       description "Trace options for anti-virus feature flag";
       leaf name {
         description "Trace options for anti-virus feature flag name";
         type enumeration {
           enum "basic" {
             description "Trace anti-virus module generic basic information";
           }
           enum "detail" {
             description "Trace anti-virus module generic detail information";
           }
           enum "engine" {
             description "Trace scan engine information";
           }
           enum "pattern" {
             description "Trace detail information of pattern loading";
           }
           enum "updater" {
             description "Trace pattern updater process activities";
           }
           enum "manager" {
             description "Trace anti-virus manager process activities";
           }
           enum "worker" {
             description "Trace anti-virus worker process activities";
           }
           enum "sendmail" {
             description "Trace mail notifier process activities";
           }
           enum "ipc" {
             description "Trace communication events with PFE";
           }
           enum "event" {
             description "Trace communication events between RE side processes";
           }
           enum "statistics" {
             description "Trace statistics information";
           }
           enum "all" {
             description "Enable trace all anti-virus trace options";
           }
         }
       }
     }
   }
   grouping anti-virus-trickling {
     description "Anti-virus trickling";
     leaf timeout {
       description "Trickling timeout";
       type union {
         type string {
           pattern "<.*>|$.*";
         }
         type uint32 {
           range "0 .. 600";
         }
       }
     }
   }
   grouping apbr_rule_type {
     leaf name {
       description "Rule name";
       type string {
         length "1 .. 63";
       }
     }
     uses apply-advanced;
     leaf disable-midstream-routing {
       description "Disable midstream routing";
       type empty;
     }
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf-list category {
         ordered-by user;
         description "Url category";
         type string;
       }
       leaf-list dscp {
         ordered-by user;
         description "Specify dscp value to match";
         type union {
           type string {
             pattern "<.*>|$.*";
           }
           type int32 {
             range "0 .. 63";
           }
         }
       }
     }
     container then {
       presence "enable then";
       description "Specify rule action to take when packet match criteria";
       uses apply-advanced;
       container routing-instance {
         description "Packets are directed to specified routing instance";
         leaf routing-instance-name {
           description "Name of routing instance";
           type string {
           }
         }
       }
       container sla-rule {
         presence "enable sla-rule";
         description "SLA Rule";
         uses apply-advanced;
         leaf sla-rule-name {
           description "SLA rule name";
           type string;
         }
       }
       leaf application-services-bypass {
         description "Bypass the application services";
         type empty;
       }
     }
   }
   grouping appfw_rule_type {
     leaf name {
       description "Rule name";
       type string {
         length "1 .. 63";
       }
     }
     uses apply-advanced;
     container match {
       presence "enable match";
       description "Specify security rule  match-criteria";
       uses apply-advanced;
       leaf-list dynamic-application {
         ordered-by user;
         type string;
       }
       leaf-list dynamic-application-group {
         ordered-by user;
         description "Specify dynamic application group name to match";
         type string;
       }
       leaf ssl-encryption {
         description "Select SSL encryption rules";
         type enumeration {
           enum "any" {
             description "Encrypted and non-encrypted rule";
           }
           enum "yes" {
             description "Encrypted rule";
           }
           enum "no" {
             description "Non-encrypted rule";
           }
         }
       }
     }
     container then {
       presence "enable then";
       description "Specify rule action to take when packet match criteria";
       uses apply-advanced;
       choice action {
         case case_1 {
           leaf permit {
             description "Permit packets";
             type empty;
           }
         }
         case case_2 {
           container deny {
             presence "enable deny";
             description "Deny packets";
             uses apply-advanced;
             leaf block-message {
               description "Redirect sessions";
               type empty;
             }
           }
         }
         case case_3 {
           container reject {
             presence "enable reject";
             description "Reject packets";
             uses apply-advanced;
             leaf block-message {
               description "Redirect sessions";
               type empty;
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping appqoe-probe-params {
     description "Active probe parameters";
     uses apply-advanced;
     container data-fill {
       description "Probe Data Payload content";
       uses apply-advanced;
       leaf fill {
         description "Repetitive payload string ";
         type string {
           length "1 .. 63";
         }
       }
     }
     container data-size {
       presence "enable data-size";
       description "Probe data size";
       uses apply-advanced;
       leaf size {
         description "Data Payload size of probe packet";
         type union {
           type string {
             pattern "<.*>|$.*";
           }
           type uint32 {
             range "4 .. 256";
           }
         }
       }
     }
     container per-packet-loss-timeout {
       presence "enable per-packet-loss-timeout";
       description "Time interval between 2 consecutive SaaS probes";
       uses apply-advanced;
       leaf timeout {
         description "Interval value in milliseconds";
         default "1000";
         type union {
           type string {
             pattern "<.*>|$.*";
           }
           type uint32 {
             range "100 .. 10000";
           }
         }
       }
     }
     container probe-interval {
       presence "enable probe-interval";
       description "Time interval between 2 consecutive probes";
       uses apply-advanced;
       leaf interval {
         description "Interval value in sec";
         default "10";
         type union {
           type string {
             pattern "<.*>|$.*";
           }
           type uint32 {
             range "1 .. 60";
           }
         }
       }
     }
     container probe-count {
       presence "enable probe-count";
       description "Minimum number of samples to be collected to evaluate SLA measurement";
       uses apply-advanced;
       leaf count {
         description "Sample count";
         default "5";
         type union {
           type string {
             pattern "<.*>|$.*";
           }
           type uint32 {
             range "1 .. 1000";
           }
         }
       }
     }
     container burst-size {
       presence "enable burst-size";
       description "Number of probes out of probe count to be sent as a burst";
       uses apply-advanced;
       leaf size {
         description "Burst size";
         default "1";
         type union {
           type string {
             pattern "<.*>|$.*";
           }
           type uint32 {
             range "1 .. 100";
           }
         }
       }
     }
     container sla-export-interval {
       description "Enabled time based SLA exporting";
       uses apply-advanced;
       leaf interval {
         description "Interval (sec)";
         type union {
           type string {
             pattern "<.*>|$.*";
           }
           type uint32 {
             range "60 .. 600";
           }
         }
       }
     }
     container dscp-code-points {
       description "Mapping of code point aliases to bit strings";
       uses apply-advanced;
       leaf dscp {
         description "DSCP";
         type string;
       }
     }
     container forwarding-class {
       description "Forwarding class corresponding to the DSCP";
       uses apply-advanced;
       leaf fc-name {
         description "Forwarding class name";
         type string;
       }
     }
     container loss-priority {
       presence "enable loss-priority";
       uses apply-advanced;
       leaf priority {
         description "Packet loss priority";
         type enumeration {
           enum "low" {
             description "Low loss priority";
           }
           enum "medium-low" {
             description "Medium-low loss priority";
           }
           enum "medium-high" {
             description "Medium-high loss priority";
           }
           enum "high" {
             description "High loss priority";
           }
         }
       }
     }
   }
   grouping appqoe-probe-path {
     description "Set probe path details";
     uses apply-advanced;
     container local {
       description "Local node's info";
       presence "enable local";
       uses appqoe-node;
     }
     container remote {
       description "Remote node's info";
       presence "enable remote";
       uses appqoe-node;
     }
   }
   grouping appqoe-node {
     description "Set node info";
     uses apply-advanced;
     container ip-address {
       presence "enable ip-address";
       description "Set IP address";
       uses apply-advanced;
       leaf ip_address {
         description "IP address";
         type jt:ipaddr;
       }
     }
   }
   grouping appqoe_sla_metric_profile {
     description "Metric Name";
     uses apply-advanced;
     container delay-round-trip {
       presence "enable delay-round-trip";
       description "Maximum acceptable delay";
       uses apply-advanced;
       leaf delay-val {
         description "Delay value(micro-sec)";
         type union {
           type string {
             pattern "<.*>|$.*";
           }
           type uint32 {
             range "0 .. 60000000";
           }
         }
       }
     }
     container jitter {
       presence "enable jitter";
       description "Maximum acceptable jitter";
       uses apply-advanced;
       leaf jitter-val {
         description "Jitter value(micro-sec)";
         type union {
           type string {
             pattern "<.*>|$.*";
           }
           type uint32 {
             range "0 .. 60000000";
           }
         }
       }
     }
     container jitter-type {
       presence "enable jitter-type";
       description "Type of Jitter";
       uses apply-advanced;
       leaf type {
         description "Jitter Type";
         type enumeration {
           enum "two-way-jitter" {
             description "Two-way-jitter-type";
           }
           enum "egress-jitter" {
             description "Egress-jitter-type";
           }
           enum "ingress-jitter" {
             description "Ingress-jitter-type";
           }
         }
       }
     }
     container packet-loss {
       presence "enable packet-loss";
       description "Maximum acceptable packet-loss";
       uses apply-advanced;
       leaf loss {
         description "Packet loss percentage";
         type union {
           type string {
             pattern "<.*>|$.*";
           }
           type uint32 {
             range "1 .. 100";
           }
         }
       }
     }
     container match {
       presence "enable match";
       description "Type of SLA match";
       uses apply-advanced;
       leaf sla_match {
         type enumeration {
           enum "any-one" {
             description "Match any one strings";
           }
           enum "all" {
             description "Match all metrics";
           }
         }
       }
     }
   }
   grouping authentication-source-type {
     description "Configure user-identification authentication-source";
     leaf name {
       description "User-identification authentication-source name";
       type enumeration {
         enum "local-authentication-table" {
           description "Local-authentication-table, default priority is 100.";
         }
         enum "unified-access-control" {
           description "Unified-access-control, default priority is 200.";
         }
         enum "firewall-authentication" {
           description "Firewall-authentication, default priority is 150.";
         }
         enum "active-directory-authentication-table" {
           description "Active-directory-authentication-table, default priority is 125.";
         }
         enum "aruba-clearpass" {
           description "ClearPass-authentication-table, default priority is 110.";
         }
       }
     }
     uses apply-advanced;
     choice authentication-source-option {
       case case_1 {
         leaf priority {
           description "Larger number means lower priority, 0 for disable";
           type union {
             type string {
               pattern "<.*>|$.*";
             }
             type uint16 {
               range "0 .. 65535";
             }
           }
         }
       }
     }
   }
   grouping av-fallback-settings {
     description "Anti-virus fallback settings";
     uses apply-advanced;
     leaf default {
       description "Default action";
       type enumeration {
         enum "permit" {
         }
         enum "log-and-permit" {
         }
         enum "block" {
         }
       }
     }
     leaf content-size {
       description "Fallback action for over content size";
       type enumeration {
         enum "permit" {
         }
         enum "log-and-permit" {
         }
         enum "block" {
         }
       }
     }
     leaf engine-not-ready {
       description "Fallback action for engine not ready";
       type enumeration {
         enum "permit" {
         }
         enum "log-and-permit" {
         }
         enum "block" {
         }
       }
     }
     leaf timeout {
       description "Fallback action for engine scan timeout";
       type enumeration {
         enum "permit" {
         }
         enum "log-and-permit" {
         }
         enum "block" {
         }
       }
     }
     leaf out-of-resources {
       description "Fallback action for out of resources";
       type enumeration {
         enum "permit" {
         }
         enum "log-and-permit" {
         }
         enum "block" {
         }
       }
     }
     leaf too-many-requests {
       description "Fallback action for requests exceed engine limit";
       type enumeration {
         enum "permit" {
         }
         enum "log-and-permit" {
         }
         enum "block" {
         }
       }
     }
     leaf decompress-err {
       description "Fallback action for decompress error";
       type enumeration {
         enum "permit" {
         }
         enum "log-and-permit" {
         }
         enum "block" {
         }
       }
     }
   }
   grouping aws-object {
     uses apply-advanced;
     container cloudwatch {
       description "Configure AWS CloudWatch";
       uses apply-advanced;
       container metric {
         description "Configure AWS CloudWatch metric";
         uses apply-advanced;
         leaf collect-interval {
           description "Set metric collection interval";
           default "3";
           units "minutes";
           type union {
             type string {
               pattern "<.*>|$.*";
             }
             type uint32 {
               range "1 .. 60";
             }
           }
         }
         leaf namespace {
           description "Container for collected metrics";
           type string {
             length "1 .. 32";
           }
         }
         leaf region {
           description "Set AWS CloudWatch metric region";
           type string;
         }
       }
       container log {
         description "Configure AWS CloudWatch metric";
         uses apply-advanced;
         leaf group {
           description "Group of log streams";
           type string {
             length "1 .. 32";
           }
         }
         leaf region {
           description "Set AWS CloudWatch log region";
           type string;
         }
         list file {
           key name;
           description "File from which to collect log data";
           leaf name {
             description "Name of file from which to collect log data";
             type string {
               length "1 .. 64";
             }
           }
           uses apply-advanced;
           leaf security-hub-import {
             description "Import security events in the file to AWS Security Hub";
             type empty;
           }
           leaf collect-interval {
             description "Set log collection interval";
             default "3";
             units "minutes";
             type union {
               type string {
                 pattern "<.*>|$.*";
               }
               type uint32 {
                 range "1 .. 60";
               }
             }
           }
         }
       }
     }
   }
   grouping category-list-type {
     description "Configure category-list object";
     leaf name {
       description "Configure name of category-list object";
       type string {
         length "1 .. 59";
       }
     }
     uses apply-advanced;
     leaf-list value {
       ordered-by user;
       description "Configure value of category-list object";
       type string;
     }
   }
   grouping certificate-object {
     leaf name {
       description "Simple name to identify this certificate";
       type string;
     }
     uses apply-advanced;
     leaf certificate {
       description "Certificate and private key string";
       type string;
     }
   }
   grouping command-list-type {
     description "Configure command-list object";
     leaf name {
       description "Configure name of command-list object";
       type string {
         length "1 .. 29";
       }
     }
     uses apply-advanced;
     leaf-list value {
       ordered-by user;
       description "Configure value of command-list object";
       type string {
         length "1 .. 64";
       }
     }
   }
   grouping content-filtering-feature {
     description "Content-filtering feature";
     uses apply-advanced;
     list profile {
       key name;
       ordered-by user;
       description "Content filtering profile";
       leaf name {
         description "Content-filtering feature profile name";
         type string {
           length "1 .. 29";
         }
       }
       uses apply-advanced;
       leaf permit-command {
         description "Permit command list";
         type string;
       }
       leaf block-command {
         description "Block command list";
         type string;
       }
       leaf block-extension {
         description "Block extension list";
         type string;
       }
       container block-mime {
         presence "enable block-mime";
         description "Content-filtering feature block MIME";
         uses apply-advanced;
         leaf list {
           description "Block MIME list";
           type string;
         }
         leaf exception {
           description "Exception of block MIME list";
           type string;
         }
       }
       container block-content-type {
         description "Content-filtering feature block content type";
         uses apply-advanced;
         leaf activex {
           description "Block activex";
           type empty;
         }
         leaf java-applet {
           description "Block Java-applet";
           type empty;
         }
         leaf exe {
           description "Block Windows/dos exe file";
           type empty;
         }
         leaf zip {
           description "Block zip file";
           type empty;
         }
         leaf http-cookie {
           description "Block HTTP cookie";
           type empty;
         }
       }
       container notification-options {
         presence "enable notification-options";
         description "Notification options";
         uses apply-advanced;
         leaf type {
           description "Notification options type";
           type enumeration {
             enum "protocol-only" {
               description "Notification in protocol level";
             }
             enum "message" {
               description "Notification in message";
             }
           }
         }
         choice notify-mail-sender-choice {
           leaf notify-mail-sender {
             description "Notifiy mail sender";
             type empty;
           }
           leaf no-notify-mail-sender {
             description "Don't notifiy mail sender";
             type empty;
           }
         }
         leaf custom-message {
           description "Custom notification message";
           type string {
             length "1 .. 512";
           }
         }
       }
     }
   }
   grouping custom-attack-group-type {
     description "Define custom attack group";
     leaf name {
       description "Custom attack group name";
       type string;
     }
     uses apply-advanced;
     leaf attack-group-description {
       description "Attack group description in xml format";
       status deprecated;
       type string;
     }
     leaf-list group-members {
       ordered-by user;
       description "List of attacks/attack groups belonging to this group";
       type string;
     }
   }
   grouping custom-attack-type {
     description "Define custom attack";
     leaf name {
       description "Custom attack name";
       type string {
       }
     }
     uses apply-advanced;
     leaf-list attack-description {
       ordered-by user;
       description "Attack description";
       type string;
     }
     leaf recommended-action {
       description "Recommended Action";
       type enumeration {
         enum "none" {
           description "No action";
         }
         enum "ignore" {
           description "No further inspection on the flow";
         }
         enum "drop-packet" {
           description "Drop the packet";
         }
         enum "drop" {
           description "Drop the packet and subsequent packets of the flow";
         }
         enum "close-client" {
           description "Reset the client side";
         }
         enum "close-server" {
           description "Reset the server side";
         }
         enum "close" {
           description "Reset both client and server";
         }
       }
     }
     leaf severity {
       description "Select the severity that matches the lethality of this attack on your network";
       type enumeration {
         enum "info" {
           description "Provide information of attack when it matches.";
         }
         enum "warning" {
           description "Issue a warning when attack matches.";
         }
         enum "minor" {
           description "The attack is a  minor one.";
         }
         enum "major" {
           description "The attack is a major one.";
         }
         enum "critical" {
           description "The attack is a critical one.";
         }
       }
     }
     container time-binding {
       description "Time binding params";
       leaf count {
         description "Number of times this attack is to be triggered";
         type union {
           type uint32;
           type string {
             pattern "<.*>|$.*";
           }
         }
       }
       leaf scope {
         description "Scope within which the count occurs";
         type enumeration {
           enum "peer" {
             description "If the attack is between a single source and single destination";
           }
           enum "source" {
             description "If the attack is from one source and multiple destination";
           }
           enum "destination" {
             description "If the attack is from multiple sources to one destination";
           }
         }
       }
       leaf interval {
         description "Maximum time-gap between two instances of the attack. Format : MMm-SSs";
         default "01m-00s";
         type string {
         }
       }
     }
     container detection-filter {
       description "Detection filter params";
       leaf count {
         description "Number of matches for this attack to be triggered. Must be greater than 0";
         type union {
           type uint32;
           type string {
             pattern "<.*>|$.*";
           }
         }
       }
       leaf scope {
         description "Scope within which the count occurs";
         type enumeration {
           enum "session" {
             description "If the attack is between a single source and single destination";
           }
           enum "source" {
             description "If the attack is from one source and multiple destination";
           }
           enum "destination" {
             description "If the attack is from multiple sources to one destination";
           }
         }
       }
       leaf interval {
         description "Time period over which count is accrued. Format : MMm-SSs. Minimum value is 1 second";
         type string {
         }
       }
     }
     container attack-type {
       description "Type of attack";
       uses apply-advanced;
       container signature {
         description "Signature based attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf context {
           description "Context";
           type string;
         }
         leaf pattern {
           description "Pattern is the signature of the attack you want to detect";
           type string {
             length "0 .. 511";
           }
         }
         leaf pattern-pcre {
           description "Attack signature pattern in PCRE format";
           type string {
             length "0 .. 511";
           }
         }
         container content {
           description "Mention the match-modifire parameters to enhance pattern matching";
           leaf pattern {
             description "Specify match-modifier pattern";
             type string;
           }
           leaf pcre {
             description "PCRE expression";
             type string {
               length "0 .. 511";
             }
           }
           container depth {
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           type string {
             length "0 .. 511";
           }
         }
         leaf negate {
           description "Trigger the attack if condition is not met";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container udp {
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmp {
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmpv6 {
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
         }
       }
       container anomaly {
         description "Protocol anomaly";
         uses apply-advanced;
         leaf service {
           description "Service name";
           type string;
         }
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
       container chain {
         description "Chain attack";
         uses apply-advanced;
         container protocol-binding {
           description "Protocol binding over which attack will be detected";
           uses apply-advanced;
           choice protocol {
             case case_1 {
               container tcp {
                 presence "enable tcp";
                 description "Attack is for TCP packets only";
                 uses apply-advanced;
                 list minimum-port {
                   key name;
                   ordered-by user;
                   description "Multiple sets of (single port/port ranges) can be specified";
                   uses port-range;
                 }
               }
             }
             case case_2 {
               container udp {
                 presence "enable udp";
                 description "Attack is for UDP packets only";
                 uses apply-advanced;
                 list minimum-port {
                   key name;
                   ordered-by user;
                   description "Either single port or port ranges can be specified";
                   uses port-range;
                 }
               }
             }
             case case_3 {
               container rpc {
                 presence "enable rpc";
                 description "Attack is for RPC packets only";
                 uses apply-advanced;
                 leaf program-number {
                   description "RPC Program Number";
                   type union {
                     type uint32;
                     type string {
                       pattern "<.*>|$.*";
                     }
                   }
                 }
               }
             }
             case case_4 {
               leaf icmp {
                 description "Attack is for ICMP packets only";
                 type empty;
               }
             }
             case case_5 {
               leaf icmpv6 {
                 description "Attack is for ICMPv6 packets only";
                 type empty;
               }
             }
             case case_6 {
               container ip {
                 presence "enable ip";
                 description "Attack is for all IP based packets";
                 uses apply-advanced;
                 leaf protocol-number {
                   description "Transport layer protocol number";
                   type union {
                     type string {
                       pattern "<.*>|$.*";
                     }
                     type uint32 {
                       range "0 .. 139";
                     }
                   }
                 }
               }
             }
             case case_7 {
               container ipv6 {
                 presence "enable ipv6";
                 description "Attack is for all IPv6 based packets";
                 uses apply-advanced;
                 leaf protocol-number {
                   description "Transport layer protocol number";
                   type union {
                     type string {
                       pattern "<.*>|$.*";
                     }
                     type uint32 {
                       range "0 .. 139";
                     }
                   }
                 }
               }
             }
             case case_8 {
               leaf application {
                 description "Application name";
                 type string;
               }
             }
             case case_9 {
               leaf nested-application {
                 description "Nested application name";
                 status deprecated;
                 type string;
               }
             }
           }
         }
         leaf scope {
           description "Scope of the attack";
           type enumeration {
             enum "session" {
               description "Allow matches across transactions within the same session";
             }
             enum "transaction" {
               description "Allow matches in single transactions within the same session";
             }
           }
         }
         leaf order {
           description "Attacks should match in the order in which they are defined";
           type empty;
         }
         leaf reset {
           description "Repeat match should generate a new alert";
           type empty;
         }
         leaf expression {
           description "Boolean Expression(or, and, oand). Multiple expressions can be combined using parenthesis.";
           type string;
         }
         list member {
           key name;
           ordered-by user;
           description "List of member attacks.";
           uses chain-member-type;
         }
       }
     }
   }
   grouping chain-member-type {
     description "Chain member";
     leaf name {
       description "Custom attack name";
       type string;
     }
     uses apply-advanced;
     container attack-type {
       presence "enable attack-type";
       description "Type of attack";
       uses apply-advanced;
       container signature {
         description "Signature based attack";
         uses apply-advanced;
         leaf context {
           description "Context";
           type string;
         }
         leaf pattern {
           description "Pattern is the signature of the attack you want to detect";
           type string {
             length "0 .. 511";
           }
         }
         leaf pattern-pcre {
           description "Attack signature pattern in PCRE format";
           type string {
             length "0 .. 511";
           }
         }
         container content {
           description "Mention the match-modifire parameters to enhance pattern matching";
           leaf pattern {
             description "Specify match-modifier pattern";
             type string;
           }
           leaf pcre {
             description "PCRE expression";
             type string {
               length "0 .. 511";
             }
           }
           container depth {
             description "Maximum depth to search pattern within a packet. Depth is not relative";
             leaf depth-value {
               description "Specify the value of 'depth'";
               type union {
                 type string {
                   pattern "<.*>|$.*";
                 }
                 type uint16 {
                   range "1 .. 65535";
                 }
               }
             }
             leaf depth-variable {
               description "Specify the variable name from which 'depth' should be extracted";
               type string;
             }
           }
           container offset {
             description "Where to start searching for a pattern within a packet. Offset value is not relative";
             leaf offset-value {
               description "Specify the value of 'offset'";
               type union {
                 type string {
                   pattern "<.*>|$.*";
                 }
                 type uint16 {
                   range "0 .. 65535";
                 }
               }
             }
             leaf offset-variable {
               description "Specify the variable name from which 'offset' should be extracted";
               type string;
             }
           }
           container within {
             description "Maximum Number of bytes present between two conjugative pattern match. within is  relative";
             leaf within-value {
               description "Specify the value of 'within'";
               type union {
                 type string {
                   pattern "<.*>|$.*";
                 }
                 type uint16 {
                   range "1 .. 65535";
                 }
               }
             }
             leaf within-variable {
               description "Specify the variable name from which 'within' should be extracted";
               type string;
             }
           }
           container distance {
             description "Maximum Length to ignore before searching next pattern match. Distance is  relative";
             leaf distance-value {
               description "Specify the value of 'distance'";
               type union {
                 type string {
                   pattern "<.*>|$.*";
                 }
                 type int32 {
                   range "-65535 .. 65535";
                 }
               }
             }
             leaf distance-variable {
               description "Specify the variable name from which 'distance' should be extracted";
               type string;
             }
           }
           container byte-extract {
             description "Mention the byte-extract parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type int32;
                 type string {
                   pattern "<.*>|$.*";
                 }
               }
             }
             leaf var-name {
               description "Specify the name of the variable to reference in other rule options";
               type string;
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the byte alignment";
               type enumeration {
                 enum "2-byte" {
                   description "Round the number of converted bytes to 2-byte boundary";
                 }
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-test {
             description "Mention the byte-test parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type int32;
                   type string {
                     pattern "<.*>|$.*";
                   }
                 }
               }
               leaf offset-variable {
                 description "Specify the name of the offset variable";
                 type string;
               }
             }
             container rvalue {
               description "Specify the rvalue to test the converted value against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "less-than" {
                   description "Perform operation 'less than'";
                 }
                 enum "greater-than" {
                   description "Perform operation 'greater than'";
                 }
                 enum "less-than-or-equal" {
                   description "Perform operation 'less than or equal'";
                 }
                 enum "greater-than-or-equal" {
                   description "Perform operation 'greater than or equal'";
                 }
                 enum "equal" {
                   description "Perform operation 'equal'";
                 }
                 enum "bitwise-AND" {
                   description "Perform operation 'bitwise AND'";
                 }
                 enum "bitwise-XOR" {
                   description "Perform operation 'bitwise OR'";
                 }
               }
             }
             leaf negate {
               description "Check if the operator is not true";
               type empty;
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
           }
           container byte-math {
             description "Mention the byte-math parameters for signature in length encoded protocols";
             leaf bytes {
               description "Specify the number of bytes to extract from packet";
               type union {
                 type string {
                   pattern "<.*>|$.*";
                 }
                 type uint32 {
                   range "1 .. 10";
                 }
               }
             }
             leaf offset {
               description "Specify the number of bytes in to payload to start processing";
               type union {
                 type string {
                   pattern "<.*>|$.*";
                 }
                 type uint16 {
                   range "0 .. 65535";
                 }
               }
             }
             container rvalue {
               description "Specify the value to use mathematical operation against";
               leaf rvalue-value {
                 description "Specify the value";
                 type union {
                   type uint32;
                   type string {
                     pattern "<.*>|$.*";
                   }
                 }
               }
               leaf rvalue-variable {
                 description "Specify the variable name";
                 type string;
               }
             }
             leaf relative {
               description "Specify whether to use an offset relative to last pattern match or not";
               type empty;
             }
             leaf operator {
               description "Specify the operation to perform on extracted value";
               type enumeration {
                 enum "addition" {
                   description "Perform operation 'addition'";
                 }
                 enum "subtraction" {
                   description "Perform operation 'subtraction'";
                 }
                 enum "multiplication" {
                   description "Perform operation 'multiplication'";
                 }
                 enum "division" {
                   description "Perform operation 'division'";
                 }
                 enum "right-shift" {
                   description "Perform operation 'right shift'";
                 }
                 enum "left-shift" {
                   description "Perform operation 'left shift'";
                 }
               }
             }
             leaf endianness {
               description "Specify the endianness with which bytes read should be processed";
               type enumeration {
                 enum "Little" {
                   description "Process data in little endian";
                 }
                 enum "Big" {
                   description "Process data in big endian";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf result {
               description "Specify the variable name to which result should be stored";
               type string;
             }
           }
           container byte-jump {
             description "Mention the byte-jump parameters for signature in length encoded protocols";
             leaf bytes {
               description "Specify the number of bytes to extract from packet";
               type union {
                 type string {
                   pattern "<.*>|$.*";
                 }
                 type uint32 {
                   range "1 .. 10";
                 }
               }
             }
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf multiplier {
               description "Specify the value to be multiplied against the bytes read";
               type union {
                 type uint16;
                 type string {
                   pattern "<.*>|$.*";
                 }
               }
             }
             leaf endianness {
               description "Specify the endianness with which bytes read should be processed";
               type enumeration {
                 enum "Little" {
                   description "Process data in little endian";
                 }
                 enum "Big" {
                   description "Process data in big endian";
                 }
               }
             }
             leaf align {
               description "Specify the endianness with which bytes read should be processed";
               type enumeration {
                 enum "4-byte" {
                   description "Round the number of converted bytes to 4-byte boundary";
                 }
               }
             }
             leaf string {
               description "Specify the data type in which string data should be parsed";
               type enumeration {
                 enum "hex" {
                   description "Process data in hexadecimal format";
                 }
                 enum "dec" {
                   description "Process data in decimal format";
                 }
                 enum "oct" {
                   description "Process data in octal format";
                 }
               }
             }
             leaf bitmask {
               description "Specify the bitmask (1-4 bytes) for AND operation in hexadecimal format";
               type string;
             }
             leaf from-beginning {
               description "Enable jump from the beginning of the payload";
               type empty;
             }
             leaf from-end {
               description "Enable jump from the end of the payload";
               type empty;
             }
             leaf post-offset {
               description "Specify the number of bytes to skip forward or backward";
               type union {
                 type string {
                   pattern "<.*>|$.*";
                 }
                 type int32 {
                   range "-65535 .. 65535";
                 }
               }
             }
           }
           container is-data-at {
             description "Mention the is-data-at parameters for signature in length encoded protocols";
             container offset {
               description "Mention the offset variable name or offset value to be used";
               leaf offset-value {
                 description "Specify the number of bytes in to payload to start processing";
                 type union {
                   type string {
                     pattern "<.*>|$.*";
                   }
                   type uint16 {
                     range "0 .. 65535";
                   }
                 }
               }
               leaf offset-variable {
                 description "Specify the name of the offset variable";
                 type string;
               }
             }
             leaf relative {
               description "Specify whether to use an offset relative to last pattern match or not";
               type empty;
             }
             leaf negate {
               description "Negates the results of the isdataat test";
               type empty;
             }
           }
         }
         container optional-parameters {
           description "Mention the optional parameters to enhance pattern matching";
           leaf min-offset {
             description "Minimum offset in data at which pattern-match can end";
             type union {
               type uint64;
               type string {
                 pattern "<.*>|$.*";
               }
             }
           }
           leaf max-offset {
             description "Maximum offset in data at which pattern-match can end";
             type union {
               type uint64;
               type string {
                 pattern "<.*>|$.*";
               }
             }
           }
           leaf min-length {
             description "Minimum match length required to match the pattern";
             type union {
               type uint64;
               type string {
                 pattern "<.*>|$.*";
               }
             }
           }
           leaf edit-distance {
             description "Match the pattern within this edit distance";
             type union {
               type uint32;
               type string {
                 pattern "<.*>|$.*";
               }
             }
           }
           leaf hamming-distance {
             description "Match the pattern within this hamming distance";
             type union {
               type uint32;
               type string {
                 pattern "<.*>|$.*";
               }
             }
           }
         }
         leaf regexp {
           description "Regular expression used for matching repetition of patterns";
           type string {
             length "0 .. 511";
           }
         }
         leaf negate {
           description "Trigger the attack if condition is not met";
           type empty;
         }
         leaf direction {
           description "Connection direction of the attack";
           type enumeration {
             enum "client-to-server" {
               description "Client to Server";
             }
             enum "server-to-client" {
               description "Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
         container protocol {
           description "Protocol header matches";
           uses apply-advanced;
           container ipv4 {
             description "IPv4 protocol parameters";
             uses apply-advanced;
             container tos {
               presence "enable tos";
               description "Type of Service";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container ihl {
               presence "enable ihl";
               description "Header length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container total-length {
               presence "enable total-length";
               description "Total Length of IP datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container identification {
               presence "enable identification";
               description "Fragment Identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container ip-flags {
               presence "enable ip-flags";
               description "IP Flag bits";
               choice rb-choice {
                 leaf rb {
                   description "Reserved bit";
                   type empty;
                 }
                 leaf no-rb {
                   description "Don't reserved bit";
                   type empty;
                 }
               }
               choice mf-choice {
                 leaf mf {
                   description "More Fragment bit";
                   type empty;
                 }
                 leaf no-mf {
                   description "Don't more Fragment bit";
                   type empty;
                 }
               }
               choice df-choice {
                 leaf df {
                   description "Don't Fragment bit";
                   type empty;
                 }
                 leaf no-df {
                   description "Don't don't Fragment bit";
                   type empty;
                 }
               }
             }
             container ttl {
               presence "enable ttl";
               description "Time to live";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container protocol {
               presence "enable protocol";
               description "Transport layer protocol";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container destination {
               presence "enable destination";
               description "Destination IP-address/Hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv4addr;
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container ipv6 {
             description "IPv6 protocol parameters";
             uses apply-advanced;
             container traffic-class {
               presence "enable traffic-class";
               description "Traffic class. Similar to TOS in IPv4";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container payload-length {
               presence "enable payload-length";
               description "Length of the payload in the IPv6 datagram";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container flow-label {
               presence "enable flow-label";
               description "Flow label identification";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 1048575";
                   }
                 }
               }
             }
             container hop-limit {
               presence "enable hop-limit";
               description "Hop limit";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container next-header {
               presence "enable next-header";
               description "The header following the basic IPv6 header";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container source {
               presence "enable source";
               description "Source IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container destination {
               presence "enable destination";
               description "Destination IP-address or hostname";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type jt:ipv6addr;
               }
             }
             container extension-header {
               description "IPv6 Extension headers";
               uses apply-advanced;
               container routing-header {
                 presence "enable routing-header";
                 description "IPv6 Routing extension header";
                 uses apply-advanced;
                 container header-type {
                   description "Routing header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
               }
               container destination-option {
                 description "IPv6 Destination option extension header";
                 uses apply-advanced;
                 container option-type {
                   description "Destination option header type";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type union {
                       type string {
                         pattern "<.*>|$.*";
                       }
                       type uint32 {
                         range "0 .. 255";
                       }
                     }
                   }
                 }
                 container home-address {
                   description "IPv6 Home address of the mobile node";
                   uses apply-advanced;
                   leaf match {
                     description "Match condition";
                     type enumeration {
                       enum "equal" {
                         description "Match when value in packet is exact match";
                       }
                       enum "greater-than" {
                         description "Match when value in packet is greater";
                       }
                       enum "less-than" {
                         description "Match when value in packet is less";
                       }
                       enum "not-equal" {
                         description "Match when value in packet is not exact match";
                       }
                     }
                   }
                   leaf value {
                     description "Match value";
                     type jt:ipv6addr;
                   }
                 }
               }
             }
           }
           container tcp {
             description "TCP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container ack-number {
               presence "enable ack-number";
               description "Acknowledgement Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 4294967295";
                   }
                 }
               }
             }
             container header-length {
               presence "enable header-length";
               description "Header Length in words";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 15";
                   }
                 }
               }
             }
             container reserved {
               presence "enable reserved";
               description "Three reserved bits";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 7";
                   }
                 }
               }
             }
             container window-size {
               presence "enable window-size";
               description "Window Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container urgent-pointer {
               presence "enable urgent-pointer";
               description "Urgent Pointer";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container tcp-flags {
               presence "enable tcp-flags";
               description "TCP header flags";
               choice r1-choice {
                 leaf r1 {
                   description "Set Reserverd bit 1";
                   type empty;
                 }
                 leaf no-r1 {
                   description "Don't set Reserverd bit 1";
                   type empty;
                 }
               }
               choice r2-choice {
                 leaf r2 {
                   description "Set Reserved bit 2";
                   type empty;
                 }
                 leaf no-r2 {
                   description "Don't set Reserved bit 2";
                   type empty;
                 }
               }
               choice urg-choice {
                 leaf urg {
                   description "Set Urgent bit";
                   type empty;
                 }
                 leaf no-urg {
                   description "Don't set Urgent bit";
                   type empty;
                 }
               }
               choice ack-choice {
                 leaf ack {
                   description "Set Acknowledge bit";
                   type empty;
                 }
                 leaf no-ack {
                   description "Don't set Acknowledge bit";
                   type empty;
                 }
               }
               choice psh-choice {
                 leaf psh {
                   description "Set Push bit";
                   type empty;
                 }
                 leaf no-psh {
                   description "Don't set Push bit";
                   type empty;
                 }
               }
               choice rst-choice {
                 leaf rst {
                   description "Set Reset bit";
                   type empty;
                 }
                 leaf no-rst {
                   description "Don't set Reset bit";
                   type empty;
                 }
               }
               choice syn-choice {
                 leaf syn {
                   description "Set SYN bit";
                   type empty;
                 }
                 leaf no-syn {
                   description "Don't set SYN bit";
                   type empty;
                 }
               }
               choice fin-choice {
                 leaf fin {
                   description "Set FINish bit";
                   type empty;
                 }
                 leaf no-fin {
                   description "Don't set FINish bit";
                   type empty;
                 }
               }
             }
             container option {
               presence "enable option";
               description "Kind";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container data-length {
               presence "enable data-length";
               description "Size of IP datagram subtracted by TCP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "2 .. 255";
                   }
                 }
               }
             }
             container window-scale {
               presence "enable window-scale";
               description "Window scale";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container mss {
               presence "enable mss";
               description "Maximum Segment Size";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container udp {
             description "UDP protocol parameters";
             uses apply-advanced;
             container source-port {
               presence "enable source-port";
               description "Source port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container destination-port {
               presence "enable destination-port";
               description "Destination port";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by UDP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmp {
             description "ICMP protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence Number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IP datagram subtracted by ICMP header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
           container icmpv6 {
             description "ICMPv6 protocol parameters";
             uses apply-advanced;
             container type {
               presence "enable type";
               description "Type";
               uses apply-advanced;
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container code {
               presence "enable code";
               description "Code";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container identification {
               presence "enable identification";
               description "Identifier in echo request/reply";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container sequence-number {
               presence "enable sequence-number";
               description "Sequence number";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 65535";
                   }
                 }
               }
             }
             container data-length {
               presence "enable data-length";
               description "Size of IPv6 datagram subtracted by ICMPv6 header length";
               leaf match {
                 description "Match condition";
                 type enumeration {
                   enum "equal" {
                     description "Match when value in packet is exact match";
                   }
                   enum "greater-than" {
                     description "Match when value in packet is greater";
                   }
                   enum "less-than" {
                     description "Match when value in packet is less";
                   }
                   enum "not-equal" {
                     description "Match when value in packet is not exact match";
                   }
                 }
               }
               leaf value {
                 description "Match value";
                 type union {
                   type string {
                     pattern "<.*>|$.*";
                   }
                   type uint32 {
                     range "0 .. 255";
                   }
                 }
               }
             }
             container checksum-validate {
               presence "enable checksum-validate";
               description "Validate checksum field against calculated checksum";
               leaf match {
                 description "Match condition";
                 type enumeration {
                   enum "equal" {
                     description "Match when checksum field in packet is exact match";
                   }
                   enum "greater-than" {
                     description "Match when checksum field in packet is greater";
                   }
                   enum "less-than" {
                     description "Match when checksum field in packet is less";
                   }
                   enum "not-equal" {
                     description "Match when checksum field in packet is not exact match";
                   }
                 }
               }
               leaf value {
                 description "Match value";
                 default "0";
                 type union {
                   type string {
                     pattern "<.*>|$.*";
                   }
                   type uint32 {
                     range "0 .. 65535";
                   }
                 }
               }
             }
           }
         }
       }
       container anomaly {
         description "Protocol anomaly";
         uses apply-advanced;
         leaf test {
           description "Protocol anomaly condition to be checked";
           type string;
         }
         leaf direction {
           description "Direction";
           type enumeration {
             enum "client-to-server" {
               description "From Client to Server";
             }
             enum "server-to-client" {
               description "From Server to Client";
             }
             enum "any" {
               description "Any direction";
             }
           }
         }
         leaf shellcode {
           description "Specify shellcode flag for this attack";
           type enumeration {
             enum "intel" {
               description "Detect shellcode for intel platforms";
             }
             enum "sparc" {
               description "Detect shellcode for sparc platforms";
             }
             enum "all" {
               description "Detect shellcode for both intel and sparc platforms";
             }
             enum "no-shellcode" {
               description "Do not detect shellcode";
             }
           }
         }
       }
     }
   }
   grouping custom-message-type {
     description "Configure custom-message object";
     leaf name {
       description "Configure name of custom-message object";
       type string {
         length "1 .. 59";
       }
     }
     uses apply-advanced;
     leaf type {
       description "Type of custom message";
       type enumeration {
         enum "redirect-url" {
           description "Redirect URL";
         }
         enum "user-message" {
           description "User message";
         }
         enum "custom-page" {
           description "Customer page";
         }
       }
     }
     choice contents {
       case case_1 {
         leaf content {
           description "Content of custom message";
           type string {
             length "1 .. 1024";
           }
         }
       }
       case case_2 {
         leaf custom-page-file {
           description "Name of custom page file";
           type string {
             length "1 .. 64";
           }
         }
       }
     }
   }
   grouping default-anti-spam-feature {
     description "Anti-spam feature";
     uses apply-advanced;
     leaf type {
       description "Anti-spam type";
       type enumeration {
         enum "sbl" {
           description "Anti-spam sophos sbl";
         }
         enum "anti-spam-none" {
         }
       }
     }
     leaf address-whitelist {
       description "Anti-spam whitelist";
       type string;
     }
     leaf address-blacklist {
       description "Anti-spam blacklist";
       type string;
     }
     container traceoptions {
       description "Trace options for anti-spam feature";
       uses anti-spam-traceoptions;
     }
     container sbl {
       description "SBL settings";
       presence "enable sbl";
       uses default-sbl-type;
     }
   }
   grouping anti-spam-traceoptions {
     description "Trace options for anti-spam  feature";
     uses apply-advanced;
     list flag {
       key name;
       ordered-by user;
       description "Trace options for anti-spam feature flag";
       leaf name {
         description "Trace options for anti-spam feature flag name";
         type enumeration {
           enum "manager" {
             description "Trace anti-spam manager information";
           }
           enum "sbl" {
             description "Trace SBL server information";
           }
           enum "all" {
             description "Enable trace all anti-spam trace options";
           }
         }
       }
     }
   }
   grouping default-anti-virus-feature {
     description "Anti-virus feature";
     uses apply-advanced;
     container mime-whitelist {
       description "Anti-virus MIME whitelist";
       uses apply-advanced;
       leaf list {
         description "MIME list";
         type string;
       }
       leaf exception {
         description "Exception settings for MIME white list";
         type string;
       }
     }
     leaf url-whitelist {
       description "Anti-virus URL white list";
       type string;
     }
     leaf type {
       description "Anti-virus engine type";
       default "anti-virus-none";
       type enumeration {
         enum "sophos-engine" {
           description "Anti-virus sophos-engine";
         }
         enum "avira-engine" {
           description "Anti-virus avira-engine";
         }
         enum "anti-virus-none" {
         }
       }
     }
     container forwarding-mode {
       description "Anti-virus forwarding mode";
       uses apply-advanced;
       leaf hold {
         description "Hold mode (hold file until analysis is complete, default is CDF mode)";
         type empty;
       }
       leaf inline-tap {
         description "Detect-only mode without blocking (default is off)";
         type empty;
       }
     }
     container scan-options {
       presence "enable scan-options";
       description "Anti-virus scan options";
       uses apply-advanced;
       choice pre-detection-choice {
         leaf pre-detection {
           description "Anti-virus Pre-Detection";
           type empty;
         }
         leaf no-pre-detection {
           description "Don't anti-virus Pre-Detection";
           type empty;
         }
       }
       choice uri-check-choice {
         leaf uri-check {
           description "Anti-virus uri-check";
           type empty;
         }
         leaf no-uri-check {
           description "Don't anti-virus uri-check";
           type empty;
         }
       }
       leaf content-size-limit {
         description "Content size limit";
         units "kilobytes";
         type string;
       }
       leaf timeout {
         description "Scan engine timeout";
         units "seconds";
         type union {
           type string {
             pattern "<.*>|$.*";
           }
           type uint32 {
             range "1 .. 1800";
           }
         }
       }
       leaf decompress-layer-limit {
         description "Decompress layer limit";
         type union {
           type string {
             pattern "<.*>|$.*";
           }
           type uint32 {
             range "0 .. 10";
           }
         }
       }
     }
     container trickling {
       description "Anti-virus trickling";
       presence "enable trickling";
       uses anti-virus-trickling;
     }
     container notification-options {
       description "Anti-virus notification options";
       presence "enable notification-options";
       uses anti-virus-notification-options;
     }
     container fallback-options {
       description "Anti-virus fallback options";
       presence "enable fallback-options";
       uses av-fallback-settings;
     }
     container traceoptions {
       description "Trace options for anti-virus feature";
       uses anti-virus-traceoptions;
     }
     container avira-engine {
       description "Anti-virus Avira-engine";
       uses apply-advanced;
       container pattern-update {
         description "Anti-virus avira-engine pattern update";
         presence "enable pattern-update";
         uses anti-virus-pattern-update;
       }
     }
     container sophos-engine {
       description "Anti-virus sophos-engine";
       uses apply-advanced;
       container server {
         description "SAV and Anti-Spam first hop DNS server";
         uses apply-advanced;
         leaf ip {
           description "SAV and Anti-Spam first hop DNS server ip";
           type jt:ipaddr;
         }
         leaf routing-instance {
           description "Routing instance name";
           type string;
         }
         leaf source-address {
           description "Source ip address used to connect server";
           type jt:ipaddr;
         }
       }
       leaf sxl-timeout {
         description "Sxl sophos anti-virus engine timeout";
         default "2";
         units "seconds";
         type union {
           type string {
             pattern "<.*>|$.*";
           }
           type uint32 {
             range "1 .. 5";
           }
         }
       }
       leaf sxl-retry {
         description "Sxl sophos anti-virus engine query retry (number of times)";
         default "1";
         type union {
           type string {
             pattern "<.*>|$.*";
           }
           type uint32 {
             range "0 .. 5";
           }
         }
       }
       container pattern-update {
         description "Anti-virus sophos-engine pattern update";
         presence "enable pattern-update";
         uses anti-virus-pattern-update;
       }
       container fallback-options {
         description "Anti-virus sophos-engine fallback options";
         presence "enable fallback-options";
         status deprecated;
         uses av-fallback-settings;
       }
       container scan-options {
         description "Anti-virus sophos-engine scan options";
         presence "enable scan-options";
         status deprecated;
         uses default-sophos-scan-options;
       }
       container trickling {
         description "Anti-virus trickling";
         presence "enable trickling";
         status deprecated;
         uses anti-virus-trickling;
       }
       container notification-options {
         description "Anti-virus notification options";
         presence "enable notification-options";
         status deprecated;
         uses anti-virus-notification-options;
       }
     }
   }
   grouping default-content-filtering-feature {
     description "Content-filtering feature";
     uses apply-advanced;
     leaf type {
       description "Content-filtering type";
       default "local";
       type enumeration {
         enum "local" {
           description "Content-filtering local";
         }
         enum "content-filtering-none" {
         }
       }
     }
     container traceoptions {
       description "Trace options for content-filtering feature";
       uses content-filtering-traceoptions;
     }
     leaf permit-command {
       description "Permit command list";
       status deprecated;
       type string;
     }
     leaf block-command {
       description "Block command list";
       status deprecated;
       type string;
     }
     leaf block-extension {
       description "Block extension list";
       status deprecated;
       type string;
     }
     container block-mime {
       presence "enable block-mime";
       description "Content-filtering feature block MIME";
       status deprecated;
       uses apply-advanced;
       leaf list {
         description "Block MIME list";
         type string;
       }
       leaf exception {
         description "Exception of block MIME list";
         type string;
       }
     }
     container block-content-type {
       description "Content-filtering feature block content type";
       status deprecated;
       uses apply-advanced;
       leaf activex {
         description "Block activex";
         type empty;
       }
       leaf java-applet {
         description "Block Java-applet";
         type empty;
       }
       leaf exe {
         description "Block Windows/dos exe file";
         type empty;
       }
       leaf zip {
         description "Block zip file";
         type empty;
       }
       leaf http-cookie {
         description "Block HTTP cookie";
         type empty;
       }
     }
     list rule-set {
       key name;
       ordered-by user;
       description "Default Rule-set configuration";
       uses cf-rule-set;
     }
     container notification-options {
       presence "enable notification-options";
       description "Notification options";
       uses apply-advanced;
       leaf log {
         description "Generate security event if content is blocked by rule";
         type empty;
       }
       leaf type {
         description "Notification options type";
         type enumeration {
           enum "protocol-only" {
             description "Notification in protocol level";
           }
           enum "message" {
             description "Notification in message";
           }
         }
       }
       choice notify-mail-sender-choice {
         leaf notify-mail-sender {
           description "Notifiy mail sender";
           type empty;
         }
         leaf no-notify-mail-sender {
           description "Don't notifiy mail sender";
           type empty;
         }
       }
       leaf custom-message {
         description "Custom notification message";
         type string {
           length "1 .. 512";
         }
       }
     }
   }
   grouping cf-rule-set {
     description "UTM CF Rule-Set object";
     leaf name {
       description "UTM CF Rule-set name";
       type string {
         length "1 .. 29";
       }
     }
     uses apply-advanced;
     list rule {
       key name;
       ordered-by user;
       description "Configure UTM CF Rules";
       uses cf-rule;
     }
   }
   grouping cf-rule {
     description "UTM CF Rule object";
     leaf name {
       description "UTM CF Rule name";
       type string {
         length "1 .. 29";
       }
     }
     uses apply-advanced;
     container match {
       description "Rule match criteria";
       uses apply-advanced;
       leaf-list applications {
         ordered-by user;
         description "List of applications to be inspected";
         type string;
       }
       leaf direction {
         description "Direction of the content to be inspected";
         type enumeration {
           enum "upload" {
             description "Uploading content";
           }
           enum "download" {
             description "Downloading content";
           }
           enum "any" {
             description "Content in any direction";
           }
         }
       }
       leaf-list file-types {
         ordered-by user;
         description "List of file-types in match critera";
         type string;
       }
     }
     container then {
       description "Rule then criteria";
       uses apply-advanced;
       leaf action {
         description "Configure action";
         type enumeration {
           enum "no-action" {
             description "No action";
           }
           enum "block" {
             description "Block and drop connection";
           }
           enum "close-client" {
             description "Close client";
           }
           enum "close-server" {
             description "Close server";
           }
           enum "close-client-and-server" {
             description "Close client and server";
           }
         }
       }
       container notification {
         description "Event logging and notification options";
         presence "enable notification";
         uses cf-notification;
       }
     }
   }
   grouping cf-notification {
     description "Event logging and notification options";
     uses apply-advanced;
     leaf log {
       description "Generate security event if content is blocked by rule";
       type empty;
     }
     container endpoint {
       presence "enable endpoint";
       uses apply-advanced;
       leaf type {
         description "Endpoint notification type";
         type enumeration {
           enum "protocol-only" {
             description "Notification in protocol level";
           }
           enum "message" {
             description "Notification in message";
           }
         }
       }
       choice notify-mail-sender-choice {
         leaf notify-mail-sender {
           description "Notifiy mail sender";
           type empty;
         }
         leaf no-notify-mail-sender {
           description "Don't notifiy mail sender";
           type empty;
         }
       }
       leaf custom-message {
         description "Custom notification message";
         type string {
           length "1 .. 512";
         }
       }
     }
   }
   grouping content-filtering-traceoptions {
     description "Trace options for content-filtering feature";
     uses apply-advanced;
     list flag {
       key name;
       ordered-by user;
       description "Trace options for content-filtering feature flag";
       leaf name {
         description "Trace options for content-filtering feature flag name";
         type enumeration {
           enum "basic" {
             description "Trace content-filtering basic information";
           }
           enum "detail" {
             description "Trace content-filtering detail information";
           }
           enum "all" {
             description "Enable trace all content-filtering trace options";
           }
         }
       }
     }
   }
   grouping default-sbl-type {
     description "SBL type";
     uses apply-advanced;
     choice sbl-default-server-choice {
       leaf sbl-default-server {
         description "Default SBL server";
         type empty;
       }
       leaf no-sbl-default-server {
         description "Don't default SBL server";
         type empty;
       }
     }
     leaf spam-action {
       description "Anti-spam actions";
       default "tag-subject";
       type enumeration {
         enum "block" {
           description "Block e-mail";
         }
         enum "tag-header" {
           description "Tag header of e-mail";
         }
         enum "tag-subject" {
           description "Tag subject of e-mail";
         }
       }
     }
     leaf custom-tag-string {
       description "Custom tag string";
       type string {
         length "1 .. 512";
       }
     }
   }
   grouping default-sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       default "10000";
       units "kilobytes";
       type string;
     }
     leaf timeout {
       description "Scan engine timeout";
       units "seconds";
       type union {
         type string {
           pattern "<.*>|$.*";
         }
         type uint32 {
           range "1 .. 1800";
         }
       }
     }
   }
   grouping default-webfilter-feature {
     description "Web-filtering feature settings";
     uses apply-advanced;
     leaf url-whitelist {
       description "Configure custom URL for whitelist category";
       type string;
     }
     leaf url-blacklist {
       description "Configure custom URL for blacklist category";
       type string;
     }
     leaf http-reassemble {
       description "Reassemble HTTP request segments";
       type empty;
     }
     leaf http-persist {
       description "Check all HTTP request in a connection";
       type empty;
     }
     leaf type {
       description "Configure web-filtering engine type";
       default "web-filtering-none";
       type enumeration {
         enum "websense-redirect" {
         }
         enum "juniper-local" {
         }
         enum "juniper-enhanced" {
         }
         enum "web-filtering-none" {
         }
       }
     }
     container traceoptions {
       description "Trace options for web-filtering feature";
       uses web-filtering-traceoptions;
     }
     container websense-redirect {
       description "Configure web-filtering websense redirect engine";
       uses default-websense-type;
     }
     container juniper-local {
       description "Configure web-filtering juniper local engine";
       uses default-juniper-local-type;
     }
     container juniper-enhanced {
       description "Configure web-filtering juniper enhanced engine";
       uses default-juniper-enhanced-type;
     }
   }
   grouping default-juniper-enhanced-type {
     description "Juniper Enhanced";
     uses apply-advanced;
     container cache {
       presence "enable cache";
       uses apply-advanced;
       leaf timeout {
         description "Juniper enhanced cache timeout";
         default "1440";
         units "minutes";
         type union {
           type string {
             pattern "<.*>|$.*";
           }
           type uint32 {
             range "1 .. 1800";
           }
         }
       }
       leaf size {
         description "Juniper enhanced cache size";
         default "1024";
         units "kilobytes";
         type string;
       }
     }
     container server {
       description "Juniper enhanced server";
       presence "enable server";
       uses juniper-enhanced-server;
     }
     container reputation {
       presence "enable reputation";
       description "Customize reputation level";
       uses apply-advanced;
       leaf reputation-very-safe {
         description "Base-reputation-value (default 90)";
         default "90";
         type union {
           type string {
             pattern "<.*>|$.*";
           }
           type uint32 {
             range "1 .. 100";
           }
         }
       }
       leaf reputation-moderately-safe {
         description "Base-reputation-value (default 80)";
         default "80";
         type union {
           type string {
             pattern "<.*>|$.*";
           }
           type uint32 {
             range "1 .. 100";
           }
         }
       }
       leaf reputation-fairly-safe {
         description "Base-reputation-value (default 70)";
         default "70";
         type union {
           type string {
             pattern "<.*>|$.*";
           }
           type uint32 {
             range "1 .. 100";
           }
         }
       }
       leaf reputation-suspicious {
         description "Base-reputation-value (default 60)";
         default "60";
         type union {
           type string {
             pattern "<.*>|$.*";
           }
           type uint32 {
             range "1 .. 100";
           }
         }
       }
     }
     leaf query-type {
       description "Juniper enhanced query type";
       type enumeration {
         enum "url-ip" {
           description "Query category by URL and IP address";
         }
         enum "url" {
           description "Query category by URL only";
         }
       }
     }
     leaf base-filter {
       description "Juniper base filter";
       type string;
     }
     list category {
       key name;
       ordered-by user;
       description "Juniper enhanced category";
       uses juniper-enhanced-category-type;
     }
     container site-reputation-action {
       description "Juniper enhanced site reputation action";
       presence "enable site-reputation-action";
       uses juniper-enhanced-site-reputation-setting;
     }
     leaf default {
       description "Juniper enhanced profile default";
       type enumeration {
         enum "permit" {
           description "Permit action";
         }
         enum "block" {
           description "Block action";
         }
         enum "log-and-permit" {
           description "Log and permit action";
         }
         enum "quarantine" {
           description "Quarantine action";
         }
       }
     }
     leaf custom-message {
       description "Custom message";
       type string;
     }
     container fallback-settings {
       description "Juniper enhanced fallback settings";
       presence "enable fallback-settings";
       uses web-filtering-fallback-setting;
     }
     leaf timeout {
       description "Juniper enhanced timeout";
       default "15";
       units "seconds";
       type union {
         type string {
           pattern "<.*>|$.*";
         }
         type uint32;
       }
     }
     leaf no-safe-search {
       description "Do not perform safe-search for Juniper enhanced protocol";
       type empty;
     }
   }
   grouping default-juniper-local-type {
     description "Juniper local";
     uses apply-advanced;
     leaf default {
       description "Juniper local profile default";
       type enumeration {
         enum "permit" {
           description "Permit action";
         }
         enum "block" {
           description "Block action";
         }
         enum "log-and-permit" {
           description "Log and permit action";
         }
       }
     }
     list category {
       key name;
       ordered-by user;
       description "Custom category";
       uses custom-category-type;
     }
     leaf custom-message {
       description "Custom message";
       type string;
     }
     leaf no-safe-search {
       description "Do not perform safe-search for Juniper local protocol";
       type empty;
     }
     container fallback-settings {
       description "Juniper local fallback settings";
       presence "enable fallback-settings";
       uses web-filtering-fallback-setting;
     }
     leaf timeout {
       description "Juniper local timeout";
       default "15";
       units "seconds";
       type union {
         type string {
           pattern "<.*>|$.*";
         }
         type uint32 {
           range "1 .. 1800";
         }
       }
     }
   }
   grouping custom-category-type {
     description "Custom category type";
     leaf name {
       description "Name of custom category";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       type string;
     }
   }
   grouping default-websense-type {
     description "Websense redirect";
     uses apply-advanced;
     container server {
       description "Websense redirect server";
       presence "enable server";
       uses server;
     }
     list category {
       key name;
       ordered-by user;
       description "Custom category";
       uses custom-category-type;
     }
     leaf custom-message {
       description "Custom message";
       type string;
     }
     leaf no-safe-search {
       description "Do not perform safe-search for websense redirect protocol";
       type empty;
     }
     container fallback-settings {
       description "Websense redirect fallback settings";
       presence "enable fallback-settings";
       uses web-filtering-fallback-setting;
     }
     leaf timeout {
       description "Websense redirect timeout";
       default "15";
       units "seconds";
       type union {
         type string {
           pattern "<.*>|$.*";
         }
         type uint32 {
           range "1 .. 1800";
         }
       }
     }
     leaf sockets {
       description "Websense redirect sockets number";
       default "32";
       type union {
         type string {
           pattern "<.*>|$.*";
         }
         type uint32 {
           range "1 .. 32";
         }
       }
     }
     leaf account {
       description "Websense redirect account";
       type string {
         length "1 .. 28";
       }
     }
   }
   grouping dynamic-attack-group-type {
     description "Define dynamic attack group";
     leaf name {
       description "Name of the dynamic attack group";
       type string;
     }
     uses apply-advanced;
     leaf attack-group-description {
       description "Filter name/value in xml format";
       status deprecated;
       type string;
     }
     container filters {
       description "Configure filters";
       uses apply-advanced;
       container direction {
         presence "enable direction";
         description "Direction of attack";
         uses apply-advanced;
         leaf expression {
           description "Boolean AND/OR to be used for values";
           default "or";
           type enumeration {
             enum "and" {
               description "AND values together (recommended if 'exclude-*' values are set)";
             }
             enum "or" {
               description "OR values together";
             }
           }
         }
         leaf-list values {
           ordered-by user;
           description "Values for direction field";
           type enumeration {
             enum "client-to-server" {
               description "Select attacks from client to server";
             }
             enum "server-to-client" {
               description "Select attacks from server to client";
             }
             enum "any" {
               description "Select attacks which can occur in either direction";
             }
             enum "exclude-client-to-server" {
               description "Filter out attacks from client to server";
             }
             enum "exclude-server-to-client" {
               description "Filter out attacks from server to client";
             }
             enum "exclude-any" {
               description "Filter out attacks which occur in either direction";
             }
           }
         }
       }
       container severity {
         presence "enable severity";
         description "Severity of attack";
         uses apply-advanced;
         leaf-list values {
           ordered-by user;
           description "Values for severity field";
           type enumeration {
             enum "info" {
               description "Provide information of attack when it matches.";
             }
             enum "warning" {
               description "Issue a warning when attack matches.";
             }
             enum "minor" {
               description "The attack is a minor one.";
             }
             enum "major" {
               description "The attack is a major one.";
             }
             enum "critical" {
               description "The attack is a critical one.";
             }
           }
         }
       }
       container type {
         presence "enable type";
         description "Type of attack";
         uses apply-advanced;
         leaf-list values {
           ordered-by user;
           description "Values for type field";
           type enumeration {
             enum "signature" {
               description "Signature based attacks";
             }
             enum "anomaly" {
               description "Protocol anomalies";
             }
           }
         }
       }
       choice recommended-choice {
         leaf recommended {
           description "Recommended flag";
           type empty;
         }
         leaf no-recommended {
           description "Don't recommended flag";
           type empty;
         }
       }
       container performance {
         presence "enable performance";
         description "Performance of attack";
         uses apply-advanced;
         leaf-list values {
           ordered-by user;
           description "Values for performance field";
           type enumeration {
             enum "unknown" {
               description "Performance level unknown";
             }
             enum "fast" {
               description "Fast performance";
             }
             enum "normal" {
               description "Normal performance";
             }
             enum "slow" {
               description "Slow performance";
             }
           }
         }
       }
       container category {
         presence "enable category";
         description "Category of attack";
         uses apply-advanced;
         leaf-list values {
           ordered-by user;
           description "Values for category field";
           type string;
         }
       }
       container service {
         presence "enable service";
         description "Service/Application of attack";
         uses apply-advanced;
         leaf-list values {
           ordered-by user;
           description "Values for service field";
           type string;
         }
       }
       container false-positives {
         presence "enable false-positives";
         description "False positive field in attack";
         uses apply-advanced;
         leaf-list values {
           ordered-by user;
           description "Values for false-positives field";
           type enumeration {
             enum "unknown" {
               description "Unknown information";
             }
             enum "rarely" {
               description "Rare false positives occurrence";
             }
             enum "occasionally" {
               description "Ocassional false positives occurrence";
             }
             enum "frequently" {
               description "Frequent false positives occurrence";
             }
           }
         }
       }
       list vendor {
         key name;
         ordered-by user;
         description "Vendor/Product the attack belongs to";
         uses vendor-object;
       }
       container file-type {
         presence "enable file-type";
         description "File type the attack is valid for";
         uses apply-advanced;
         leaf-list values {
           ordered-by user;
           description "Values for file-type field";
           type string;
         }
       }
       container vulnerability-type {
         presence "enable vulnerability-type";
         description "Vulnariability type of attack";
         uses apply-advanced;
         leaf-list values {
           ordered-by user;
           description "Values for vulnariability-type field";
           type string;
         }
       }
       choice excluded-choice {
         leaf excluded {
           description "Excluded Attacks";
           type empty;
         }
         leaf no-excluded {
           description "Don't excluded Attacks";
           type empty;
         }
       }
       container attack-prefix {
         presence "enable attack-prefix";
         description "Prefix match for attack names";
         uses apply-advanced;
         leaf-list values {
           ordered-by user;
           description "Values for attack name prefix match";
           type string;
         }
       }
       list cvss-score {
         key name;
         ordered-by user;
         description "CVSS score of Attack ";
         leaf name {
           description "Match condition of CVSS score";
           type enumeration {
             enum "greater-than" {
               description "Match when cvss score is greater";
             }
             enum "less-than" {
               description "Match when cvss score is less";
             }
           }
         }
         uses apply-advanced;
         leaf value {
           description "Match value";
           type decimal64 {
             fraction-digits 9;
             range "0 .. 10";
           }
         }
       }
       list age-of-attack {
         key name;
         ordered-by user;
         description "Age of an Attack ";
         leaf name {
           description "Match condition of Age of Attack";
           type enumeration {
             enum "greater-than" {
               description "Match when Age of Attack is greater";
             }
             enum "less-than" {
               description "Match when Age of Attack is less";
             }
           }
         }
         uses apply-advanced;
         leaf value {
           description "Match value";
           type union {
             type string {
               pattern "<.*>|$.*";
             }
             type uint32 {
               range "1 .. 100";
             }
           }
         }
       }
     }
   }
   grouping e2e-action-profile {
     leaf name {
       description "Name of the action profile";
       type string {
         length "1 .. 64";
       }
     }
     uses apply-advanced;
     leaf preserve-trace-order {
       description "Preserve trace order (has performance overhead)";
       type empty;
     }
     leaf record-pic-history {
       description "Record the PIC(s) in which the packet has been processed";
       type empty;
     }
     list event {
       key name;
       ordered-by user;
       uses e2e-event;
     }
     list module {
       key name;
       ordered-by user;
       uses e2e-module;
     }
   }
   grouping e2e-event {
     leaf name {
       description "Name of the event";
       type enumeration {
         enum "np-ingress" {
           description "NP ingress";
         }
         enum "np-egress" {
           description "NP egress";
         }
         enum "mac-ingress" {
           description "SRX1K/3K IOC Mac ingress";
         }
         enum "mac-egress" {
           description "SRX1K/3K IOC Mac egress";
         }
         enum "lbt" {
           description "Load-Balance-Thread";
         }
         enum "pot" {
           description "Packet-Order-Thread";
         }
         enum "jexec" {
           description "JExec";
         }
         enum "lt-enter" {
           description "LT(Logical Tunnel) enter";
         }
         enum "lt-leave" {
           description "LT(Logical Tunnel) leave";
         }
       }
     }
     uses apply-advanced;
     leaf trace {
       description "Trace action";
       type empty;
     }
     leaf count {
       description "Count action";
       type empty;
     }
     leaf packet-summary {
       description "Packet summary action";
       type empty;
     }
     leaf packet-dump {
       description "Packet dump action";
       type empty;
     }
   }
   grouping e2e-module {
     leaf name {
       description "Name of the module";
       type enumeration {
         enum "flow" {
           description "Flow module";
         }
       }
     }
     uses apply-advanced;
     list flag {
       key name;
       ordered-by user;
       description "Events and other information to include in trace output";
       leaf name {
         type enumeration {
           enum "all" {
             description "All flow trace";
           }
         }
       }
     }
   }
   grouping end-to-end-debug-filter {
     description "End to end debug packer filter settings";
     leaf name {
       description "Name of the filter";
       type string {
         length "1 .. 64";
       }
     }
     uses apply-advanced;
     leaf action-profile {
       description "Actions to take with this filter";
       type string;
     }
     leaf protocol {
       description "Match IP protocol type";
       type string;
     }
     leaf source-prefix {
       description "Source IPv4/IPv6 address prefix";
       type jt:ipprefix;
     }
     leaf destination-prefix {
       description "Destination IPv4/IPv6 address prefix";
       type jt:ipprefix;
     }
     leaf source-port {
       description "Match TCP/UDP source port";
       type string;
     }
     leaf destination-port {
       description "Match TCP/UDP destination port";
       type string;
     }
     leaf interface {
       description "Logical interface";
       type union {
         type jt:interface-name;
         type string {
           pattern "<.*>|$.*";
         }
       }
     }
   }
   grouping extension-list-type {
     description "Configure extension-list object";
     leaf name {
       description "Configure name of extension-list object";
       type string {
         length "1 .. 29";
       }
     }
     uses apply-advanced;
     leaf-list value {
       ordered-by user;
       description "Configure value of extension-list object";
       type string {
         length "1 .. 29";
       }
     }
   }
   grouping flow-filter-type {
     description "Flow filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf conn-tag {
       description "Session connection tag";
       type union {
         type string {
           pattern "<.*>|$.*";
         }
         type uint32 {
           range "0 .. 4294967295";
         }
       }
     }
     leaf logical-system {
       description "Logical system";
       status deprecated;
       type string {
         length "1 .. 63";
       }
     }
     leaf source-port {
       description "Match TCP/UDP source port";
       type string;
     }
     leaf destination-port {
       description "Match TCP/UDP destination port";
       type string;
     }
     leaf interface {
       description "Source logical interface";
       type union {
         type jt:interface-name;
         type string {
           pattern "<.*>|$.*";
         }
       }
     }
   }
   grouping flow-traceoptions-object {
     description "Trace options for flow services";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         type enumeration {
           enum "all" {
             description "All events";
           }
           enum "basic-datapath" {
             description "Basic packet flow";
           }
           enum "high-availability" {
             description "Flow high-availability information";
           }
           enum "host-traffic" {
             description "Flow host-traffic information";
           }
           enum "fragmentation" {
             description "Ip fragmentation and reassembly events";
           }
           enum "multicast" {
             description "Multicast flow information";
           }
           enum "route" {
             description "Route lookup information";
           }
           enum "session" {
             description "Session creation and deletion events";
           }
           enum "session-scan" {
             description "Session scan information";
           }
           enum "tcp-basic" {
             description "TCP packet flow";
           }
           enum "tunnel" {
             description "Tunnel information";
           }
           enum "jexec" {
             description "Junos forwarding module";
           }
         }
       }
     }
     leaf rate-limit {
       description "Limit the incoming rate of trace messages";
       default "0";
       type union {
         type string {
           pattern "<.*>|$.*";
         }
         type uint32 {
           range "0 .. 4294967295";
         }
       }
     }
     list packet-filter {
       key name;
       ordered-by user;
       description "Flow packet debug filters";
       max-elements 64;
       uses flow-filter-type;
     }
     container trace-level {
       description "FLow trace level";
       uses apply-advanced;
       choice level {
         case case_1 {
           leaf minimal {
             description "Significant messages including warning, error, criticality, alert and emergency.";
             type empty;
           }
         }
         case case_2 {
           leaf brief {
             description "Brief messages including notice, in addition to minimal messages";
             type empty;
           }
         }
         case case_3 {
           leaf detail {
             description "Detail messages including info and debug, in addition to brief messages";
             type empty;
           }
         }
       }
     }
     leaf root-override {
       description "Allow collect flow trace in root from all logical-systems and tenants";
       type empty;
     }
   }
   grouping gtp-object {
     uses apply-advanced;
     list profile {
       key name;
       description "Configure GTP Profile";
       leaf name {
         description "GTP profile name";
         type string {
           length "1 .. 23";
         }
       }
       uses apply-advanced;
       leaf min-message-length {
         description "Minimum message length, from 0 to 65535 ";
         default "0";
         type union {
           type string {
             pattern "<.*>|$.*";
           }
           type uint32 {
             range "0 .. 65535";
           }
         }
       }
       leaf max-message-length {
         description "Maximum message length, from 1 to 65535";
         default "65535";
         type union {
           type string {
             pattern "<.*>|$.*";
           }
           type uint32 {
             range "1 .. 65535";
           }
         }
       }
       leaf timeout {
         description "Tunnel idle timeout";
         default "1000";
         units "hour";
         type union {
           type string {
             pattern "<.*>|$.*";
           }
           type uint32 {
             range "1 .. 1000";
           }
         }
       }
       container rate-limit {
         description "Limit messages per second";
         presence "enable rate-limit";
         uses rate-limit-object;
       }
       container log {
         presence "enable log";
         description "GPRS tunneling protocol logs";
         uses apply-advanced;
         leaf forwarded {
           description "Log passed good packets";
           type enumeration {
             enum "basic" {
               description "Basic logs";
             }
             enum "detail" {
               description "Detailed logs";
             }
           }
         }
         leaf event {
           description "Log alarms and tunnel management events";
           type enumeration {
             enum "basic" {
               description "Basic logs";
             }
             enum "detail" {
               description "Detailed logs";
             }
           }
         }
         leaf prohibited {
           description "Log dropped packets";
           type enumeration {
             enum "basic" {
               description "Basic logs";
             }
             enum "detail" {
               description "Detailed logs";
             }
           }
         }
         list gtp-u {
           key name;
           description "Logs for gtp-u";
           leaf name {
             description "Logs for gtp-u";
             type enumeration {
               enum "all" {
                 description "All gtp-u logs";
               }
               enum "dropped" {
                 description "Dropped gtp-u logs";
               }
             }
           }
           uses apply-advanced;
         }
         container rate-limited {
           presence "enable rate-limited";
           description "Dropped for rate-limit";
           uses apply-advanced;
           choice rate-limited-attr {
             case case_1 {
               leaf basic {
                 description "Basic logs";
                 type empty;
               }
             }
             case case_2 {
               leaf detail {
                 description "Detailed logs";
                 type empty;
               }
             }
           }
         }
       }
       container remove-ie {
         presence "enable remove-ie";
         description "Remove information elements";
         uses apply-advanced;
         list version {
           key name;
           description "GTP version";
           leaf name {
             description "Version name";
             type enumeration {
               enum "v1" {
                 description "GTP v1";
               }
             }
           }
           uses apply-advanced;
           list release {
             key name;
             description "Remove information elements by release";
             leaf name {
               description "Release name";
               type enumeration {
                 enum "R6" {
                   description "Release 6";
                 }
                 enum "R7" {
                   description "Release 7";
                 }
                 enum "R8" {
                   description "Release 8";
                 }
                 enum "R9" {
                   description "Release 9";
                 }
               }
             }
             uses apply-advanced;
           }
           list number {
             key name;
             description "Remove information elements by number";
             leaf name {
               type union {
                 type string {
                   pattern "<.*>|$.*";
                 }
                 type uint32 {
                   range "1 .. 255";
                 }
               }
             }
             uses apply-advanced;
           }
         }
       }
       container path-rate-limit {
         description "Limit control messages based on IP pairs";
         uses apply-advanced;
         list message-type {
           key name;
           description "Specific group of control messages";
           leaf name {
             description "Specific group of control messages";
             type enumeration {
               enum "create-req" {
                 description "Limit packet-per-second of GTP create request";
               }
               enum "delete-req" {
                 description "Limit packet-per-second of GTP delete request";
               }
               enum "echo-req" {
                 description "Limit packet-per-minute of GTP echo request";
               }
               enum "other" {
                 description "Limit packet-per-second of all other GTP control messages";
               }
             }
           }
           uses apply-advanced;
           container drop-threshold {
             description "Set drop threshold for path rate limiting";
             uses apply-advanced;
             leaf forward {
               description "Limit messages of forward direction";
               type union {
                 type string {
                   pattern "<.*>|$.*";
                 }
                 type uint32 {
                   range "1 .. 10000";
                 }
               }
             }
             leaf reverse {
               description "Limit messages of reverse direction";
               type union {
                 type string {
                   pattern "<.*>|$.*";
                 }
                 type uint32 {
                   range "1 .. 10000";
                 }
               }
             }
           }
           container alarm-threshold {
             description "Set alarm threshold for path rate limiting";
             uses apply-advanced;
             leaf forward {
               description "Limit messages of forward direction";
               type union {
                 type string {
                   pattern "<.*>|$.*";
                 }
                 type uint32 {
                   range "1 .. 10000";
                 }
               }
             }
             leaf reverse {
               description "Limit messages of reverse direction";
               type union {
                 type string {
                   pattern "<.*>|$.*";
                 }
                 type uint32 {
                   range "1 .. 10000";
                 }
               }
             }
           }
         }
       }
       container drop {
         description "Drop certain type of messages";
         uses apply-advanced;
         list aa-create-pdp {
           key name;
           ordered-by user;
           description "Create AA pdp request/response message";
           leaf name {
             description "GTP version for message";
             type enumeration {
               enum "0" {
                 description "Version 0";
               }
             }
           }
           uses apply-advanced;
         }
         list aa-delete-pdp {
           key name;
           ordered-by user;
           description "Delete AA pdp request/response message";
           leaf name {
             description "GTP version for message";
             type enumeration {
               enum "0" {
                 description "Version 0";
               }
             }
           }
           uses apply-advanced;
         }
         list bearer-resource {
           key name;
           ordered-by user;
           description "Bearer resource command/failure message";
           leaf name {
             description "GTP version for message";
             type enumeration {
               enum "2" {
                 description "Version 2";
               }
             }
           }
           uses apply-advanced;
         }
         list change-notification {
           key name;
           ordered-by user;
           description "Change notification request/response message";
           leaf name {
             description "GTP version for message";
             type enumeration {
               enum "2" {
                 description "Version 2";
               }
             }
           }
           uses apply-advanced;
         }
         list config-transfer {
           key name;
           ordered-by user;
           description "Configuration transfer message";
           leaf name {
             description "GTP version for message";
             type enumeration {
               enum "2" {
                 description "Version 2";
               }
             }
           }
           uses apply-advanced;
         }
         list context {
           key name;
           ordered-by user;
           description "Context request/response/ack message";
           leaf name {
             description "GTP version for message";
             type enumeration {
               enum "2" {
                 description "Version 2";
               }
             }
           }
           uses apply-advanced;
         }
         list create-bearer {
           key name;
           ordered-by user;
           description "Create bearer request/response message";
           leaf name {
             description "GTP version for message";
             type enumeration {
               enum "2" {
                 description "Version 2";
               }
             }
           }
           uses apply-advanced;
         }
         list create-data-forwarding {
           key name;
           ordered-by user;
           description "Create indirect data forwarding tunnel request/response message";
           leaf name {
             description "GTP version for message";
             type enumeration {
               enum "2" {
                 description "Version 2";
               }
             }
           }
           uses apply-advanced;
         }
         list create-pdp {
           key name;
           ordered-by user;
           description "Create pdp request/response message";
           leaf name {
             description "GTP version for message";
             type enumeration {
               enum "0" {
                 description "Version 0";
               }
               enum "1" {
                 description "Version 1";
               }
               enum "all" {
                 description "All versions";
               }
             }
           }
           uses apply-advanced;
         }
         list create-session {
           key name;
           ordered-by user;
           description "Create session request/response message";
           leaf name {
             description "GTP version for message";
             type enumeration {
               enum "2" {
                 description "Version 2";
               }
             }
           }
           uses apply-advanced;
         }
         list create-tnl-forwarding {
           key name;
           ordered-by user;
           description "Create forwarding tunnel request/response message";
           leaf name {
             description "GTP version for message";
             type enumeration {
               enum "2" {
                 description "Version 2";
               }
             }
           }
           uses apply-advanced;
         }
         list cs-paging {
           key name;
           ordered-by user;
           description "CS paging indication message";
           leaf name {
             description "GTP version for message";
             type enumeration {
               enum "2" {
                 description "Version 2";
               }
             }
           }
           uses apply-advanced;
         }
         list data-record {
           key name;
           ordered-by user;
           description "Data record request/response message";
           leaf name {
             description "GTP version for message";
             type enumeration {
               enum "0" {
                 description "Version 0";
               }
               enum "1" {
                 description "Version 1";
               }
               enum "all" {
                 description "All versions";
               }
             }
           }
           uses apply-advanced;
         }
         list delete-bearer {
           key name;
           ordered-by user;
           description "Delete bearer request/response message";
           leaf name {
             description "GTP version for message";
             type enumeration {
               enum "2" {
                 description "Version 2";
               }
             }
           }
           uses apply-advanced;
         }
         list delete-command {
           key name;
           ordered-by user;
           description "Delete bearer command/failure message";
           leaf name {
             description "GTP version for message";
             type enumeration {
               enum "2" {
                 description "Version 2";
               }
             }
           }
           uses apply-advanced;
         }
         list delete-data-forwarding {
           key name;
           ordered-by user;
           description "Delete indirect data forwarding tunnel request/response message";
           leaf name {
             description "GTP version for message";
             type enumeration {
               enum "2" {
                 description "Version 2";
               }
             }
           }
           uses apply-advanced;
         }
         list delete-pdn {
           key name;
           ordered-by user;
           description "Delete PDN connection set request/response message";
           leaf name {
             description "GTP version for message";
             type enumeration {
               enum "2" {
                 description "Version 2";
               }
             }
           }
           uses apply-advanced;
         }
         list delete-pdp {
           key name;
           ordered-by user;
           description "Delete pdp request/response message";
           leaf name {
             description "GTP version for message";
             type enumeration {
               enum "0" {
                 description "Version 0";
               }
               enum "1" {
                 description "Version 1";
               }
               enum "all" {
                 description "All versions";
               }
             }
           }
           uses apply-advanced;
         }
         list delete-session {
           key name;
           ordered-by user;
           description "Delete session request/response message";
           leaf name {
             description "GTP version for message";
             type enumeration {
               enum "2" {
                 description "Version 2";
               }
             }
           }
           uses apply-advanced;
         }
         list detach {
           key name;
           ordered-by user;
           description "Detach notification/ack message";
           leaf name {
             description "GTP version for message";
             type enumeration {
               enum "2" {
                 description "Version 2";
               }
             }
           }
           uses apply-advanced;
         }
         list downlink-notification {
           key name;
           ordered-by user;
           description "Downlink data notification/ack/failure message";
           leaf name {
             description "GTP version for message";
             type enumeration {
               enum "2" {
                 description "Version 2";
               }
             }
           }
           uses apply-advanced;
         }
         list echo {
           key name;
           ordered-by user;
           description "Echo request/response message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
         list error-indication {
           key name;
           ordered-by user;
           description "Error indication message";
           leaf name {
             description "GTP version for message";
             type enumeration {
               enum "0" {
                 description "Version 0";
               }
               enum "1" {
                 description "Version 1";
               }
               enum "all" {
                 description "All versions";
               }
             }
           }
           uses apply-advanced;
         }
         list failure-report {
           key name;
           ordered-by user;
           description "Failure report request/response message";
           leaf name {
             description "GTP version for message";
             type enumeration {
               enum "0" {
                 description "Version 0";
               }
               enum "1" {
                 description "Version 1";
               }
               enum "all" {
                 description "All versions";
               }
             }
           }
           uses apply-advanced;
         }
         list fwd-access {
           key name;
           ordered-by user;
           description "Forward access context notification/ack message";
           leaf name {
             description "GTP version for message";
             type enumeration {
               enum "2" {
                 description "Version 2";
               }
             }
           }
           uses apply-advanced;
         }
         list fwd-relocation {
           key name;
           ordered-by user;
           description "Forward relocation request/response/comp/comp-ack message";
           leaf name {
             description "GTP version for message";
             type enumeration {
               enum "1" {
                 description "Version 1";
               }
               enum "2" {
                 description "Version 2";
               }
               enum "all" {
                 description "All versions";
               }
             }
           }
           uses apply-advanced;
         }
         list fwd-srns-context {
           key name;
           ordered-by user;
           description "Forward SRNS context/context-ack message";
           leaf name {
             description "GTP version for message";
             type enumeration {
               enum "1" {
                 description "Version 1";
               }
             }
           }
           uses apply-advanced;
         }
         list g-pdu {
           key name;
           ordered-by user;
           description "G-PDU (user PDU) message/T-PDU";
           leaf name {
             description "GTP version for message";
             type enumeration {
               enum "0" {
                 description "Version 0";
               }
               enum "1" {
                 description "Version 1";
               }
               enum "all" {
                 description "All versions";
               }
             }
           }
           uses apply-advanced;
         }
         list identification {
           key name;
           ordered-by user;
           description "Identification request/response message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
         list mbms-session-start {
           key name;
           ordered-by user;
           description "MBMS session start request/response message";
           leaf name {
             description "GTP version for message";
             type enumeration {
               enum "1" {
                 description "Version 1";
               }
               enum "2" {
                 description "Version 2";
               }
               enum "all" {
                 description "All versions";
               }
             }
           }
           uses apply-advanced;
         }
         list mbms-session-stop {
           key name;
           ordered-by user;
           description "MBMS session stop request/response message";
           leaf name {
             description "GTP version for message";
             type enumeration {
               enum "1" {
                 description "Version 1";
               }
               enum "2" {
                 description "Version 2";
               }
               enum "all" {
                 description "All versions";
               }
             }
           }
           uses apply-advanced;
         }
         list mbms-session-update {
           key name;
           ordered-by user;
           description "MBMS session update request/response message";
           leaf name {
             description "GTP version for message";
             type enumeration {
               enum "1" {
                 description "Version 1";
               }
               enum "2" {
                 description "Version 2";
               }
               enum "all" {
                 description "All versions";
               }
             }
           }
           uses apply-advanced;
         }
         list modify-bearer {
           key name;
           ordered-by user;
           description "Modify bearer request/response message";
           leaf name {
             description "GTP version for message";
             type enumeration {
               enum "2" {
                 description "Version 2";
               }
             }
           }
           uses apply-advanced;
         }
         list modify-command {
           key name;
           ordered-by user;
           description "Modify bearer command/failure message";
           leaf name {
             description "GTP version for message";
             type enumeration {
               enum "2" {
                 description "Version 2";
               }
             }
           }
           uses apply-advanced;
         }
         list node-alive {
           key name;
           ordered-by user;
           description "Node alive request/response message";
           leaf name {
             description "GTP version for message";
             type enumeration {
               enum "0" {
                 description "Version 0";
               }
               enum "1" {
                 description "Version 1";
               }
               enum "all" {
                 description "All versions";
               }
             }
           }
           uses apply-advanced;
         }
         list note-ms-present {
           key name;
           ordered-by user;
           description "Note MS GPRS present request/response message";
           leaf name {
             description "GTP version for message";
             type enumeration {
               enum "0" {
                 description "Version 0";
               }
               enum "1" {
                 description "Version 1";
               }
               enum "all" {
                 description "All versions";
               }
             }
           }
           uses apply-advanced;
         }
         list pdu-notification {
           key name;
           ordered-by user;
           description "PDU notification requst/response/reject/reject-response message";
           leaf name {
             description "GTP version for message";
             type enumeration {
               enum "0" {
                 description "Version 0";
               }
               enum "1" {
                 description "Version 1";
               }
               enum "all" {
                 description "All versions";
               }
             }
           }
           uses apply-advanced;
         }
         list ran-info {
           key name;
           ordered-by user;
           description "RAN info relay message";
           leaf name {
             description "GTP version for message";
             type enumeration {
               enum "1" {
                 description "Version 1";
               }
               enum "2" {
                 description "Version 2";
               }
               enum "all" {
                 description "All versions";
               }
             }
           }
           uses apply-advanced;
         }
         list redirection {
           key name;
           ordered-by user;
           description "Redirection request/response message";
           leaf name {
             description "GTP version for message";
             type enumeration {
               enum "0" {
                 description "Version 0";
               }
               enum "1" {
                 description "Version 1";
               }
               enum "all" {
                 description "All versions";
               }
             }
           }
           uses apply-advanced;
         }
         list release-access {
           key name;
           ordered-by user;
           description "Release access-bearer request/response message";
           leaf name {
             description "GTP version for message";
             type enumeration {
               enum "2" {
                 description "Version 2";
               }
             }
           }
           uses apply-advanced;
         }
         list relocation-cancel {
           key name;
           ordered-by user;
           description "Relocation cancel request/response message";
           leaf name {
             description "GTP version for message";
             type enumeration {
               enum "1" {
                 description "Version 1";
               }
               enum "2" {
                 description "Version 2";
               }
               enum "all" {
                 description "All versions";
               }
             }
           }
           uses apply-advanced;
         }
         list resume {
           key name;
           ordered-by user;
           description "Resume notification/ack message";
           leaf name {
             description "GTP version for message";
             type enumeration {
               enum "2" {
                 description "Version 2";
               }
             }
           }
           uses apply-advanced;
         }
         list send-route {
           key name;
           ordered-by user;
           description "Send route info request/response message";
           leaf name {
             description "GTP version for message";
             type enumeration {
               enum "0" {
                 description "Version 0";
               }
               enum "1" {
                 description "Version 1";
               }
               enum "all" {
                 description "All versions";
               }
             }
           }
           uses apply-advanced;
         }
         list sgsn-context {
           key name;
           ordered-by user;
           description "SGSN context request/response/ack message";
           leaf name {
             description "GTP version for message";
             type enumeration {
               enum "0" {
                 description "Version 0";
               }
               enum "1" {
                 description "Version 1";
               }
               enum "all" {
                 description "All versions";
               }
             }
           }
           uses apply-advanced;
         }
         list stop-paging {
           key name;
           ordered-by user;
           description "Stop paging indication message";
           leaf name {
             description "GTP version for message";
             type enumeration {
               enum "2" {
                 description "Version 2";
               }
             }
           }
           uses apply-advanced;
         }
         list supported-extension {
           key name;
           ordered-by user;
           description "Supported extension headers notification message";
           leaf name {
             description "GTP version for message";
             type enumeration {
               enum "1" {
                 description "Version 1";
               }
             }
           }
           uses apply-advanced;
         }
         list suspend {
           key name;
           ordered-by user;
           description "Suspend notification/ack message";
           leaf name {
             description "GTP version for message";
             type enumeration {
               enum "2" {
                 description "Version 2";
               }
             }
           }
           uses apply-advanced;
         }
         list trace-session {
           key name;
           ordered-by user;
           description "Trace session activation/deactivation message";
           leaf name {
             description "GTP version for message";
             type enumeration {
               enum "2" {
                 description "Version 2";
               }
             }
           }
           uses apply-advanced;
         }
         list update-bearer {
           key name;
           ordered-by user;
           description "Update bearer request/response message";
           leaf name {
             description "GTP version for message";
             type enumeration {
               enum "2" {
                 description "Version 2";
               }
             }
           }
           uses apply-advanced;
         }
         list update-pdn {
           key name;
           ordered-by user;
           description "Update PDN connection set request/response message";
           leaf name {
             description "GTP version for message";
             type enumeration {
               enum "2" {
                 description "Version 2";
               }
             }
           }
           uses apply-advanced;
         }
         list update-pdp {
           key name;
           ordered-by user;
           description "Update pdp request/response message";
           leaf name {
             description "GTP version for message";
             type enumeration {
               enum "0" {
                 description "Version 0";
               }
               enum "1" {
                 description "Version 1";
               }
               enum "all" {
                 description "All versions";
               }
             }
           }
           uses apply-advanced;
         }
         list ver-not-supported {
           key name;
           ordered-by user;
           description "Version not supported message";
           leaf name {
             description "GTP version for message";
             type enumeration {
               enum "0" {
                 description "Version 0";
               }
               enum "1" {
                 description "Version 1";
               }
               enum "2" {
                 description "Version 2";
               }
               enum "all" {
                 description "All versions";
               }
             }
           }
           uses apply-advanced;
         }
       }
       list apn {
         key name;
         description "GTP Access Point Name (APN) filter";
         leaf name {
           description "Specific APN pattern string";
           type string {
             length "1 .. 64";
           }
         }
         uses apply-advanced;
         list imsi-prefix {
           key name;
           description "Specific filter prefix digits for International Mobile Subscriber Identification(IMSI)";
           leaf name {
             description "IMSI prefix should be * or 5-15 digits";
             type string {
               length "1 .. 15";
             }
           }
           uses apply-advanced;
           container action {
             description "Configure GTP profile APN action";
             uses apply-advanced;
             choice action-c {
               case case_1 {
                 leaf pass {
                   description "Pass all selection modes for this APN";
                   type empty;
                 }
               }
               case case_2 {
                 leaf drop {
                   description "Drop all selection modes for this APN";
                   type empty;
                 }
               }
               case case_3 {
                 container selection {
                   presence "enable selection";
                   description "Allowed selection modes for this APN";
                   uses apply-advanced;
                   leaf ms {
                     description "Mobile Station selection mode";
                     type empty;
                   }
                   leaf net {
                     description "Network selection mode";
                     type empty;
                   }
                   leaf vrf {
                     description "Subscriber verified mode";
                     type empty;
                   }
                 }
               }
             }
           }
         }
       }
       leaf restart-path {
         description "Restart GTP paths";
         type enumeration {
           enum "echo" {
             description "Restart GTP paths by detecting restart number stored in the Echo messages";
           }
           enum "create" {
             description "Restart GTP paths by detecting restart number stored in the Create messages";
           }
           enum "all" {
             description "Restart GTP paths by detecting restart number stored in the Echo or Create messages";
           }
         }
       }
       leaf seq-number-validated {
         description "Validate G-PDU sequence number";
         type empty;
       }
       leaf gtp-in-gtp-denied {
         description "Deny nested GTP";
         type empty;
       }
       leaf u-tunnel-validated {
         description "Validate GTP-u tunnel";
         type empty;
       }
       leaf end-user-address-validated {
         description "Validate end user address";
         type empty;
       }
       leaf req-timeout {
         description "Request message timeout, default timeout value 5 seconds";
         units "second";
         type union {
           type string {
             pattern "<.*>|$.*";
           }
           type uint8 {
             range "1 .. 30";
           }
         }
       }
       leaf handover-on-roaming-intf {
         description "Enable tunnel setup by Handover messages on roaming interface";
         type empty;
       }
       container handover-group {
         description "SGSN handover group configuration";
         uses apply-advanced;
         leaf group-name {
           description "SGSN handover group name";
           type string {
             length "1 .. 23";
           }
         }
       }
       leaf listening-mode {
         description "Enable listening-mode for GTP inspection";
         type empty;
       }
       container ne-group {
         description "IP validation check for NE group configuration";
         uses apply-advanced;
         leaf group-name {
           description "GTP ip group name";
           type string {
             length "1 .. 23";
           }
         }
       }
       container ue-group {
         description "End User IP validation check for UE group configuration";
         uses apply-advanced;
         leaf group-name {
           description "GTP ip group name";
           type string {
             length "1 .. 23";
           }
         }
       }
       container must-ie-v1 {
         description "GTPv1 Must IE check configuration";
         uses apply-advanced;
         leaf msgie-prf-v1-name {
           description "GTPv1 message-ie profile name";
           type string {
             length "1 .. 23";
           }
         }
       }
       container must-ie-v2 {
         description "GTPv2 Must IE check configuration";
         uses apply-advanced;
         leaf msgie-prf-v2-name {
           description "GTPv2 message-ie profile name";
           type string {
             length "1 .. 23";
           }
         }
       }
       container remove-ie-v1 {
         description "GTPv1 IE Removal configuration";
         uses apply-advanced;
         leaf ieset-name {
           description "GTP ie-set name";
           type string {
             length "1 .. 23";
           }
         }
       }
       container remove-ie-v2 {
         description "GTPv2 IE Removal configuration";
         uses apply-advanced;
         leaf ieset-name {
           description "GTP ie-set name";
           type string {
             length "1 .. 23";
           }
         }
       }
       choice apn-control-c {
         case case_1 {
           container apn-control {
             description "GTP per APN control";
             uses apply-advanced;
             leaf apn-ctrl-name {
               description "APN control profile name";
               type string {
                 length "1 .. 23";
               }
             }
           }
         }
         case case_2 {
           container apn-control-group {
             description "GTP per APN control group";
             uses apply-advanced;
             leaf apn-ctrl-grp-name {
               description "APN control group name";
               type string {
                 length "1 .. 23";
               }
             }
           }
         }
       }
     }
     container traceoptions {
       description "Trace options for GPRS tunneling protocol";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "parser" {
               description "Trace parser events";
             }
             enum "chassis-cluster" {
               description "Trace chassis cluster events";
             }
             enum "gsn" {
               description "Trace gsn events";
             }
             enum "jmpi" {
               description "Trace jmpi events";
             }
             enum "tnl" {
               description "Trace tnl events";
             }
             enum "req" {
               description "Trace req events";
             }
             enum "path" {
               description "Trace path events";
             }
             enum "all" {
               description "Trace everything";
             }
           }
         }
       }
       container trace-level {
         description "GTP trace level";
         uses apply-advanced;
         choice level {
           case case_1 {
             leaf error {
               description "Match error conditions";
               type empty;
             }
           }
           case case_2 {
             leaf warning {
               description "Match warning messages";
               type empty;
             }
           }
           case case_3 {
             leaf notice {
               description "Match conditions that should be handled specially";
               type empty;
             }
           }
           case case_4 {
             leaf info {
               description "Match informational messages";
               type empty;
             }
           }
           case case_5 {
             leaf verbose {
               description "Match verbose messages";
               type empty;
             }
           }
         }
       }
     }
     container handover-default {
       description "Set handover default deny";
       uses apply-advanced;
       leaf deny {
         description "Handover default deny";
         type empty;
       }
     }
     list ip-group {
       key name;
       description "Set GTP IP group";
       leaf name {
         description "Set ip group name";
         type string {
           length "1 .. 23";
         }
       }
       uses apply-advanced;
       list address-book {
         key name;
         description "Set addreess book";
         leaf name {
           description "Set address book name";
           type string {
             length "1 .. 63";
           }
         }
         uses apply-advanced;
         container address-set {
           description "Set address set";
           uses apply-advanced;
           leaf set-name {
             description "Set address set name";
             type string {
               length "1 .. 63";
             }
           }
         }
       }
     }
     list ie-set {
       key name;
       description "Set GTP IE set profile";
       max-elements 20;
       leaf name {
         description "Set GTP IE set profile name";
         type string {
           length "1 .. 23";
         }
       }
       uses apply-advanced;
       list ie {
         key name;
         description "Set IE number";
         leaf name {
           description "Set IE number";
           type union {
             type string {
               pattern "<.*>|$.*";
             }
             type uint8 {
               range "1 .. 255";
             }
           }
         }
         uses apply-advanced;
       }
     }
     list message-ie-profile-v1 {
       key name;
       description "Set GTPv1 message IE profile";
       max-elements 10;
       leaf name {
         description "Set GTPv1 message IE profile name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
         list ie {
           key name;
           description "Set IE number";
           leaf name {
             description "Set IE number";
             type union {
               type string {
                 pattern "<.*>|$.*";
               }
               type uint8 {
                 range "1 .. 255";
               }
             }
           }
           uses apply-advanced;
         }
       }
     }
     list grouped-ie-profile {
       key name;
       description "Set GTP grouped IE filter profile";
       max-elements 100;
       leaf name {
         description "Set GTP grouped IE filter profile name";
         type string {
           length "1 .. 23";
         }
       }
       uses apply-advanced;
       list ie {
         key name;
         description "Set IE number";
         uses ie-filter-object;
       }
     }
     list message-ie-profile-v2 {
       key name;
       description "Set GTP message IE filter profile";
       max-elements 10;
       leaf name {
         description "Set message IE filter profile name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
         list ie {
           key name;
           description "Set IE number";
           uses ie-filter-object;
         }
       }
     }
     list message-list {
       key name;
       description "Set message list";
       max-elements 10;
       leaf name {
         description "Set message list name";
         type string {
           length "1 .. 23";
         }
       }
       uses apply-advanced;
       list message {
         key name;
         description "Set message type";
         leaf name {
           description "Set message type";
           type union {
             type string {
               pattern "<.*>|$.*";
             }
             type uint8 {
               range "1 .. 255";
             }
           }
         }
         uses apply-advanced;
       }
     }
     list rate-limit {
       key name;
       description "Limiting message rate";
       leaf name {
         description "Rate limit policy name";
         type enumeration {
           enum "default" {
             description "Default rate limit policy name";
           }
         }
       }
       uses apply-advanced;
       container message {
         description "GTP limited message type";
         uses message-object;
       }
     }
     list apn-control {
       key name;
       description "GTP APN control profile";
       max-elements 1024;
       leaf name {
         description "APN control profile name";
         type string {
           length "1 .. 23";
         }
       }
       uses apply-advanced;
       container apn {
         description "APN of the APN control profile";
         uses apply-advanced;
         leaf apn-string {
           description "APN string";
           type string {
             length "1 .. 100";
           }
         }
       }
       container rate-limit {
         description "APN controlled rate-limit";
         presence "enable rate-limit";
         uses rate-limit-object;
       }
     }
     list apn-control-group {
       key name;
       description "GTP APN control profile group";
       max-elements 1024;
       leaf name {
         description "APN control profile group name";
         type string {
           length "1 .. 23";
         }
       }
       uses apply-advanced;
       list apn-control {
         key name;
         description "APN control profile";
         leaf name {
           description "APN control profile name";
           type string {
             length "1 .. 23";
           }
         }
         uses apply-advanced;
       }
     }
   }
   grouping ha-object {
     uses apply-advanced;
     container aws {
       uses apply-advanced;
       choice service-ctrl {
         case case_1 {
           leaf eip-based {
             description "EIP";
             type empty;
           }
         }
       }
       container peer-liveliness {
         presence "enable peer-liveliness";
         description "Configure peer-liveliness probe method";
         uses apply-advanced;
         container probe-ip {
           description "Using IP for activeness probe";
           leaf destination-ip {
             description "Destination IPv4 address for activeness probe";
             type jt:ipv4addr;
           }
           leaf source-ip {
             description "Source IPV4 address for activeness probe";
             type jt:ipv4addr;
           }
           leaf routing-instance {
             description "Routing instance name";
             type string;
           }
         }
       }
     }
   }
   grouping idp-policy-type {
     leaf name {
       description "IDP policy name";
       type string;
     }
     container rulebase-ips {
       description "IPS rulebase";
       uses apply-advanced;
       list rule {
         key name;
         ordered-by user;
         description "Configure IPS rule";
         leaf name {
           description "Rule name";
           type string;
         }
         uses apply-advanced;
         leaf description {
           description "Rule description";
           type string;
         }
         container match {
           description "Rule match criteria";
           uses apply-advanced;
           leaf from-zone {
             description "Match from zone";
             default "any";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
               leaf-list source-prefix {
                 ordered-by user;
                 description "Match source address";
                 type jt:ipv4prefix;
               }
             }
             case case_4 {
               leaf-list source-prefix-except {
                 ordered-by user;
                 description "Don't match source address";
                 type jt:ipv4prefix;
               }
             }
           }
           leaf to-zone {
             description "Match to zone";
             default "any";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
               leaf-list destination-prefix {
                 ordered-by user;
                 description "Match destination address";
                 type jt:ipv4prefix;
               }
             }
             case case_4 {
               leaf-list destination-prefix-except {
                 ordered-by user;
                 description "Don't match destination address";
                 type jt:ipv4prefix;
               }
             }
           }
           leaf application {
             description "Specify application or application-set name to match";
             type string;
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
         container then {
           uses apply-advanced;
           container action {
             choice action {
               case case_1 {
                 leaf no-action {
                   description "No action";
                   type empty;
                 }
               }
               case case_2 {
                 leaf ignore-connection {
                   description "Ignore";
                   type empty;
                 }
               }
               case case_3 {
                 container mark-diffserv {
                   description "Mark differentiated services codepoint (DSCP)";
                   uses apply-advanced;
                   leaf codepoint {
                     description "Codepoint value";
                     type union {
                       type string {
                         pattern "<.*>|$.*";
                       }
                       type uint32 {
                         range "0 .. 63";
                       }
                     }
                   }
                 }
               }
               case case_4 {
                 container class-of-service {
                   description "Classification of traffic based on class-of-service";
                   uses apply-advanced;
                   leaf forwarding-class {
                     description "Forwarding class for outgoing packets";
                     type string {
                     }
                   }
                   leaf dscp-code-point {
                     description "Differentiated services code point value";
                     type union {
                       type string {
                         pattern "<.*>|$.*";
                       }
                       type uint32 {
                         range "0 .. 63";
                       }
                     }
                   }
                 }
               }
               case case_5 {
                 leaf drop-packet {
                   description "Drop packet";
                   type empty;
                 }
               }
               case case_6 {
                 leaf drop-connection {
                   description "Drop connection";
                   type empty;
                 }
               }
               case case_7 {
                 leaf close-client {
                   description "Close client";
                   type empty;
                 }
               }
               case case_8 {
                 leaf close-server {
                   description "Close server";
                   type empty;
                 }
               }
               case case_9 {
                 leaf close-client-and-server {
                   description "Close client and server";
                   type empty;
                 }
               }
               case case_10 {
                 leaf recommended {
                   description "Recommended";
                   type empty;
                 }
               }
             }
           }
           container ip-action {
             uses apply-advanced;
             choice ip-action {
               case case_1 {
                 leaf ip-notify {
                   description "Notify about future traffic";
                   type empty;
                 }
               }
               case case_2 {
                 leaf ip-close {
                   description "Close future connections";
                   type empty;
                 }
               }
               case case_3 {
                 leaf ip-block {
                   description "Block future connections";
                   type empty;
                 }
               }
             }
             leaf target {
               type enumeration {
                 enum "service" {
                   description "Match source, destination, dst-port and protocol";
                 }
                 enum "source-zone-address" {
                   description "Match source-zone and source-address";
                 }
                 enum "source-address" {
                   description "Match source";
                 }
                 enum "destination-address" {
                   description "Match destination";
                 }
                 enum "zone-service" {
                   description "Match source-zone, destination, dst-port, protocol";
                 }
                 enum "source-zone" {
                   description "Match source-zone";
                 }
               }
             }
             leaf log {
               description "Log IP action taken";
               type empty;
             }
             leaf log-create {
               description "Log IP action creation";
               type empty;
             }
             leaf timeout {
               description "Number of seconds IP action should remain effective";
               type union {
                 type string {
                   pattern "<.*>|$.*";
                 }
                 type uint32 {
                   range "0 .. 64800";
                 }
               }
             }
             leaf refresh-timeout {
               description "Refresh timeout when future connections match installed ip-action filter";
               type empty;
             }
           }
           container notification {
             presence "enable notification";
             description "Configure notification/logging options";
             uses apply-advanced;
             container log-attacks {
               presence "enable log-attacks";
               description "Enable attack logging";
               uses apply-advanced;
               leaf alert {
                 description "Set alert flag in attack log";
                 type empty;
               }
             }
             container packet-log {
               presence "enable packet-log";
               uses apply-advanced;
               leaf pre-attack {
                 description "No of packets to capture before attack";
                 default "1";
                 type union {
                   type string {
                     pattern "<.*>|$.*";
                   }
                   type uint32 {
                     range "1 .. 255";
                   }
                 }
               }
               leaf post-attack {
                 description "No of packets to capture after attack";
                 type union {
                   type string {
                     pattern "<.*>|$.*";
                   }
                   type uint32 {
                     range "0 .. 255";
                   }
                 }
               }
               leaf post-attack-timeout {
                 description "Timeout (seconds) after attack before stopping packet capture";
                 default "5";
                 type union {
                   type string {
                     pattern "<.*>|$.*";
                   }
                   type uint32 {
                     range "0 .. 1800";
                   }
                 }
               }
             }
           }
           leaf severity {
             description "Set rule severity level";
             type enumeration {
               enum "info" {
               }
               enum "warning" {
               }
               enum "minor" {
               }
               enum "major" {
               }
               enum "critical" {
               }
             }
           }
           container application-services {
             description "Enable application services for this rule";
             container security-intelligence {
               description "Generate security intellegence feeds";
               leaf add-attacker-ip-to-feed {
                 description "Specify the desired feed-name";
                 type string {
                   length "1 .. 64";
                 }
               }
               leaf add-target-ip-to-feed {
                 description "Specify the desired feed-name";
                 type string {
                   length "1 .. 64";
                 }
               }
             }
           }
         }
         leaf terminal {
           description "Set/Unset terminal flag";
           type empty;
         }
       }
     }
     container rulebase-exempt {
       description "Exempt rulebase";
       uses apply-advanced;
       list rule {
         key name;
         ordered-by user;
         description "Configure exempt rule";
         leaf name {
           description "Rule name";
           type string;
         }
         uses apply-advanced;
         leaf description {
           description "Rule description";
           type string;
         }
         container match {
           description "Rule match criteria";
           uses apply-advanced;
           leaf from-zone {
             description "Match from zone";
             default "any";
             type string;
           }
           choice source {
             case case_1 {
               leaf-list source-address {
                 ordered-by user;
                 description "Match source address";
                 type string;
               }
             }
             case case_2 {
               leaf-list source-except {
                 ordered-by user;
                 description "Don't match source address";
                 type string;
               }
             }
             case case_3 {
               leaf-list source-prefix {
                 ordered-by user;
                 description "Match source address";
                 type jt:ipv4prefix;
               }
             }
             case case_4 {
               leaf-list source-prefix-except {
                 ordered-by user;
                 description "Don't match source address";
                 type jt:ipv4prefix;
               }
             }
           }
           leaf to-zone {
             description "Match to zone";
             default "any";
             type string;
           }
           choice destination {
             case case_1 {
               leaf-list destination-address {
                 ordered-by user;
                 description "Match destination address";
                 type string;
               }
             }
             case case_2 {
               leaf-list destination-except {
                 ordered-by user;
                 description "Don't match destination address";
                 type string;
               }
             }
             case case_3 {
               leaf-list destination-prefix {
                 ordered-by user;
                 description "Match destination address";
                 type jt:ipv4prefix;
               }
             }
             case case_4 {
               leaf-list destination-prefix-except {
                 ordered-by user;
                 description "Don't match destination address";
                 type jt:ipv4prefix;
               }
             }
           }
           container attacks {
             description "Match attack objects";
             uses apply-advanced;
             leaf-list custom-attacks {
               ordered-by user;
               description "Custom attacks";
               type string;
             }
             leaf-list custom-attack-groups {
               ordered-by user;
               description "Custom attack groups";
               type string;
             }
             leaf-list dynamic-attack-groups {
               ordered-by user;
               description "Dynamic attack groups";
               type string;
             }
             leaf-list predefined-attacks {
               ordered-by user;
               description "Predefined attacks";
               type string;
             }
             leaf-list predefined-attack-groups {
               ordered-by user;
               description "Predefined attack groups";
               type string;
             }
           }
         }
       }
     }
   }
   grouping idpd-traceoptions-type {
     description "Trace options for idpd";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         description "Flag name to include in trace output";
         type enumeration {
           enum "all" {
             description "All events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
   grouping ids-option-type {
     description "Configure screen object";
     leaf name {
       description "Screen object name";
       type string {
         length "1 .. 64";
       }
     }
     uses apply-advanced;
     leaf description {
       description "Text description of screen";
       type string {
         length "1 .. 900";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       container block-frag {
         presence "enable block-frag";
         description "Enable ip fragment blocking ids option";
         uses apply-advanced;
         leaf-list white-list {
           ordered-by user;
           description "Configure ip block fragmentation white list group name";
           type string;
           max-elements 2;
         }
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       leaf syn-defense {
         description "Enable tcp syn-defense";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
     }
   }
   grouping by-protocol-object-type {
     description "Configure limit-session on the basis of protocol";
     uses apply-advanced;
     container tcp {
       description "Configure limit-session on the basis of TCP";
       presence "enable tcp";
       uses by-protocol-object-limit-tcp-type;
     }
     container udp {
       description "Configure limit-session on the basis of UDP";
       presence "enable udp";
       uses by-protocol-object-limit-type;
     }
     container icmp {
       description "Configure limit-session on the basis of ICMP";
       presence "enable icmp";
       uses by-protocol-object-limit-type;
     }
   }
   grouping by-protocol-object-limit-tcp-type {
     description "Configure the limit-session for tcp protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
     container syn-cookie {
       presence "enable syn-cookie";
       description "Configure syn-cookie parameters";
       uses apply-advanced;
       leaf mss {
         description "TCP maximum segment size";
         type union {
           type string {
             pattern "<.*>|$.*";
           }
           type uint32 {
             range "64 .. 65535";
           }
         }
       }
       leaf threshold-rate {
         description "TCP-SYN cps rate to trigger SYN-COOKIE";
         type union {
           type string {
             pattern "<.*>|$.*";
           }
           type uint32 {
             range "1 .. 4294967295";
           }
         }
       }
       leaf threshold-num {
         description "Number of sessions to trigger SYN-COOKIE";
         type union {
           type string {
             pattern "<.*>|$.*";
           }
           type uint32;
         }
       }
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
   }
   grouping ids-wlist-type {
     leaf name {
       description "White-list name";
       type string {
         length "1 .. 32";
       }
     }
     uses apply-advanced;
     leaf-list address {
       ordered-by user;
       description "Address";
       type jt:ipprefix;
       max-elements 32;
     }
   }
   grouping ie-filter-object {
     leaf name {
       description "Set IE number";
       type union {
         type string {
           pattern "<.*>|$.*";
         }
         type uint8 {
           range "1 .. 255";
         }
       }
     }
     uses apply-advanced;
     list instance {
       key name;
       description "Set instance";
       leaf name {
         description "Set instance number";
         type union {
           type string {
             pattern "<.*>|$.*";
           }
           type uint8 {
             range "0 .. 11";
           }
         }
       }
       uses apply-advanced;
       container grouped-ie-profile {
         description "Set GTP IE filter for grouped IE";
         uses apply-advanced;
         leaf grpie-prf-name {
           description "Set grouped IE profile";
           type string {
             length "1 .. 23";
           }
         }
       }
     }
   }
   grouping jsf_application_traffic_control_rule_set_type {
     description "Define service application traffic rule-set reference";
     uses apply-advanced;
     leaf rule-set {
       description "Service rule-set name";
       type string {
         length "1 .. 64";
       }
     }
   }
   grouping juniper-enhanced-category-type {
     description "Juniper enhanced category type";
     leaf name {
       description "Name of Juniper enhanced category";
       type string {
         length "1 .. 59";
       }
     }
     uses apply-advanced;
     leaf action {
       description "Action to perform when web traffic matches category";
       type enumeration {
         enum "permit" {
         }
         enum "log-and-permit" {
         }
         enum "block" {
         }
         enum "quarantine" {
         }
       }
     }
     leaf custom-message {
       description "Custom message";
       type string;
     }
   }
   grouping juniper-enhanced-server {
     description "Server handling categorization requests";
     uses apply-advanced;
     leaf host {
       description "Server host IP address or string host name";
       type string;
     }
     leaf port {
       description "Server port";
       type union {
         type string {
           pattern "<.*>|$.*";
         }
         type uint16 {
           range "1 .. 65535";
         }
       }
     }
     leaf proxy-profile {
       description "Proxy profile";
       type string {
         length "1 .. 64";
       }
     }
     leaf routing-instance {
       description "Routing instance name";
       type string;
     }
     leaf source-address {
       description "Source ip address used to connect server";
       type jt:ipaddr;
     }
   }
   grouping juniper-enhanced-site-reputation-setting {
     description "Juniper enhanced site reputation settings";
     uses apply-advanced;
     leaf very-safe {
       description "Action when site reputation is very safe";
       type enumeration {
         enum "permit" {
         }
         enum "log-and-permit" {
         }
         enum "block" {
         }
         enum "quarantine" {
         }
       }
     }
     leaf moderately-safe {
       description "Action when site reputation is moderately safe";
       type enumeration {
         enum "permit" {
         }
         enum "log-and-permit" {
         }
         enum "block" {
         }
         enum "quarantine" {
         }
       }
     }
     leaf fairly-safe {
       description "Action when site reputation is fairly safe";
       type enumeration {
         enum "permit" {
         }
         enum "log-and-permit" {
         }
         enum "block" {
         }
         enum "quarantine" {
         }
       }
     }
     leaf suspicious {
       description "Action when site reputation is suspicious";
       type enumeration {
         enum "permit" {
         }
         enum "log-and-permit" {
         }
         enum "block" {
         }
         enum "quarantine" {
         }
       }
     }
     leaf harmful {
       description "Action when site reputation is harmful";
       type enumeration {
         enum "permit" {
         }
         enum "log-and-permit" {
         }
         enum "block" {
         }
         enum "quarantine" {
         }
       }
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
     list host {
       key name;
       ordered-by user;
       max-elements 10;
       leaf name {
         description "Name of host to notify";
         type string {
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           type jt:ipaddr;
         }
         leaf vrf-name {
           description "Routing instance name for tcp logging";
           type string;
         }
         leaf ssl-profile {
           description "SSL profile name for tcp logging";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
         enum "stream-event" {
           description "Process security logs in both forwarding plane and control plane";
         }
       }
     }
     leaf event-rate {
       description "Control plane event rate";
       units "logs per second";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
       }
     }
     leaf escape {
       description "Enable escape defined by RFC5424 for the sd and binary format logs";
       type empty;
     }
     container time-format {
       description "Configure year or millisecond for syslog";
       uses time-format-object;
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
       uses apply-advanced;
       container logs-per-table {
         presence "enable logs-per-table";
         description "Log number per table in database";
         uses apply-advanced;
         leaf session-all {
           description "Log number of session";
           type union {
             type string {
               pattern "<.*>|$.*";
             }
             type uint32;
           }
         }
         leaf screen {
           description "Log number of screen";
           type union {
             type string {
               pattern "<.*>|$.*";
             }
             type uint32;
           }
         }
         leaf idp {
           description "Log number of idp";
           type union {
             type string {
               pattern "<.*>|$.*";
             }
             type uint32;
           }
         }
         leaf utm {
           description "Log number of utm";
           type union {
             type string {
               pattern "<.*>|$.*";
             }
             type uint32;
           }
         }
         leaf ipsec-vpn {
           description "Log number of ipsec-vpn";
           type union {
             type string {
               pattern "<.*>|$.*";
             }
             type uint32;
           }
         }
         leaf sky {
           description "Log number of sky";
           type union {
             type string {
               pattern "<.*>|$.*";
             }
             type uint32;
           }
         }
       }
       leaf table-lifetime {
         description "Table lifetime day(s)";
         default "90";
         type union {
           type string {
             pattern "<.*>|$.*";
           }
           type uint32 {
             range "0 .. 365";
           }
         }
       }
       container table-mode {
         presence "enable table-mode";
         description "Report table mode";
         uses apply-advanced;
         leaf dense {
           description "Applicable when massive log and long duration";
           type empty;
         }
       }
       container database-filter {
         presence "enable database-filter";
         description "Check the logs whether should be inserted into database";
         uses apply-advanced;
         list event-category {
           key name;
           ordered-by user;
           description "Filter by event-category";
           leaf name {
             description "Name";
             type enumeration {
               enum "session" {
                 description "Session log";
               }
               enum "screen" {
                 description "Screen log";
               }
               enum "idp" {
                 description "IDP log";
               }
               enum "webfilter" {
                 description "Webfilter log";
               }
               enum "content-filter" {
                 description "Content-filter log";
               }
               enum "anti-virus" {
                 description "Antivirus log";
               }
               enum "anti-spam" {
                 description "Anti-spam log";
               }
               enum "ipsec" {
                 description "IPsec VPN log";
               }
               enum "sky" {
                 description "Sky ATP log";
               }
               enum "secintel" {
                 description "Secintel log";
               }
               enum "icap" {
                 description "ICAP log";
               }
               enum "ssl-proxy" {
                 description "SSL proxy log";
               }
               enum "dnsf" {
                 description "DNSF log";
               }
               enum "session-create" {
                 description "Session create log";
               }
               enum "session-close" {
                 description "Session close log";
               }
               enum "session-deny" {
                 description "Session deny log";
               }
             }
           }
           uses apply-advanced;
         }
         leaf exclude {
           description "Exclude the logs";
           type empty;
         }
       }
     }
     choice source {
       case case_1 {
         leaf source-address {
           description "Source ip address used when exporting security logs";
           type jt:ipaddr;
         }
       }
       case case_2 {
         leaf source-interface {
           description "Source interface used when exporting security logs";
           type union {
             type jt:interface-name;
             type string {
               pattern "<.*>|$.*";
             }
           }
         }
       }
     }
     container transport {
       presence "enable transport";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       type string {
       }
     }
     list local-category {
       key name;
       ordered-by user;
       description "Selects the type of events that may be logged locally";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session open and close events are logged";
           }
           enum "session-open" {
             description "Session open events are logged";
           }
           enum "session-close" {
             description "Session close events are logged";
           }
           enum "urlf" {
             description "URLF events are logged";
           }
           enum "ha" {
             description "Stateful High-Availability open and close events are logged";
           }
           enum "ha-open" {
             description "Stateful High-Availability open events are logged";
           }
           enum "ha-close" {
             description "Stateful High-Availability close events are logged";
           }
           enum "pcp" {
             description "PCP logs";
           }
           enum "dnsf" {
             description "DNSF";
           }
         }
       }
       uses apply-advanced;
     }
     leaf root-streaming {
       description "Logs will be streamed from the Root LSYS";
       type empty;
     }
     list stream {
       key name;
       ordered-by user;
       description "Set security log stream settings";
       max-elements 8;
       leaf name {
         description "Name of security log stream";
         type string {
           length "1 .. 63";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
         }
       }
       list category {
         key name;
         ordered-by user;
         description "Selects the type of events that may be logged";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session open and close events are logged";
             }
             enum "session-open" {
               description "Session open events are logged";
             }
             enum "session-close" {
               description "Session close events are logged";
             }
             enum "urlf" {
               description "URLF events are logged";
             }
             enum "ha" {
               description "Stateful High-Availability open and close events are logged";
             }
             enum "ha-open" {
               description "Stateful High-Availability open events are logged";
             }
             enum "ha-close" {
               description "Stateful High-Availability close events are logged";
             }
             enum "pcp" {
               description "PCP logs";
             }
             enum "dnsf" {
               description "DNSF";
             }
           }
         }
         uses apply-advanced;
       }
       list filter {
         key name;
         ordered-by user;
         description "Selects the filter to filter the logs to be logged";
         leaf name {
           type enumeration {
             enum "threat-attack" {
               description "Threat-attack security events are logged";
             }
           }
         }
         uses apply-advanced;
       }
       container host {
         description "Destination to send security logs to";
         uses host-object;
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         description "Security log file options for logs in local file";
         uses apply-advanced;
         leaf localfilename {
           description "Name of local log file";
           type string {
             length "1 .. 256";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32;
           }
         }
         leaf allow-duplicates {
           description "To disable log consolidation";
           type empty;
         }
       }
       container transport {
         presence "enable transport";
         description "Set security log transport settings";
         uses apply-advanced;
         leaf tcp-connections {
           description "Set tcp connection number per-stream";
           type union {
             type string {
               pattern "<.*>|$.*";
             }
             type uint32 {
               range "1 .. 5";
             }
           }
         }
         leaf protocol {
           description "Set security log transport protocol for the device";
           type enumeration {
             enum "udp" {
               description "UDP transfer for log";
             }
             enum "tcp" {
               description "TCP transfer for log";
             }
             enum "tls" {
               description "TLS transfer for log";
             }
           }
         }
         leaf tls-profile {
           description "TLS profile";
           type string;
         }
       }
       container time-format {
         description "Configure year or millisecond for syslog";
         uses time-format-object;
       }
       leaf source-address {
         description "Source ip address used when exporting security logs";
         type jt:ipaddr;
       }
     }
     container file {
       description "Security log file options for logs in binary/protobuf format";
       uses apply-advanced;
       leaf filename {
         description "Name of log file";
         type string {
           length "1 .. 256";
         }
       }
       leaf size {
         description "Maximum size of log file in megabytes";
         type union {
           type string {
             pattern "<.*>|$.*";
           }
           type uint32 {
             range "1 .. 10";
           }
         }
       }
       leaf path {
         description "Path to log files";
         type string {
           length "1 .. 256";
         }
       }
       leaf files {
         description "Maximum number of log files";
         type union {
           type string {
             pattern "<.*>|$.*";
           }
           type uint32 {
             range "2 .. 10";
           }
         }
       }
     }
     container apply {
       description "Apply settings from other features";
       uses apply-advanced;
       leaf dscp-code-point {
         description "Apply setting class-of-service host-outbound-traffic dscp-code-point";
         type empty;
       }
     }
     container traceoptions {
       description "Security log daemon trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
     list profile {
       key name;
       ordered-by user;
       description "Security log profile setting";
       max-elements 10;
       leaf name {
         description "Name of security log profile";
         type string {
           length "1 .. 63";
         }
       }
       uses apply-advanced;
       list stream-name {
         key name;
         ordered-by user;
         description "Use which stream ";
         max-elements 4;
         leaf name {
           description "Name of the stream";
           type string;
         }
         uses apply-advanced;
       }
       container category {
         presence "enable category";
         description "Selects the category of events for the profile";
         uses apply-advanced;
         container session {
           presence "enable session";
           description "Select session category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container webfilter {
           presence "enable webfilter";
           description "Select webfilter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antivirus {
           presence "enable antivirus";
           description "Select antivirus category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container content-filter {
           presence "enable content-filter";
           description "Select content-filter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antispam {
           presence "enable antispam";
           description "Select antispam category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container idp {
           presence "enable idp";
           description "Select idp category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container secintel {
           presence "enable secintel";
           description "Select secintel category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container aamw {
           presence "enable aamw";
           description "Select aamw category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container ssl-proxy {
           presence "enable ssl-proxy";
           description "Select ssl-proxy category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container apptrack {
           presence "enable apptrack";
           description "Select apptrack category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
       }
       container default-profile {
         presence "enable default-profile";
         uses apply-advanced;
         leaf activate {
           description "Set this profile as default profile";
           type empty;
         }
       }
       container template {
         presence "enable template";
         description "Select the template for the profile";
         uses apply-advanced;
         choice template-id {
           case case_1 {
             leaf traditional-firewall {
               description "Traditional-firewall";
               type empty;
             }
           }
           case case_2 {
             leaf unified-ngfw {
               description "Unified-ngfw";
               type empty;
             }
           }
           case case_3 {
             leaf sd-wan {
               description "Sd-wan";
               type empty;
             }
           }
         }
       }
     }
   }
   grouping host-object {
     uses apply-advanced;
     leaf ipaddr {
       description "IP address/Host name";
       type string {
         length "1 .. 256";
       }
     }
     leaf port {
       description "Host port number";
       type union {
         type uint16;
         type string {
           pattern "<.*>|$.*";
         }
       }
     }
     leaf routing-instance {
       description "Routing-instance name";
       type string;
     }
     leaf log-tag {
       description "Tag included in logs to this host";
       type string {
       }
     }
   }
   grouping logical-system-type {
     description "Logical system name";
     leaf name {
       description "Logical system name";
       type string;
     }
     uses apply-advanced;
     leaf max-sessions {
       description "Max number of IDP sessions";
       type union {
         type uint32;
         type string {
           pattern "<.*>|$.*";
         }
       }
     }
   }
   grouping macro-data-type {
     leaf name {
       description "Keyword part of the keyword-value pair";
       type string;
     }
     leaf value {
       description "Value part of the keyword-value pair";
       type string;
     }
   }
   grouping message-object {
     uses apply-advanced;
     container v0 {
       description "GTPv0 message type";
       uses apply-advanced;
       leaf msg-list-name {
         description "GTP message list name";
         type string {
           length "1 .. 23";
         }
       }
     }
     container v1 {
       description "GTPv1 message type";
       uses apply-advanced;
       leaf msg-list-name {
         description "GTP message list name";
         type string {
           length "1 .. 23";
         }
       }
     }
     container v2 {
       description "GTPv2 message type";
       uses apply-advanced;
       leaf msg-list-name {
         description "GTP message list name";
         type string {
           length "1 .. 23";
         }
       }
     }
   }
   grouping mime-list-type {
     description "Configure mime-list object";
     leaf name {
       description "Configure name of mime-list object";
       type string {
         length "1 .. 40";
       }
     }
     uses apply-advanced;
     leaf-list value {
       ordered-by user;
       description "Configure MIME value";
       type string {
         length "1 .. 249";
       }
     }
   }
   grouping mirror-filter-type {
     description "Secuirty mirror filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf source-port {
       description "Match TCP/UDP source port";
       type string;
     }
     leaf destination-port {
       description "Match TCP/UDP destination port";
       type string;
     }
     leaf interface-in {
       description "Incoming Logical interface";
       type union {
         type jt:interface-name;
         type string {
           pattern "<.*>|$.*";
         }
       }
     }
     leaf interface-out {
       description "Outgoing Logical interface";
       type union {
         type jt:interface-name;
         type string {
           pattern "<.*>|$.*";
         }
       }
     }
     container output {
       description "Configure output interface and MAC address";
       uses apply-advanced;
       leaf interface {
         description "Outgoing Logical interface";
         type union {
           type jt:interface-name;
           type string {
             pattern "<.*>|$.*";
           }
         }
       }
       leaf destination-mac {
         description "MAC address to match";
         type string;
       }
     }
   }
   grouping named-address-book-type {
     description "Configure global address book";
     leaf name {
       description "Address book name";
       type string;
     }
     uses apply-advanced;
     leaf description {
       description "Text description of address book";
       type string {
         length "1 .. 900";
       }
     }
     list address {
       key name;
       ordered-by user;
       description "Define a security address";
       uses address_type;
     }
     list address-set {
       key name;
       ordered-by user;
       description "Define a security address set";
       uses address_set_type;
     }
     container attach {
       description "Attach this address book to interface, zone or routing-instance";
       uses apply-advanced;
       list zone {
         key name;
         ordered-by user;
         description "Define a zone to be attached";
         leaf name {
           description "Security zone name";
           type string {
             length "1 .. 63";
           }
         }
         uses apply-advanced;
       }
     }
   }
   grouping address_set_type {
     leaf name {
       description "Security address-set name";
       type string {
         length "1 .. 63";
       }
     }
     uses apply-advanced;
     leaf description {
       description "Text description of address set";
       type string {
         length "1 .. 900";
       }
     }
     list address {
       key name;
       ordered-by user;
       description "Address to be included in this set";
       max-elements 16384;
       leaf name {
         description "Security address name";
         type string {
           length "1 .. 63";
         }
       }
       uses apply-advanced;
     }
     list address-set {
       key name;
       ordered-by user;
       description "Define an address-set name";
       max-elements 16384;
       leaf name {
         type string {
           length "1 .. 63";
         }
       }
       uses apply-advanced;
     }
   }
   grouping address_type {
     leaf name {
       description "Security address name";
       type string {
         length "1 .. 63";
       }
     }
     uses apply-advanced;
     leaf description {
       description "Text description of address";
       type string {
         length "1 .. 900";
       }
     }
     choice address-content {
       case case_1 {
         leaf ip-prefix {
           description "Numeric IPv4 or IPv6 address with prefix";
           type jt:ipprefix;
         }
       }
       case case_2 {
         list dns-name {
           key name;
           ordered-by user;
           description "DNS address name";
           max-elements 1;
           uses dns-name-type;
         }
       }
       case case_3 {
         list wildcard-address {
           key name;
           ordered-by user;
           description "Numeric IPv4 wildcard address with in the form of a.d.d.r/netmask";
           max-elements 1;
           uses wildcard-address-type;
         }
       }
       case case_4 {
         list range-address {
           key name;
           ordered-by user;
           description "Address range";
           max-elements 1;
           uses range-address-type;
         }
       }
       case case_5 {
         list address-range {
           key name;
           ordered-by user;
           description "Address range";
           max-elements 1;
           uses usf-range-address-type;
         }
       }
     }
   }
   grouping dns-name-type {
     description "DNS address name";
     leaf name {
       description "Fully qualified hostname";
       type string {
         length "1 .. 253";
       }
     }
     uses apply-advanced;
     leaf ipv4-only {
       description "IPv4 dns address";
       type empty;
     }
     leaf ipv6-only {
       description "IPv6 dns address";
       type empty;
     }
   }
   grouping nat-object {
     description "Configure Network Address Translation";
     uses apply-advanced;
     container source {
       description "Configure Source NAT";
       uses ssg-source-nat-object;
     }
     container destination {
       description "Configure Destination NAT";
       uses ssg-destination-nat-object;
     }
     container static {
       description "Configure Static NAT";
       uses ssg-static-nat-object;
     }
     container proxy-arp {
       description "Configure Proxy ARP";
       uses ssg-proxy-arp-object;
     }
     container proxy-ndp {
       description "Configure Proxy NDP";
       uses ssg-proxy-ndp-object;
     }
     container natv6v4 {
       description "Configure NAT between IPv6 and IPv4 options";
       uses apply-advanced;
       leaf no-v6-frag-header {
         description "V6 packet does not always add fragment header when performing nat translation from v4 side to v6 side ";
         type empty;
       }
     }
     leaf allow-overlapping-pools {
       description "IP addresses of NAT pools can overlap with other pool";
       type empty;
     }
     container traceoptions {
       description "NAT trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "routing-socket" {
               description "Trace routing socket events";
             }
             enum "routing-protocol" {
               description "Trace routing protocol events";
             }
             enum "all" {
               description "Trace everything";
             }
             enum "source-nat-re" {
               description "Trace source nat events on RE side";
             }
             enum "source-nat-rt" {
               description "Trace source nat events on PFE-RT side";
             }
             enum "source-nat-pfe" {
               description "Trace source nat events on PFE-ukernel side";
             }
             enum "destination-nat-re" {
               description "Trace destination nat events on RE side";
             }
             enum "destination-nat-rt" {
               description "Trace destination nat events on PFE-RT side";
             }
             enum "destination-nat-pfe" {
               description "Trace destination nat events on PFE-ukernel side";
             }
             enum "static-nat-re" {
               description "Trace static nat events on RE side";
             }
             enum "static-nat-rt" {
               description "Trace static nat events on PFE-RT side";
             }
             enum "static-nat-pfe" {
               description "Trace static nat events on PFE-ukernel side";
             }
             enum "nat-svc-set-re" {
               description "Trace NAT and svc-set events on RE side";
             }
           }
         }
         leaf syslog {
           description "Write NAT flow traces to system log also";
           type empty;
         }
       }
     }
     list pool {
       key name;
       ordered-by user;
       description "Define a NAT pool";
       uses nat_pool_object;
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     leaf allow-overlapping-nat-pools {
       description "Allow usage of overlapping and same nat pools in multiple service sets";
       type empty;
     }
     list rule {
       key name;
       ordered-by user;
       description "Define a NAT rule";
       uses nat_rule_object;
     }
     list port-forwarding {
       key name;
       ordered-by user;
       description "Define a port-forwarding pool";
       uses pf_mapping;
     }
     list rule-set {
       key name;
       ordered-by user;
       description "Defines a set of NAT rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping nat_pool_object {
     leaf name {
       description "Pool name";
       type string {
         length "1 .. 63";
       }
     }
     uses apply-advanced;
     container pgcp {
       presence "enable pgcp";
       description "NAT pool should be used exclusive by the pgcp service";
       uses apply-advanced;
       leaf remotely-controlled {
         description "Remotely controlled NAT pool allocation";
         type empty;
       }
       leaf ports-per-session {
         description "Number of ports to allocate in each call setup";
         default "2";
         type union {
           type uint8;
           type string {
             pattern "<.*>|$.*";
           }
         }
       }
       list hint {
         key name;
         ordered-by user;
         description "NAT-hint list (Any string available up to 3 characters, not mandatory field)";
         max-elements 5;
         uses nat_pgcp_hint_list_object;
       }
       leaf-list transport {
         ordered-by user;
         description "NAT pool transport types list";
         type enumeration {
           enum "tcp" {
             description "TCP";
           }
           enum "udp" {
             description "UDP";
           }
           enum "rtp-avp" {
             description "RTP/AVP";
           }
         }
       }
     }
     list address {
       key name;
       ordered-by user;
       description "Address or address prefix for NAT";
       leaf name {
         type jt:ipprefix-only;
       }
       uses apply-advanced;
     }
     container interface {
       description "Interface for nat pool";
       leaf interface-name {
         type union {
           type jt:interface-unit;
           type string {
             pattern "<.*>|$.*";
           }
         }
       }
     }
     leaf address-overload {
       description "Nat pool address overload with JunOS";
       type empty;
     }
     list address-range {
       key "low high";
       ordered-by user;
       description "Range of addresses for NAT";
       leaf low {
         description "Lower limit of address range";
         type jt:ipaddr;
       }
       leaf high {
         description "Upper limit of address range";
         type jt:ipaddr;
       }
     }
     container port {
       description "Specify ports for NAT";
       uses apply-advanced;
       choice port_choice {
         case case_1 {
           container automatic {
             presence "enable automatic";
             uses apply-advanced;
             choice automatic_choice {
               case case_1 {
                 leaf auto {
                   description "Automatically choose ports";
                   status deprecated;
                   type empty;
                 }
               }
               case case_2 {
                 leaf sequential {
                   description "Allocate ports in sequence";
                   type empty;
                 }
               }
               case case_3 {
                 leaf random-allocation {
                   description "Allocate ports randomly";
                   type empty;
                 }
               }
             }
           }
         }
         case case_2 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
             leaf random-allocation {
               description "Allocate ports randomly";
               type empty;
             }
           }
         }
       }
       choice block-allocation-choice {
         case case_1 {
           container secured-port-block-allocation {
             presence "enable secured-port-block-allocation";
             description "Secured Port block allocation";
             leaf block-size {
               description "Number of port per block.";
               default "128";
               type union {
                 type string {
                   pattern "<.*>|$.*";
                 }
                 type uint16 {
                   range "1 .. 64512";
                 }
               }
             }
             leaf max-blocks-per-address {
               description "Max block per address";
               default "8";
               type union {
                 type string {
                   pattern "<.*>|$.*";
                 }
                 type uint16 {
                   range "1 .. 512";
                 }
               }
             }
             leaf active-block-timeout {
               description "Active block timeout";
               default "120";
               type union {
                 type string {
                   pattern "<.*>|$.*";
                 }
                 type uint32 {
                   range "0 .. 86400";
                 }
               }
             }
           }
         }
         case case_2 {
           container deterministic-port-block-allocation {
             presence "enable deterministic-port-block-allocation";
             description "Deterministic Port Block Allocation";
             leaf block-size {
               description "Number of ports per block";
               default "512";
               type union {
                 type string {
                   pattern "<.*>|$.*";
                 }
                 type uint16 {
                   range "0 .. 64512";
                 }
               }
             }
             leaf include-boundary-addresses {
               description "Include network and broadcast in 'from' src-addresses";
               type empty;
             }
           }
         }
       }
       leaf preserve-parity {
         description "Allocate port with same parity as original port";
         type empty;
       }
       leaf preserve-range {
         description "Preserve privileged port range after NAT";
         type empty;
       }
     }
     container address-allocation {
       presence "enable address-allocation";
       description "Address allocation method for NAPT";
       uses apply-advanced;
       leaf round-robin {
         description "Round robin method of allocation";
         type empty;
       }
     }
     leaf mapping-timeout {
       description "Address-pooling paired and endpoint-independent mapping timeout (120..86400)";
       default "300";
       units "second";
       type union {
         type int32;
         type string {
           pattern "<.*>|$.*";
         }
       }
     }
     leaf flow-timeout {
       description "Default flow timeout for NAT flows";
       default "300";
       units "second";
       type union {
         type string {
           pattern "<.*>|$.*";
         }
         type int32 {
           range "30 .. 86400";
         }
       }
     }
     leaf ei-mapping-timeout {
       description "Endpoint-independent mapping timeout (120..86400)";
       units "second";
       type union {
         type int32;
         type string {
           pattern "<.*>|$.*";
         }
       }
     }
     leaf app-mapping-timeout {
       description "Address-pooling paired mapping timeout (120..86400)";
       units "second";
       type union {
         type int32;
         type string {
           pattern "<.*>|$.*";
         }
       }
     }
     leaf limit-ports-per-address {
       description "Limit number of ports allocated per host (IP address)";
       units "connections";
       type union {
         type string {
           pattern "<.*>|$.*";
         }
         type int32 {
           range "2 .. 65435";
         }
       }
     }
     container snmp-trap-thresholds {
       presence "enable snmp-trap-thresholds";
       description "Define snmp traps for service sets";
       uses apply-advanced;
       container address-port {
         presence "enable address-port";
         description "Nat pool address and port usage trap threshold range";
         leaf low {
           description "Lower limit of pool trap threshold";
           units "percent";
           type union {
             type string {
               pattern "<.*>|$.*";
             }
             type uint16 {
               range "0 .. 100";
             }
           }
         }
         leaf high {
           description "Upper limit of pool trap threshold";
           units "percent";
           type union {
             type string {
               pattern "<.*>|$.*";
             }
             type uint16 {
               range "0 .. 100";
             }
           }
         }
       }
     }
   }
   grouping nat_pgcp_hint_list_object {
     description "NAT hints";
     leaf name {
       description "NAT-hint string list";
       type string {
         length "1 .. 4";
       }
     }
   }
   grouping nat_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match an input to or output from on interface";
         }
       }
     }
     list term {
       key name;
       ordered-by user;
       description "Define a NAT term";
       leaf name {
         description "Term name";
         type string {
           length "1 .. 63";
         }
       }
       uses apply-advanced;
       leaf nat-type {
         description "NAT type (symmetric/full-cone)";
         type enumeration {
           enum "symmetric" {
             description "Symmetric NAT";
           }
           enum "full-cone" {
             description "Full Cone NAT";
           }
         }
       }
       container from {
         description "Define match criteria";
         uses sfw_match_object;
       }
       container then {
         description "Action to take if the 'from' condition is matched";
         uses apply-advanced;
         choice designation {
           case case_1 {
             leaf no-translation {
               description "Do not perform translation";
               type empty;
             }
           }
         }
         choice port-forwarding {
           case case_1 {
             leaf port-forwarding-mappings {
               description "Port forwarding mappings";
               type string {
                 length "1 .. 63";
               }
             }
           }
         }
         container translated {
           description "Define translation parameters";
           uses apply-advanced;
           choice source-pool-choice {
             case case_1 {
               leaf source-pool {
                 description "NAT pool for source translation";
                 type string {
                   length "1 .. 63";
                 }
               }
             }
             case case_2 {
               leaf source-prefix {
                 description "NAT prefix for source translation";
                 type jt:ipprefix-only;
               }
             }
           }
           leaf clat-prefix {
             description "Clat-prefix to be used for 464 translation type";
             type jt:ipprefix-only;
           }
           leaf clat-ipv6-prefix-length {
             description "The ipv6 prefix length for CLAT source address";
             default "64";
             type enumeration {
               enum "32" {
                 description "The ipv6 prefix length of 32";
               }
               enum "40" {
                 description "The ipv6 prefix length of 40";
               }
               enum "48" {
                 description "The ipv6 prefix length of 48";
               }
               enum "56" {
                 description "The ipv6 prefix length of 56";
               }
               enum "64" {
                 description "The ipv6 prefix length of 64";
               }
               enum "96" {
                 description "The ipv6 prefix length of 96";
               }
             }
           }
           choice destination-pool-choice {
             case case_1 {
               leaf destination-pool {
                 description "NAT pool for destination translation";
                 type string {
                   length "1 .. 63";
                 }
               }
             }
             case case_2 {
               leaf destination-prefix {
                 description "NAT prefix for destination translation";
                 type jt:ipprefix-only;
               }
             }
           }
           choice dns-alg-pool-choice {
             case case_1 {
               leaf dns-alg-pool {
                 description "NAT pool for dns alg mappings";
                 type string {
                   length "1 .. 63";
                 }
               }
             }
             case case_2 {
               leaf dns-alg-prefix {
                 description "DNS ALG 96 bit prefix for mapping IPv4 addresses to IPv6 addresses";
                 type jt:ipprefix-only;
               }
             }
           }
           choice dns-map-address-for-destination-translation-choice {
             case case_1 {
               leaf use-dns-map-for-destination-translation {
                 description "Use dns alg address map for destination translation";
                 status deprecated;
                 type empty;
               }
             }
           }
           choice overload-pool-choice {
             case case_1 {
               leaf overload-pool {
                 description "NAT pool to be used when source pool is overloaded";
                 type string {
                   length "1 .. 63";
                 }
               }
             }
             case case_2 {
               leaf overload-prefix {
                 description "NAT prefix to be used when source pool is overloaded";
                 type jt:ipprefix-only;
               }
             }
           }
           container translation-type {
             description "Type of translation to perform";
             uses apply-advanced;
             leaf source {
               description "Type of source translation";
               status deprecated;
               type enumeration {
                 enum "static" {
                   description "Static translation";
                   status deprecated;
                 }
                 enum "dynamic" {
                   description "Dynamic translation";
                   status deprecated;
                 }
               }
             }
             leaf destination {
               description "Type of destination translation";
               status deprecated;
               type enumeration {
                 enum "static" {
                   description "Static translation";
                   status deprecated;
                 }
               }
             }
             container basic-nat44 {
               presence "enable basic-nat44";
               description "Static source address (IPv4 to IPv4) translation";
             }
             container dynamic-nat44 {
               presence "enable dynamic-nat44";
               description "Dynamic source address only (IPv4 to IPv4) translation";
             }
             container napt-44 {
               presence "enable napt-44";
               description "Source address (IPv4 to IPv4) and port translation";
             }
             container dnat-44 {
               presence "enable dnat-44";
               description "Static Destination address (IPv4 to IPv4) translation";
             }
             container stateful-nat64 {
               presence "enable stateful-nat64";
               description "Dynamic source address (IPv6 to IPv4) and prefix removal for destination address (IPv6 to IPv4)translation";
             }
             container stateful-nat464 {
               presence "enable stateful-nat464";
               description "Prefix removal for Src and Dest address (IPv6 to IPv4) translation";
             }
             container basic-nat-pt {
               presence "enable basic-nat-pt";
               description "NAT-PT (static source address (IPv6 to IPv4) and prefix removal for destination address (IPv6 to IPv4) translation)";
             }
             container napt-pt {
               presence "enable napt-pt";
               description "NAT-PT (source address (IPv6 to IPv4) and source port and prefix removal for destination address (IPv6 to IPv4) translation)";
             }
             container basic-nat66 {
               presence "enable basic-nat66";
               description "Static source address (IPv6 to IPv6) translation [same as basic-nat44 but for IPv6 address family]";
             }
             container nptv6 {
               presence "enable nptv6";
               description "Stateless source address (IPv6 to IPv6) translation";
             }
             container napt-66 {
               presence "enable napt-66";
               description "Source address (IPv6 to IPv6) and port translation [same as napt-44 but for IPv6 address family]";
             }
             container twice-napt-44 {
               presence "enable twice-napt-44";
               description "Source NAPT and destination static translation for IPv4 address family";
             }
             container twice-basic-nat-44 {
               presence "enable twice-basic-nat-44";
               description "Source static and destination static translation for IPv4 address family";
             }
             container twice-dynamic-nat-44 {
               presence "enable twice-dynamic-nat-44";
               description "Source dynamic and destination static translation for IPv4 address family";
             }
             container deterministic-napt44 {
               presence "enable deterministic-napt44";
               description "Deterministic source NAPT for IPv4 family";
               uses apply-advanced;
             }
             container deterministic-napt64 {
               presence "enable deterministic-napt64";
               description "Deterministic source NAPT for IPv6 family";
             }
           }
           leaf mapping-type {
             description "Source NAT mapping type";
             type enumeration {
               enum "endpoint-independent" {
                 description "Endpoint independent mapping";
               }
             }
           }
           leaf flow-type {
             description "Source NAT flow type";
             type enumeration {
               enum "endpoint-independent" {
                 description "Endpoint independent flow";
               }
             }
           }
           leaf ignore-dst-nat-1to1-limitation {
             description "Ignore destination NAT 1:1 limitation";
             type empty;
           }
           container secure-nat-mapping {
             presence "enable secure-nat-mapping";
             description "Mapping options for enhanced security";
             uses apply-advanced;
             leaf eif-flow-limit {
               description "Number of inbound flows to be allowed for a EIF mapping";
               type union {
                 type string {
                   pattern "<.*>|$.*";
                 }
                 type uint16 {
                   range "0 .. 65534";
                 }
               }
             }
             leaf mapping-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
             leaf flow-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
           }
           container filtering-type {
             description "Source NAT filtering type";
             uses apply-advanced;
             container endpoint-independent {
               presence "enable endpoint-independent";
               description "Endpoint independent filtering";
               uses apply-advanced;
               list prefix-list {
                 key name;
                 ordered-by user;
                 description "One or more named lists of source prefixes to match";
                 leaf name {
                   description "Name of prefix list to match against";
                   type string;
                 }
                 leaf except {
                   description "Name of prefix list not to match against";
                   type empty;
                 }
               }
             }
           }
           leaf address-pooling {
             description "Address pooling behavior for source NAT";
             type enumeration {
               enum "paired" {
                 description "Address pooling behavior of paired";
               }
             }
           }
         }
         leaf syslog {
           description "System log information about the packet";
           type empty;
         }
       }
     }
   }
   grouping pf_mapping {
     leaf name {
       description "Port Forwarding name";
       type string {
         length "1 .. 63";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping policy-object-type {
     uses apply-advanced;
     container traceoptions {
       description "Network Security Policy Tracing Options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "routing-socket" {
               description "Trace routing socket events";
             }
             enum "compilation" {
               description "Policy compilation events";
             }
             enum "ipc" {
               description "Inter-process communication events";
             }
             enum "rules" {
               description "Policy rules related events";
             }
             enum "lookup" {
               description "Policy lookup events";
             }
             enum "all" {
               description "Trace everything";
             }
           }
         }
       }
     }
     list policy {
       key "from-zone-name to-zone-name";
       ordered-by user;
       description "Define a policy context from this zone";
       leaf from-zone-name {
         description "Source zone";
         type string {
           length "1 .. 63";
         }
       }
       leaf to-zone-name {
         description "Destination zone";
         type string {
           length "1 .. 63";
         }
       }
       uses apply-advanced;
       list policy {
         key name;
         ordered-by user;
         description "Define security policy in specified zone-to-zone direction";
         uses policy_type;
       }
       container application-services {
         description "Application Services";
         uses context_application_services_type;
       }
     }
     container global {
       description "Define a global policy context";
       uses apply-advanced;
       list policy {
         key name;
         ordered-by user;
         description "Define security policy in global context";
         uses policy_type;
       }
     }
     list policy-set {
       key name;
       ordered-by user;
       description "Define a policy context for tunnel-inspection";
       leaf name {
         description "Policy-set name";
         type string {
           length "1 .. 63";
         }
       }
       uses apply-advanced;
       list policy {
         key name;
         ordered-by user;
         description "Define security policy in tunnel-inspection context";
         uses policy_type;
       }
     }
     container default-policy {
       description "Configure default action when no user-defined policy match";
       uses apply-advanced;
       leaf default-action {
         description "Default action";
         default "deny-all";
         type enumeration {
           enum "permit-all" {
             description "Permit all traffic if no policy match";
           }
           enum "deny-all" {
             description "Deny all traffic if no policy match";
           }
         }
       }
       leaf log-profile {
         description "Rtlog profile";
         type string;
       }
     }
     container policy-rematch {
       presence "enable policy-rematch";
       description "Re-evaluate the policy when changed";
       leaf extensive {
         description "Perform policy extensive rematch";
         type empty;
       }
     }
     container policy-stats {
       presence "enable policy-stats";
       description "Parameters for policy statistics";
       uses apply-advanced;
       leaf system-wide {
         description "Enable/Disable system-wide policy statistics";
         type enumeration {
           enum "enable" {
             description "Enable policy system-wide statistics";
           }
           enum "disable" {
             description "Disable policy system-wide statistics";
           }
         }
       }
     }
     container pre-id-default-policy {
       description "Configure default policy action before dynamic application is finally identified";
       uses apply-advanced;
       container then {
         description "Specify policy action to take when packet match criteria";
         uses apply-advanced;
         container log {
           description "Enable log";
           uses log_type;
         }
         container session-timeout {
           description "Session timeout";
           uses session_timeout_type;
         }
       }
     }
     container unified-policy {
       description "Unified policies lookup limitations";
       uses apply-advanced;
       leaf max-lookups {
         description "Max lookup times upon micro-app transaction finals";
         type union {
           type string {
             pattern "<.*>|$.*";
           }
           type uint32 {
             range "0 .. 4294967295";
           }
         }
       }
     }
     container dns-cache {
       description "Define security policy dns-cache behaviors";
       uses apply-advanced;
       container error-response-delete-ip {
         presence "enable error-response-delete-ip";
         description "Clear DNS cache entry IP on error DNS response";
         uses apply-advanced;
         leaf retry-interval {
           description "Interval between deleting IP and resending DNS requests";
           default "300";
           units "seconds";
           type union {
             type string {
               pattern "<.*>|$.*";
             }
             type uint32 {
               range "5 .. 86400";
             }
           }
         }
       }
     }
     list stateful-firewall-rule {
       key name;
       ordered-by user;
       description "Define a stateful-firewall-rule";
       leaf name {
         description "Stateful-firewall-rule name";
         type string {
           length "1 .. 63";
         }
       }
       uses apply-advanced;
       leaf match-direction {
         description "Direction for which the rule match is applied";
         type enumeration {
           enum "input" {
             description "Match on input to interface";
           }
           enum "output" {
             description "Match on output from interface";
           }
           enum "input-output" {
             description "Match on input to or output from interface";
           }
         }
       }
       list policy {
         key name;
         ordered-by user;
         description "Define a stateful-firewall policy";
         uses policy_type;
       }
     }
     list stateful-firewall-rule-set {
       key name;
       ordered-by user;
       description "Defines a set of stateful firewall rules";
       leaf name {
         description "Name of the stateful firewall rule set";
         type string {
           length "1 .. 63";
         }
       }
       uses apply-advanced;
       list stateful-firewall-rule {
         key name;
         ordered-by user;
         description "Rule to be included in this stateful firewall rule set";
         leaf name {
           description "Stateful-firewall-rule name";
           type string {
           }
         }
         uses apply-advanced;
       }
     }
   }
   grouping context_application_services_type {
     uses apply-advanced;
     leaf security-metadata-streaming-policy {
       description "Specify security-metadata-streaming-policy";
       type string {
         length "1 .. 63";
       }
     }
   }
   grouping log_type {
     uses apply-advanced;
     leaf session-init {
       description "Log at session init time";
       type empty;
     }
     leaf session-close {
       description "Log at session close time";
       type empty;
     }
     leaf session-update {
       description "Log with specified interval (0 to disable this log)";
       default "0";
       units "minutes";
       type union {
         type string {
           pattern "<.*>|$.*";
         }
         type uint32 {
           range "0 .. 1440";
         }
       }
     }
     leaf sfw {
       description "Display Stateful-fire-wall SYSLOGs";
       type empty;
     }
     leaf profile {
       description "Name of rtlog profile";
       type string;
     }
   }
   grouping policy_type {
     leaf name {
       description "Security policy name";
       type string {
         length "1 .. 63";
       }
     }
     uses apply-advanced;
     leaf description {
       description "Text description of policy";
       type string {
         length "1 .. 900";
       }
     }
     container match {
       description "Specify security policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             type string;
           }
         }
       }
       choice source_identity_choice {
         case case_1 {
           leaf-list source-identity {
             ordered-by user;
             type string;
           }
         }
       }
       choice source_identity_feed_choice {
         case case_1 {
           leaf-list source-identity-feed {
             ordered-by user;
             description "Specify source-identity-feed name from list to match";
             type string {
               length "1 .. 64";
             }
           }
         }
       }
       choice source_tenant_choice {
         case case_1 {
           list source-tenant {
             key name;
             ordered-by user;
             description "Source Tenant";
             uses match_source_tenant_type;
           }
         }
       }
       choice dest_service_choice {
         case case_1 {
           list destination-service {
             key name;
             ordered-by user;
             description "Destination Service";
             uses match_dest_service_type;
           }
         }
       }
       choice destination_identity_feed_choice {
         case case_1 {
           leaf-list destination-identity-feed {
             ordered-by user;
             description "Specify destination-identity-feed name from list to match";
             type string {
               length "1 .. 64";
             }
           }
         }
       }
       choice source_end_user_profile_choice {
         case case_1 {
           container source-end-user-profile {
             description "Match source end user profile";
             uses match_source_end_user_profile_value;
           }
         }
       }
       choice dynamic_application_type_choice {
         case case_1 {
           leaf-list dynamic-application {
             ordered-by user;
             type string;
           }
         }
       }
       choice url_category_type_choice {
         case case_1 {
           leaf-list url-category {
             ordered-by user;
             type string;
           }
         }
       }
       choice from_zone_choice {
         case case_1 {
           leaf-list from-zone {
             ordered-by user;
             type string;
           }
         }
       }
       choice to_zone_choice {
         case case_1 {
           leaf-list to-zone {
             ordered-by user;
             type string;
           }
         }
       }
       choice source_vrf_choice {
         case case_1 {
           leaf-list source-l3vpn-vrf-group {
             ordered-by user;
             description "L3VPN group name";
             type string;
           }
         }
       }
       choice dst_vrf_choice {
         case case_1 {
           leaf-list destination-l3vpn-vrf-group {
             ordered-by user;
             description "L3VPN group name";
             type string;
           }
         }
       }
     }
     container then {
       description "Specify policy action to take when packet match criteria";
       uses apply-advanced;
       choice action {
         case case_1 {
           container deny {
             presence "enable deny";
             description "Deny packets";
             uses apply-advanced;
             container application-services {
               description "Application Services";
               uses apply-advanced;
               container security-intelligence {
                 description "Generate security intellegence feeds";
                 uses security_intelligence_feeds;
               }
             }
           }
         }
         case case_2 {
           container reject {
             presence "enable reject";
             description "Reject packets";
             uses apply-advanced;
             leaf profile {
               description "Profile for redirect HTTP/S traffic";
               type string;
             }
             container ssl-proxy {
               presence "enable ssl-proxy";
               description "SSL proxy services";
               uses apply-advanced;
               leaf profile-name {
                 description "Specify SSL proxy service profile name";
                 type string;
               }
             }
             container application-services {
               description "Application Services";
               uses apply-advanced;
               container security-intelligence {
                 description "Generate security intellegence feeds";
                 uses security_intelligence_feeds;
               }
             }
           }
         }
         case case_3 {
           container permit {
             presence "enable permit";
             description "Permit packets";
             uses apply-advanced;
             container tunnel {
               description "Tunnel packets";
               uses tunnel_type;
             }
             container firewall-authentication {
               description "Enable authentication for this policy if permit or tunnel";
               uses firewall_authentication_type;
             }
             container destination-address {
               description "Enable destination address translation";
               presence "enable destination-address";
               uses destination_nat_enable_type;
             }
             container application-services {
               description "Application Services";
               uses application_services_type;
             }
             container tunnel-inspection {
               description "Enable tunnel inspection";
               uses apply-advanced;
               leaf profile-name {
                 description "Tunnel inspection profile";
                 type string {
                   length "1 .. 63";
                 }
               }
             }
             container tcp-options {
               description "Transmission Control Protocol session configuration";
               uses apply-advanced;
               leaf syn-check-required {
                 description "Enable per policy SYN-flag check";
                 type empty;
               }
               leaf sequence-check-required {
                 description "Enable per policy sequence-number checking";
                 type empty;
               }
               leaf initial-tcp-mss {
                 description "Override MSS value for initial direction";
                 type union {
                   type string {
                     pattern "<.*>|$.*";
                   }
                   type uint32 {
                     range "64 .. 65535";
                   }
                 }
               }
               leaf reverse-tcp-mss {
                 description "Override MSS value for reverse direction";
                 type union {
                   type string {
                     pattern "<.*>|$.*";
                   }
                   type uint32 {
                     range "64 .. 65535";
                   }
                 }
               }
               leaf window-scale {
                 description "Enable per policy window-scale";
                 type empty;
               }
             }
             leaf services-offload {
               description "Enable services offloading";
               type empty;
             }
             leaf no-services-offload {
               description "Disenable services offloading";
               type empty;
             }
             leaf advanced-connection-tracking {
               description "Lookup advanced-connection-tracking table on to-zone";
               type empty;
             }
           }
         }
       }
       container log {
         description "Enable log";
         uses log_type;
       }
       container count {
         description "Enable count";
         presence "enable count";
         uses count_type;
       }
     }
     leaf scheduler-name {
       description "Name of scheduler";
       type string {
         length "1 .. 63";
       }
     }
     leaf report-skip {
       description "Skip report for this policy";
       type empty;
     }
   }
   grouping application_services_type {
     description "Application Services";
     uses apply-advanced;
     leaf gtp-profile {
       description "Specify GPRS Tunneling Protocol profile name";
       type string {
         length "1 .. 63";
       }
     }
     leaf sctp-profile {
       description "Specify Stream Control Protocol profile name";
       type string {
         length "1 .. 63";
       }
     }
     leaf idp {
       description "Intrusion detection and prevention";
       type empty;
     }
     leaf packet-capture {
       description "Capturing traffic related to this policy";
       type empty;
     }
     leaf idp-policy {
       description "Specify idp policy name";
       type string {
         length "1 .. 255";
       }
     }
     container ssl-proxy {
       presence "enable ssl-proxy";
       description "SSL proxy services";
       uses apply-advanced;
       leaf profile-name {
         description "Specify SSL proxy service profile name";
         type string;
       }
     }
     container web-proxy {
       presence "enable web-proxy";
       description "Web proxy services";
       uses apply-advanced;
       leaf profile-name {
         description "Specify Web proxy service profile name";
         type string;
       }
     }
     container uac-policy {
       presence "enable uac-policy";
       description "Enable unified access control enforcement of policy";
       uses apply-advanced;
       leaf captive-portal {
         type string {
           length "1 .. 128";
         }
       }
     }
     leaf utm-policy {
       description "Specify utm policy name";
       type string {
         length "1 .. 255";
       }
     }
     leaf icap-redirect {
       description "Specify icap redirect profile name";
       type string {
         length "1 .. 63";
       }
     }
     container application-firewall {
       description "Application firewall services";
       status deprecated;
       uses jsf_service_rule_set_type;
     }
     container application-traffic-control {
       description "Application traffic control services";
       uses jsf_application_traffic_control_rule_set_type;
     }
     choice wx-redirection {
       case case_1 {
         leaf redirect-wx {
           description "Set WX redirection";
           type empty;
         }
       }
       case case_2 {
         leaf reverse-redirect-wx {
           description "Set WX reverse redirection";
           type empty;
         }
       }
     }
     leaf security-intelligence-policy {
       description "Specify security-intelligence policy name";
       type string {
         length "1 .. 255";
       }
     }
     leaf advanced-anti-malware-policy {
       description "Specify advanced-anti-malware policy name";
       type string {
         length "1 .. 255";
       }
     }
     container security-intelligence {
       description "Generate security intellegence feeds";
       uses security_intelligence_feeds;
     }
   }
   grouping count_type {
     uses apply-advanced;
   }
   grouping destination_nat_enable_type {
     description "Enable Destination NAT";
     uses apply-advanced;
     choice destination_nat {
       case case_1 {
         leaf drop-translated {
           description "Drop the policy if NAT translated";
           type empty;
         }
       }
       case case_2 {
         leaf drop-untranslated {
           description "Drop the policy if NAT untranslated";
           type empty;
         }
       }
     }
   }
   grouping firewall_authentication_type {
     uses apply-advanced;
     choice auth-type {
       case case_1 {
         container pass-through {
           presence "enable pass-through";
           description "Pass-through firewall authentication settings";
           uses apply-advanced;
           leaf access-profile {
             description "Specify access profile name";
             type string {
               length "1 .. 63";
             }
           }
           leaf-list client-match {
             ordered-by user;
             description "Name of user or group to match";
             type string {
               length "1 .. 63";
             }
           }
           leaf web-redirect {
             description "Redirect unauthenticated HTTP requests to the device's internal web server";
             type empty;
           }
           leaf web-redirect-to-https {
             description "Redirect unauthenticated HTTP requests to the device's internal HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
         }
       }
       case case_2 {
         container web-authentication {
           presence "enable web-authentication";
           description "Web-authentication settings";
           uses apply-advanced;
           leaf-list client-match {
             ordered-by user;
             description "Name of user or group to match";
             type string {
               length "1 .. 63";
             }
           }
         }
       }
       case case_3 {
         container user-firewall {
           description "User-firewall firewall authentication settings";
           uses apply-advanced;
           leaf access-profile {
             description "Specify access profile name";
             type string {
               length "1 .. 63";
             }
           }
           leaf web-redirect {
             description "Redirect unauthenticated HTTP req to web server";
             type empty;
           }
           leaf web-redirect-to-https {
             description "Redirect unauthenticated HTTP req to HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
           leaf domain {
             description "Specify domain name";
             type string {
               length "1 .. 64";
             }
           }
         }
       }
     }
     leaf push-to-identity-management {
       description "Push auth entry to identity management server";
       type empty;
     }
   }
   grouping jsf_service_rule_set_type {
     description "Define service rule set reference";
     uses apply-advanced;
     leaf rule-set {
       description "Service rule set name";
       type string {
         length "1 .. 64";
       }
     }
   }
   grouping match_dest_service_type {
     leaf name {
       description "Destination Service for Vector Routing Policy";
       type string;
     }
   }
   grouping match_source_end_user_profile_value {
     uses apply-advanced;
     leaf source-end-user-profile-name {
       description "Specify source-end-user-profile name from list to match";
       type string;
     }
   }
   grouping match_source_tenant_type {
     leaf name {
       description "Source Tenant for Vector Routing Policy";
       type string;
     }
   }
   grouping port-range {
     description "Port ranges";
     leaf name {
       description "Single port/minimum port in the port range";
       type union {
         type string {
           pattern "<.*>|$.*";
         }
         type uint32 {
           range "0 .. 65535";
         }
       }
     }
     leaf maximum-port {
       description "Maximum port in the port range";
       type union {
         type string {
           pattern "<.*>|$.*";
         }
         type uint32 {
           range "0 .. 65535";
         }
       }
     }
   }
   grouping profile-setting {
     description "UTM policy settings";
     leaf name {
       description "UTM policy name";
       type string {
         length "1 .. 29";
       }
     }
     uses apply-advanced;
     container anti-virus {
       description "UTM policy anti-virus profile";
       uses apply-advanced;
       leaf http-profile {
         description "Anti-virus profile";
         type string;
       }
       container ftp {
         description "FTP profile";
         uses apply-advanced;
         leaf upload-profile {
           description "Anti-virus profile";
           type string;
         }
         leaf download-profile {
           description "Anti-virus profile";
           type string;
         }
       }
       leaf smtp-profile {
         description "Anti-virus profile";
         type string;
       }
       leaf pop3-profile {
         description "Anti-virus profile";
         type string;
       }
       leaf imap-profile {
         description "Anti-virus profile";
         type string;
       }
     }
     container content-filtering {
       description "Content-filtering profile";
       uses apply-advanced;
       leaf http-profile {
         description "Content-filtering profile";
         status deprecated;
         type string;
       }
       container ftp {
         description "FTP profile";
         status deprecated;
         uses apply-advanced;
         leaf upload-profile {
           description "Content-filtering FTP upload profile";
           type string;
         }
         leaf download-profile {
           description "Content-filtering FTP download profile";
           type string;
         }
       }
       leaf smtp-profile {
         description "Content-filtering SMTP profile";
         status deprecated;
         type string;
       }
       leaf pop3-profile {
         description "Content-filtering POP3 profile";
         status deprecated;
         type string;
       }
       leaf imap-profile {
         description "Content-filtering IMAP profile";
         status deprecated;
         type string;
       }
       list rule-set {
         key name;
         ordered-by user;
         description "Configure UTM CF Rule Sets";
         uses cf-rule-set;
       }
     }
     container web-filtering {
       description "Web-filtering profile";
       uses apply-advanced;
       leaf http-profile {
         description "Web-filtering HTTP profile";
         type string;
       }
     }
     container anti-spam {
       description "Anti-spam profile";
       uses apply-advanced;
       leaf smtp-profile {
         description "Anti-spam profile";
         type string;
       }
     }
     container traffic-options {
       description "Traffic options";
       status deprecated;
       uses apply-advanced;
       container sessions-per-client {
         description "Sessions per client";
         uses apply-advanced;
         leaf limit {
           description "Sessions limit";
           default "2000";
           type union {
             type string {
               pattern "<.*>|$.*";
             }
             type uint32 {
               range "0 .. 2000";
             }
           }
         }
         leaf over-limit {
           description "Over limit number";
           type enumeration {
             enum "log-and-permit" {
             }
             enum "block" {
             }
           }
         }
       }
     }
   }
   grouping proto-object {
     leaf name {
       type string;
     }
     uses apply-advanced;
     list tunable-name {
       key name;
       ordered-by user;
       description "Protocol tunable name";
       uses tunable-object;
     }
   }
   grouping ragw-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "configuration" {
             description "Trace CLI configuration events";
           }
           enum "tunnel" {
             description "Trace tunnel install/encap/decap events";
           }
           enum "session" {
             description "Trace session related events";
           }
           enum "all" {
             description "Trace everything";
           }
         }
       }
     }
   }
   grouping range-address-type {
     description "Range address";
     leaf name {
       description "Lower limit of address range";
       type jt:ipv4addr;
     }
     uses apply-advanced;
     container to {
       description "Port range upper limit";
       uses apply-advanced;
       leaf range-high {
         description "Upper limit of address range";
         type jt:ipv4addr;
       }
     }
   }
   grouping rate-limit-object {
     uses apply-advanced;
     leaf alarm-threshold {
       description "Set alarm threshold for rate-limit";
       type union {
         type string {
           pattern "<.*>|$.*";
         }
         type uint32 {
           range "1 .. 80000";
         }
       }
     }
     leaf drop-threshold {
       description "Set drop threshold for rate-limit";
       type union {
         type string {
           pattern "<.*>|$.*";
         }
         type uint32 {
           range "1 .. 80000";
         }
       }
     }
     container message {
       description "GTP limited message type";
       uses message-object;
     }
   }
   grouping remote-access-client-config {
     leaf name {
       description "Name of config object name";
       type string {
         length "1 .. 32";
       }
     }
     uses apply-advanced;
     leaf connection-mode {
       description "Set connection-mode of client";
       default "manual";
       type enumeration {
         enum "manual" {
           description "Set to manual mode, default mode";
         }
         enum "always" {
           description "Set to always mode";
         }
       }
     }
     leaf biometric-authentication {
       description "Enable biometric authentication";
       type empty;
     }
     container windows-logon {
       presence "enable windows-logon";
       uses apply-advanced;
       leaf mode {
         description "Set windows logon mode";
         default "manual";
         type enumeration {
           enum "manual" {
             description "Manual Windows logon";
           }
           enum "automatic" {
             description "Automatic Windows logon with configured credentials";
           }
         }
       }
       leaf domain {
         description "Domain name for automatic windows logon";
         type string {
           length "1 .. 255";
         }
       }
       leaf disconnect-at-logoff {
         description "Disconnect after logoff";
         type empty;
       }
       leaf flush-credential-at-logoff {
         description "Flush cached credentials upon after logoff";
         type empty;
       }
       leaf lead-time-duration {
         description "Lead time duration for domain logon (seconds)";
         default "45";
         units "seconds";
         type union {
           type string {
             pattern "<.*>|$.*";
           }
           type uint32 {
             range "0 .. 120";
           }
         }
       }
       leaf eap-auth {
         description "EAP Authentication before profile selection";
         type empty;
       }
       leaf auto-dialog-open {
         description "Automatically open dialog for connection establishment";
         type empty;
       }
     }
     leaf no-dead-peer-detection {
       description "Disable dead-peer-detection on client";
       type empty;
     }
     container dead-peer-detection {
       description "Dead Peer Detection configuration";
       uses apply-advanced;
       leaf interval {
         description "The time between DPD probe messages (seconds) Default :60";
         default "60";
         units "seconds";
         type union {
           type string {
             pattern "<.*>|$.*";
           }
           type uint32 {
             range "1 .. 300";
           }
         }
       }
       leaf threshold {
         description "Maximum number of DPD retransmissions Default :5";
         default "5";
         type union {
           type string {
             pattern "<.*>|$.*";
           }
           type uint32 {
             range "1 .. 5";
           }
         }
       }
     }
     leaf no-tcp-encap {
       description "Disable tcp encapsulation";
       type empty;
     }
     leaf no-eap-tls {
       description "Disable EAP-TLS IKEV2 method";
       type empty;
     }
     container certificate {
       description "Certificate identifier";
       uses apply-advanced;
       leaf no-expiry-warning {
         description "Disable certificate expiry warning";
         type empty;
       }
       leaf no-pin-request-per-connection {
         description "Disable certificate pin request per connection";
         type empty;
       }
       leaf warn-before-expiry {
         description "Certificate expiration warning days (1 - 90)";
         default "60";
         units "days";
         type union {
           type string {
             pattern "<.*>|$.*";
           }
           type uint32 {
             range "1 .. 90";
           }
         }
       }
     }
     leaf-list domain-name {
       ordered-by user;
       description "Define the set of domain-name";
       type string {
         length "1 .. 256";
       }
     }
     container credentials {
       description "Credentials saving option";
       uses apply-advanced;
       choice save-option {
         case case_1 {
           leaf password {
             description "Remember both username & password";
             type empty;
           }
         }
         case case_2 {
           leaf username {
             description "Remember username only";
             type empty;
           }
         }
       }
     }
   }
   grouping remote-access-profile-config {
     leaf name {
       description "Profile identifier";
       type string {
         length "1 .. 32";
       }
     }
     uses apply-advanced;
     leaf description {
       description "Text description of remote-access profile";
       type string {
         length "1 .. 255";
       }
     }
     leaf ipsec-vpn {
       description "Select the ipsec-vpn policy object";
       type string;
     }
     leaf access-profile {
       description "Select the access-profile";
       type string;
     }
     leaf client-config {
       description "Select the client config object";
       type string;
     }
   }
   grouping remote-access-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "all" {
             description "Trace everything";
           }
         }
       }
     }
   }
   grouping sbl-type {
     description "SBL type";
     uses apply-advanced;
     list profile {
       key name;
       ordered-by user;
       description "SBL profile";
       leaf name {
         description "SBL profile name";
         type string {
           length "1 .. 29";
         }
       }
       uses apply-advanced;
       choice sbl-default-server-choice {
         leaf sbl-default-server {
           description "Default SBL server";
           type empty;
         }
         leaf no-sbl-default-server {
           description "Don't default SBL server";
           type empty;
         }
       }
       leaf spam-action {
         description "Anti-spam actions";
         type enumeration {
           enum "block" {
             description "Block e-mail";
           }
           enum "tag-header" {
             description "Tag header of e-mail";
           }
           enum "tag-subject" {
             description "Tag subject of e-mail";
           }
         }
       }
       leaf custom-tag-string {
         description "Custom tag string";
         type string {
           length "1 .. 512";
         }
       }
       leaf address-whitelist {
         description "Anti-spam whitelist";
         type string;
       }
       leaf address-blacklist {
         description "Anti-spam blacklist";
         type string;
       }
     }
   }
   grouping sctp-object {
     uses apply-advanced;
     list profile {
       key name;
       description "Configure stream transmission protocol";
       leaf name {
         description "SCTP configuration name";
         type string {
           length "1 .. 31";
         }
       }
       uses apply-advanced;
       leaf nat-only {
         description "Only do payload IPs translation for SCTP packet";
         type empty;
       }
       leaf association-timeout {
         description "SCTP association timeout length, in minutes";
         type union {
           type string {
             pattern "<.*>|$.*";
           }
           type uint32 {
             range "10 .. 1440";
           }
         }
       }
       leaf handshake-timeout {
         description "SCTP handshake timeout, in seconds";
         type union {
           type string {
             pattern "<.*>|$.*";
           }
           type uint32 {
             range "10 .. 30";
           }
         }
       }
       container drop {
         description "Disallowed SCTP payload message";
         uses apply-advanced;
         list m3ua-service {
           key name;
           ordered-by user;
           description "MTP level 3 (MTP3) user adaptation layer service";
           leaf name {
             type enumeration {
               enum "sccp" {
                 description "Signaling connection control part";
               }
               enum "tup" {
                 description "Telephone user part";
               }
               enum "isup" {
                 description "ISDN user part";
               }
             }
           }
         }
         list payload-protocol {
           key name;
           ordered-by user;
           description "SCTP payload protocol identifier";
           leaf name {
             type string;
           }
         }
       }
       container permit {
         description "Permit SCTP payload message";
         uses apply-advanced;
         list payload-protocol {
           key name;
           ordered-by user;
           description "SCTP payload protocol identifier";
           leaf name {
             type string;
           }
         }
       }
       container limit {
         description "Packet limits";
         uses apply-advanced;
         list payload-protocol {
           key name;
           ordered-by user;
           description "Payload Rate limit";
           leaf name {
             type string;
           }
           leaf rate {
             description "Rate limit";
             type union {
               type string {
                 pattern "<.*>|$.*";
               }
               type uint16 {
                 range "1 .. 12000";
               }
             }
           }
         }
         list address {
           key name;
           ordered-by user;
           description "Rate limit for a list of IP addresses";
           leaf name {
             description "IP address";
             type jt:ipaddr;
           }
           uses apply-advanced;
           list payload-protocol {
             key name;
             ordered-by user;
             description "Payload Rate limit";
             leaf name {
               type string;
             }
             leaf rate {
               description "Rate limit";
               type union {
                 type string {
                   pattern "<.*>|$.*";
                 }
                 type uint16 {
                   range "1 .. 12000";
                 }
               }
             }
           }
         }
         container rate {
           description "Rate limit";
           uses apply-advanced;
           leaf sccp {
             description "Global SCCP messages rate limit";
             type union {
               type string {
                 pattern "<.*>|$.*";
               }
               type uint16 {
                 range "1 .. 12000";
               }
             }
           }
           leaf ssp {
             description "Global SSP messages rate limit";
             type union {
               type string {
                 pattern "<.*>|$.*";
               }
               type uint16 {
                 range "1 .. 12000";
               }
             }
           }
           leaf sst {
             description "Global SST messages rate limit";
             type union {
               type string {
                 pattern "<.*>|$.*";
               }
               type uint16 {
                 range "1 .. 12000";
               }
             }
           }
           list address {
             key name;
             ordered-by user;
             description "Rate limit for a list of IP addresses";
             leaf name {
               description "IP address";
               type jt:ipaddr;
             }
             uses apply-advanced;
             leaf sccp {
               description "SCCP messages rate limit";
               type union {
                 type string {
                   pattern "<.*>|$.*";
                 }
                 type uint16 {
                   range "1 .. 12000";
                 }
               }
             }
             leaf ssp {
               description "SSP messages rate limit";
               type union {
                 type string {
                   pattern "<.*>|$.*";
                 }
                 type uint16 {
                   range "1 .. 12000";
                 }
               }
             }
             leaf sst {
               description "SST messages rate limit";
               type union {
                 type string {
                   pattern "<.*>|$.*";
                 }
                 type uint16 {
                   range "1 .. 12000";
                 }
               }
             }
           }
         }
       }
     }
     container multichunk-inspection {
       description "Configure for SCTP multi chunks inspection";
       uses apply-advanced;
       choice multichunk-flag {
         case case_1 {
           leaf disable {
             description "Set multichunk inspection flag to disable";
             type empty;
           }
         }
       }
     }
     container nullpdu {
       description "Configure for SCTP NULLPDU protocol value";
       uses apply-advanced;
       container protocol {
         description "SCTP NULLPDU payload protocol identifier";
         uses apply-advanced;
         choice nullpdu-protocol {
           case case_1 {
             leaf ID-0x0000 {
               description "Set 0x0000 to be NULLPDU ID value";
               type empty;
             }
           }
           case case_2 {
             leaf ID-0xFFFF {
               description "Set 0xFFFF to be NULLPDU ID value";
               type empty;
             }
           }
         }
       }
     }
     list log {
       key name;
       ordered-by user;
       description "GPRS stream control transmission protocol logs";
       leaf name {
         type enumeration {
           enum "configuration" {
             description "Log CLI configuration";
           }
           enum "rate-limit" {
             description "Log exceeding rate limits";
           }
           enum "association" {
             description "Log association event";
           }
           enum "data-message-drop" {
             description "Log the drop of SCTP data message";
           }
           enum "control-message-drop" {
             description "Log the drop of SCTP control message";
           }
           enum "control-message-all" {
             description "Log SCTP control message both drop and pass";
           }
         }
       }
     }
     container traceoptions {
       description "Trace options for GPRS stream control transmission protocol";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "detail" {
               description "Trace detail events";
             }
             enum "flow" {
               description "Trace flow events";
             }
             enum "parser" {
               description "Trace parser events";
             }
             enum "chassis-cluster" {
               description "Trace chassis cluster events";
             }
             enum "all" {
               description "Trace everything";
             }
           }
         }
       }
     }
   }
   grouping secure-wire-type {
     description "Secure-wire cross connection";
     leaf name {
       description "Secure-wire name";
       type string {
         length "1 .. 63";
       }
     }
     uses apply-advanced;
     leaf-list interface {
       description "Secure-wire logical interface";
       type union {
         type jt:interface-unit;
         type string {
           pattern "<.*>|$.*";
         }
       }
       max-elements 2;
     }
   }
   grouping security-authentication-key-chains {
     uses apply-advanced;
     list key-chain {
       key name;
       description "Key chain configuration";
       leaf name {
         description "Name of authentication key chain";
         type string {
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           type union {
             type string {
               pattern "<.*>|$.*";
             }
             type uint32 {
               range "0 .. 63";
             }
           }
         }
         uses apply-advanced;
         leaf secret {
           description "Authentication key";
           type string {
             length "1 .. 126";
           }
         }
         leaf key-name {
           description "Key name in hexadecimal format used for macsec";
           type string {
             length "2 .. 64";
           }
         }
         leaf start-time {
           description "Start time for key transmission (YYYY-MM-DD.HH:MM)";
           type jt:time;
         }
         leaf algorithm {
           description "Authentication algorithm";
           default "md5";
           type enumeration {
             enum "md5" {
               description "Message Digest 5";
             }
             enum "hmac-sha-1" {
               description "Hash-based Message Authentication Code (SHA1) (96 bits)";
             }
             enum "ao" {
               description "TCP Authentication Option";
             }
           }
         }
         leaf options {
           description "Protocol's transmission encoding format";
           default "basic";
           type enumeration {
             enum "basic" {
               description "Rudimentary encoding format";
             }
             enum "isis-enhanced" {
               description "RFC 5310 based encoding";
             }
           }
         }
         container ao-attribute {
           description "TCP Authentication option attributes";
           uses apply-advanced;
           leaf send-id {
             description "Send id for TCP-AO entry";
             type union {
               type string {
                 pattern "<.*>|$.*";
               }
               type uint32 {
                 range "0 .. 255";
               }
             }
           }
           leaf recv-id {
             description "Recv id for TCP-AO entry";
             type union {
               type string {
                 pattern "<.*>|$.*";
               }
               type uint32 {
                 range "0 .. 255";
               }
             }
           }
           leaf tcp-ao-option {
             description "Include TCP-AO option within message header";
             default "disabled";
             type enumeration {
               enum "enabled" {
                 description "Include the TCP-AO option";
               }
               enum "disabled" {
                 description "Not include the TCP-AO option";
               }
             }
           }
           leaf cryptographic-algorithm {
             description "Cryptographic algorithm for TCP-AO Traffic key and MAC digest generation";
             default "hmac-sha-1-96";
             type enumeration {
               enum "hmac-sha-1-96" {
                 description "Hash-based Message Authentication Code (SHA1) (96 bits)";
               }
               enum "aes-128-cmac-96" {
                 description "Cipher-based Message Authentication Code (AES128) (96 bits)";
               }
             }
           }
         }
       }
     }
   }
   grouping security-distribution-profile {
     leaf name {
       description "Name of the distribution profile";
       type string {
         length "1 .. 32";
       }
     }
     uses apply-advanced;
     leaf description {
       description "Text description of Distribution Profile";
       type string {
         length "1 .. 80";
       }
     }
     list fpc {
       key name;
       description "Flexible PIC Concentrator parameters";
       uses fpc_type;
     }
   }
   grouping fpc_type {
     leaf name {
       description "FPC slot number";
       type union {
         type string {
           pattern "<.*>|$.*";
         }
         type uint32;
       }
     }
     uses apply-advanced;
     list pic {
       key name;
       description "Physical Interface Card number";
       uses pic_type;
     }
   }
   grouping pic_type {
     leaf name {
       description "PIC slot number";
       type union {
         type string {
           pattern "<.*>|$.*";
         }
         type uint32;
       }
     }
     uses apply-advanced;
     leaf-list thread-id {
       description "Thread-id";
       type union {
         type string {
           pattern "<.*>|$.*";
         }
         type uint32 {
           range "1 .. 27";
         }
       }
     }
   }
   grouping security-group-vpn {
     uses apply-advanced;
     container member {
       description "Group VPN member configuration";
       uses gvpn-member;
     }
     container server {
       description "Group VPN server configuration";
       uses gvpn-server;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Tracing parameters";
         leaf name {
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       leaf-list server-address {
         ordered-by user;
         description "Server Addresses upto 4";
         type jt:ipv4addr;
         max-elements 4;
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IPv4 address for group member";
         type jt:ipv4addr;
       }
       leaf routing-instance {
         description "Name of routing instance that hosts local address";
         default "default";
         type string;
       }
     }
   }
   grouping gvpn-ike-policy {
     leaf name {
       description "Name of policy";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       type string {
         length "1 .. 32";
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping gvpn-member-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf dh-group {
       description "Define Diffie-Hellman group";
       type enumeration {
         enum "group14" {
           description "Diffie-Hellman Group 14";
         }
         enum "group24" {
           description "Diffie-Hellman Group 24";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping gvpn-server {
     uses apply-advanced;
     container traceoptions {
       description "Trace options for Group VPN debug";
       uses gvpn-server-traceoptions;
     }
     container ike {
       description "Group VPN IKE configuration";
       uses gvpn-server-ike;
     }
     container ipsec {
       description "Group VPN IPsec configuration";
       uses gvpn-server-ipsec-vpn;
     }
     list group {
       key name;
       ordered-by user;
       description "Define a Group VPN group";
       max-elements 50;
       uses gvpn-server-group-template;
     }
   }
   grouping gvpn-server-group-template {
     description "Configure a Group VPN group";
     leaf name {
       description "Name of the group";
       type string {
         length "1 .. 32";
       }
     }
     uses apply-advanced;
     leaf description {
       description "Text description of Group VPN group";
       type string {
         length "1 .. 80";
       }
     }
     leaf group-id {
       description "Enable Group VPN by defining group id";
       type union {
         type string {
           pattern "<.*>|$.*";
         }
         type uint32 {
           range "1 .. 4294967295";
         }
       }
     }
     leaf member-threshold {
       description "Maximum number of members in this group";
       type union {
         type uint32;
         type string {
           pattern "<.*>|$.*";
         }
       }
     }
     container server-cluster {
       description "Enable server cluster for this group";
       uses gvpn-server-cluster;
     }
     list ike-gateway {
       key name;
       ordered-by user;
       description "Name of the IKE gateway";
       uses gvpn-server-ike-gateway;
     }
     leaf activation-time-delay {
       description "Configure delay in seconds for Group VPN key activation";
       status deprecated;
       default "15";
       type union {
         type string {
           pattern "<.*>|$.*";
         }
         type uint32 {
           range "10 .. 900";
         }
       }
     }
     leaf anti-replay-time-window {
       description "Configure Anti Replay time in milliseconds";
       type union {
         type string {
           pattern "<.*>|$.*";
         }
         type uint32 {
           range "1 .. 60000";
         }
       }
     }
     container server-member-communication {
       description "Configure Server to Member communication parameters";
       uses gvpn-server-member-communication;
     }
     list ipsec-sa {
       key name;
       ordered-by user;
       description "Define a Group VPN group SA";
       uses gvpn-server-group-ipsecsa;
     }
   }
   grouping gvpn-server-cluster {
     description "Server-Cluster for group VPN";
     uses apply-advanced;
     leaf server-role {
       description "Primary or backup server";
       type enumeration {
         enum "root-server" {
           description "Root-server";
         }
         enum "sub-server" {
           description "Sub-server";
         }
       }
     }
     list ike-gateway {
       key name;
       ordered-by user;
       description "Name of the IKE gateway";
       uses gvpn-server-ike-gateway-sc;
     }
     leaf retransmission-period {
       description "Configure retransmission period in seconds Default :10";
       default "10";
       type union {
         type string {
           pattern "<.*>|$.*";
         }
         type uint32 {
           range "2 .. 60";
         }
       }
     }
   }
   grouping gvpn-server-group-ipsecsa {
     description "Configure a Group VPN group SA";
     leaf name {
       description "Name of the SA";
       type string {
         length "1 .. 32";
       }
     }
     uses apply-advanced;
     leaf proposal {
       description "Name of the IPsec proposal";
       type string {
         length "1 .. 32";
       }
     }
     list match-policy {
       key name;
       ordered-by user;
       description "Configure a Group VPN group SA";
       max-elements 10;
       uses gvpn-server-group-ipsecsa-match;
     }
   }
   grouping gvpn-server-group-ipsecsa-match {
     description "Configure a Group VPN group SA policy";
     leaf name {
       description "Name of the policy";
       type string {
         length "1 .. 32";
       }
     }
     uses apply-advanced;
     leaf source {
       description "Specify the source IP address to be matched (0.0.0.0/0 for any)";
       type jt:ipv4prefix-mandatory;
     }
     leaf destination {
       description "Specify the destination IP address to be matched (0.0.0.0/0 for any)";
       type jt:ipv4prefix-mandatory;
     }
     leaf source-port {
       description "Specify the source port to be matched (0 for any)";
       type union {
         type string {
           pattern "<.*>|$.*";
         }
         type uint32 {
           range "0 .. 65535";
         }
       }
     }
     leaf destination-port {
       description "Specify the destination port to be matched (0 for any)";
       type union {
         type string {
           pattern "<.*>|$.*";
         }
         type uint32 {
           range "0 .. 65535";
         }
       }
     }
     leaf protocol {
       description "Specify the protocol number to be matched (0 for any)";
       type union {
         type string {
           pattern "<.*>|$.*";
         }
         type uint32 {
           range "0 .. 254";
         }
       }
     }
   }
   grouping gvpn-server-ike {
     uses apply-advanced;
     list proposal {
       key name;
       ordered-by user;
       description "Define an IKE proposal";
       uses gvpn-server-ike-proposal;
     }
     list policy {
       key name;
       ordered-by user;
       description "Define an IKE policy";
       uses gvpn-ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       choice remote-identifier {
         case case_1 {
           leaf address {
             description "IP address of peer";
             type string {
               length "1 .. 32";
             }
           }
         }
         case case_2 {
           container dynamic {
             description "Site to site peer with dynamic IP address";
             uses apply-advanced;
             choice remote-id-type {
               case case_1 {
                 leaf hostname {
                   description "Use a fully-qualified domain name";
                   type string;
                 }
               }
               case case_2 {
                 leaf inet {
                   description "Use an IPV4 address to identify the dynamic peer";
                   type jt:ipv4addr;
                 }
               }
               case case_3 {
                 leaf user-at-hostname {
                   description "Use an e-mail address";
                   type string;
                 }
               }
             }
           }
         }
       }
       container dead-peer-detection {
         presence "enable dead-peer-detection";
         description "Enable Dead Peer Detection between group-server-cluster servers";
         uses apply-advanced;
         choice mode {
           case case_1 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "10 .. 60";
             }
           }
         }
         leaf threshold {
           description "Maximum number of DPD retransmissions Default :5";
           default "5";
           type union {
             type string {
               pattern "<.*>|$.*";
             }
             type uint32 {
               range "1 .. 5";
             }
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container hostname {
               description "Use a fully-qualified domain name";
               uses apply-advanced;
               leaf identity-hostname {
                 description "The local hostname";
                 type string;
               }
             }
           }
           case case_3 {
             container user-at-hostname {
               description "Use an e-mail address";
               uses apply-advanced;
               leaf identity-user {
                 description "The local user-FQDN";
                 type string;
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container hostname {
               description "Use a fully-qualified domain name";
               uses apply-advanced;
               leaf identity-hostname {
                 description "The remote hostname";
                 type string;
               }
             }
           }
           case case_3 {
             container user-at-hostname {
               description "Use an e-mail address";
               uses apply-advanced;
               leaf identity-user {
                 description "The remote user-FQDN";
                 type string;
               }
             }
           }
         }
       }
       leaf local-address {
         description "Local IP address for IKE negotiations";
         type jt:ipaddr;
       }
       leaf routing-instance {
         description "Name of routing instance that hosts local address";
         default "default";
         type string;
       }
     }
   }
   grouping gvpn-server-ike-gateway {
     description "Configure a set of IKE gateways";
     leaf name {
       description "Name of the IKE gateway";
       type string {
         length "1 .. 32";
       }
     }
     uses apply-advanced;
   }
   grouping gvpn-server-ike-gateway-sc {
     description "Configure a set of IKE gateways";
     leaf name {
       description "Name of the IKE gateway";
       type string {
         length "1 .. 32";
       }
     }
     uses apply-advanced;
   }
   grouping gvpn-server-ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
       }
     }
     leaf authentication-algorithm {
       description "Define authentication algorithm";
       type enumeration {
         enum "sha-256" {
           description "SHA 256-bit authentication algorithm";
         }
         enum "sha-384" {
           description "SHA 384-bit authentication algorithm";
         }
       }
     }
     leaf dh-group {
       description "Define Diffie-Hellman group";
       type enumeration {
         enum "group14" {
           description "Diffie-Hellman Group 14";
         }
         enum "group24" {
           description "Diffie-Hellman Group 24";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
   }
   grouping gvpn-server-ipsec-vpn {
     uses apply-advanced;
     list proposal {
       key name;
       ordered-by user;
       description "Define an IPSec proposal";
       uses gvpn-server-ipsec-proposal;
     }
   }
   grouping gvpn-server-ipsec-proposal {
     leaf name {
       description "Name of the IPSec proposal";
       type string {
         length "1 .. 32";
       }
     }
     uses apply-advanced;
     leaf description {
       description "Text description of IPSec proposal";
       type string {
         length "1 .. 80";
       }
     }
     leaf authentication-algorithm {
       description "Define authentication algorithm";
       type enumeration {
         enum "hmac-sha-256-128" {
           description "HMAC-SHA-256-128 authentication algorithm";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping gvpn-server-member-communication {
     description "Group VPN Server to Member communication";
     uses apply-advanced;
     leaf communication-type {
       description "Define type of server member communication";
       type enumeration {
         enum "unicast" {
           description "Unicast";
         }
       }
     }
     leaf lifetime-seconds {
       description "Configure lifetime in seconds";
       default "3600";
       type union {
         type string {
           pattern "<.*>|$.*";
         }
         type uint32 {
           range "300 .. 86400";
         }
       }
     }
     leaf retransmission-period {
       description "Configure retransmission period in seconds";
       default "10";
       type union {
         type string {
           pattern "<.*>|$.*";
         }
         type uint32 {
           range "2 .. 60";
         }
       }
     }
     leaf number-of-retransmission {
       description "Configure maximum number of retransmission attempts";
       default "2";
       type union {
         type string {
           pattern "<.*>|$.*";
         }
         type uint32 {
           range "0 .. 60";
         }
       }
     }
     leaf heartbeat {
       description "Configure heartbeat period in seconds";
       status deprecated;
       default "300";
       type union {
         type string {
           pattern "<.*>|$.*";
         }
         type uint32 {
           range "60 .. 3600";
         }
       }
     }
     leaf encryption-algorithm {
       description "Define encryption algorithm";
       type enumeration {
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf sig-hash-algorithm {
       description "Define sig-hash algorithm";
       type enumeration {
         enum "sha-256" {
           description "SHA 256-bit sig-hash algorithm";
         }
         enum "sha-384" {
           description "SHA 384-bit sig-hash algorithm";
         }
       }
     }
     leaf certificate {
       description "Certificate identifier";
       type string {
       }
     }
   }
   grouping gvpn-server-traceoptions {
     description "Group VPN server tracing options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters for GKSD";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
     container gateway-filter {
       description "Set gateway filter for trace";
       uses apply-advanced;
       leaf local-address {
         description "Use an IPV4 address to identify the local gateway";
         type jt:ipv4addr;
       }
       leaf remote-address {
         description "Use an IPV4 address to identify the remote gateway";
         type jt:ipv4addr;
       }
     }
   }
   grouping ipsec-gvpn-member-template {
     description "Configure a Group VPN";
     leaf name {
       description "Name of the VPN";
       type string {
         length "1 .. 32";
       }
     }
     uses apply-advanced;
     leaf ike-gateway {
       description "Name of IKE gateway";
       type string {
         length "1 .. 32";
       }
     }
     leaf group-vpn-external-interface {
       description "External interface for Group VPN";
       type union {
         type jt:interface-name;
         type string {
           pattern "<.*>|$.*";
         }
       }
     }
     leaf group {
       description "Enable Group VPN by defining group id";
       type union {
         type string {
           pattern "<.*>|$.*";
         }
         type uint32 {
           range "1 .. 4294967295";
         }
       }
     }
     leaf heartbeat-threshold {
       description "Define heartbeat threshold for Group VPN";
       status deprecated;
       default "3";
       type union {
         type string {
           pattern "<.*>|$.*";
         }
         type uint32 {
           range "0 .. 10";
         }
       }
     }
     leaf match-direction {
       description "Direction for which the rule match is applied";
       type enumeration {
         enum "input" {
           description "Match on input to interface";
         }
         enum "output" {
           description "Match on output from interface";
         }
       }
     }
     leaf tunnel-mtu {
       description "Maximum transmit packet size";
       default "1500";
       type union {
         type string {
           pattern "<.*>|$.*";
         }
         type uint32 {
           range "256 .. 9192";
         }
       }
     }
     leaf recovery-probe {
       description "Enable triggering recovery probe mechanism";
       type empty;
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     container fail-open {
       description "List of fail open rules";
       uses ipsec_gvpn_fail_open_rule_object;
     }
     container exclude {
       description "List of exclude rules";
       uses ipsec_gvpn_exclude_rule_object;
     }
   }
   grouping ipsec_gvpn_exclude_rule_object {
     uses apply-advanced;
     list rule {
       key name;
       ordered-by user;
       description "Define exlude rules upto 10";
       max-elements 10;
       uses ipsec_gvpn_rule_address_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       type string {
         length "1 .. 63";
       }
     }
     uses apply-advanced;
     container source-address {
       description "Match IP source address";
       presence "enable source-address";
       uses ipsec_gvpn_addr_object;
     }
     container destination-address {
       description "Match IP destination address";
       presence "enable destination-address";
       uses ipsec_gvpn_addr_object;
     }
     leaf application {
       description "Match application";
       type string;
     }
   }
   grouping ipsec_gvpn_addr_object {
     uses apply-advanced;
     leaf address {
       description "Prefix to match";
       type jt:ipv4prefix-only;
     }
   }
   grouping security-ike {
     uses apply-advanced;
     container traceoptions {
       description "Trace options for IPSec key management";
       uses security-traceoptions;
     }
     container trap {
       description "Controls the sending of SNMP traps";
       uses apply-advanced;
       leaf ipsec-tunnel-down {
         description "Send traps when peer is up and IPsec SA goes down";
         type empty;
       }
       leaf peer-down {
         description "Send traps when peer goes down";
         type empty;
       }
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         type string {
           length "1 .. 32";
         }
       }
       uses apply-advanced;
       leaf ike-policy {
         description "Name of the IKE policy";
         type string {
           length "1 .. 32";
         }
       }
       choice remote-identifier {
         case case_1 {
           leaf-list address {
             ordered-by user;
             description "Addresses or hostnames of peer:1 primary, upto 4 backups";
             type string;
           }
         }
         case case_2 {
           container dynamic {
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf general-ikeid {
                   description "Disables IKE-ID validation";
                   type empty;
                 }
               }
               case case_3 {
                 leaf hostname {
                   description "Use a fully-qualified domain name";
                   type string;
                 }
               }
               case case_4 {
                 leaf inet {
                   description "Use an IPV4 address to identify the dynamic peer";
                   type jt:ipv4addr;
                 }
               }
               case case_5 {
                 leaf inet6 {
                   description "Use an IPV6 address to identify the dynamic peer";
                   type jt:ipv6addr;
                 }
               }
               case case_6 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                 }
               }
             }
             leaf reject-duplicate-connection {
               description "Reject new connection from duplicate IKE-id";
               type empty;
             }
           }
         }
       }
       container dead-peer-detection {
         presence "enable dead-peer-detection";
         description "Enable Dead Peer Detection ";
         uses apply-advanced;
         choice mode {
           case case_1 {
             leaf optimized {
               description "Send probes only when there is outgoing and no incoming data traffic - RFC3706 (Default mode)";
               type empty;
             }
           }
           case case_2 {
             leaf probe-idle-tunnel {
               description "Send probes same as in optimized mode and also when there is no outgoing & incoming data traffic";
               type empty;
             }
           }
           case case_3 {
             leaf always-send {
               description "Send probes periodically regardless of incoming and outgoing data traffic ";
               type empty;
             }
           }
         }
         leaf interval {
           description "The time between DPD probe messages  Default :10";
           default "10";
           units "seconds";
           type union {
             type string {
               pattern "<.*>|$.*";
             }
             type uint32 {
               range "2 .. 60";
             }
           }
         }
         leaf threshold {
           description "Maximum number of DPD retransmissions Default :5";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "20";
         units "seconds";
         type union {
           type string {
             pattern "<.*>|$.*";
           }
           type uint32 {
             range "1 .. 300";
           }
         }
       }
       container local-identity {
         description "Set the local IKE identity";
         choice identity-type {
           case case_1 {
             container inet {
               description "Use an IPv4 address";
               uses apply-advanced;
               leaf identity-ipv4 {
                 description "The local IPv4 identity";
                 type jt:ipv4addr;
               }
             }
           }
           case case_2 {
             container inet6 {
               description "Use an IPv6 address";
               uses apply-advanced;
               leaf identity-ipv6 {
                 description "The local IPv6 identity";
                 type jt:ipv6addr;
               }
             }
           }
           case case_3 {
             container hostname {
               description "Use a fully-qualified domain name";
               uses apply-advanced;
               leaf identity-hostname {
                 description "The local hostname";
                 type string;
               }
             }
           }
           case case_4 {
             container user-at-hostname {
               description "Use an e-mail address";
               uses apply-advanced;
               leaf identity-user {
                 description "The local user-FQDN";
                 type string;
               }
             }
           }
           case case_5 {
             leaf distinguished-name {
               description "Use a distinguished name specified in local certificate";
               type empty;
             }
           }
           case case_6 {
             container key-id {
               description "Key ID identification values in ASCII string";
               uses apply-advanced;
               leaf string-key-id {
                 description "Key ID in ASCII string";
                 type string {
                   length "1 .. 127";
                 }
               }
             }
           }
         }
       }
       container remote-identity {
         description "Set the remote IKE identity";
         choice identity-type {
           case case_1 {
             container inet {
               description "Use an IPv4 address";
               uses apply-advanced;
               leaf identity-ipv4 {
                 description "The remote IPv4 identity";
                 type jt:ipv4addr;
               }
             }
           }
           case case_2 {
             container inet6 {
               description "Use an IPv6 address";
               uses apply-advanced;
               leaf identity-ipv6 {
                 description "The remote IPv6 identity";
                 type jt:ipv6addr;
               }
             }
           }
           case case_3 {
             container hostname {
               description "Use a fully-qualified domain name";
               uses apply-advanced;
               leaf identity-hostname {
                 description "The remote hostname";
                 type string;
               }
             }
           }
           case case_4 {
             container user-at-hostname {
               description "Use an e-mail address";
               uses apply-advanced;
               leaf identity-user {
                 description "The remote user-FQDN";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
           case case_6 {
             container key-id {
               description "Key ID identification values in string";
               uses apply-advanced;
               leaf string-key-id {
                 description "Key ID in ASCII string";
                 type string {
                   length "1 .. 127";
                 }
               }
             }
           }
         }
       }
       leaf external-interface {
         description "External interface for IKE negotiations";
         type union {
           type jt:interface-unit;
           type string {
             pattern "<.*>|$.*";
           }
         }
       }
       leaf local-address {
         description "Local IP address for IKE negotiations";
         type jt:ipaddr;
       }
       container aaa {
         description "Use extended authentication";
         uses apply-advanced;
         list access-profile {
           key name;
           ordered-by user;
           description "Access profile information";
           max-elements 1;
           uses access-profile-template;
         }
         container client {
           description "AAA client info for authentication";
           leaf username {
             description "AAA client username with 1 to 128 characters";
             type string {
               length "1 .. 128";
             }
           }
           leaf password {
             description "AAA client password with 1 to 128 characters";
             type string {
               length "1 .. 128";
             }
           }
         }
       }
       container xauth {
         description "Use extended authentication";
         status deprecated;
         uses apply-advanced;
         leaf access-profile {
           description "Access profile that contains authentication information";
           type string;
         }
         container client {
           description "Xauth client info for authentication";
           leaf username {
             description "XAuth client username with 1 to 128 characters";
             type string {
               length "1 .. 128";
             }
           }
           leaf password {
             description "XAuth client password with 1 to 128 characters";
             type string {
               length "1 .. 128";
             }
           }
         }
       }
       leaf general-ikeid {
         description "Accept peer IKE-ID in general";
         type empty;
       }
       container advpn {
         description "Enable Auto Discovery VPN";
         presence "enable advpn";
         uses advpn-suggester-partner;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
       container fragmentation {
         description "IKEv2 fragmentation configuration";
         uses apply-advanced;
         leaf disable {
           description "Disable IKEv2 fragmentation";
           type empty;
         }
         leaf size {
           description "Default 576 bytes for ipv4 and 1280 bytes for ipv6";
           type union {
             type string {
               pattern "<.*>|$.*";
             }
             type uint32 {
               range "570 .. 1320";
             }
           }
         }
       }
       leaf tcp-encap-profile {
         description "Ike over tcp profile name";
         type string;
       }
     }
   }
   grouping access-profile-template {
     description "Configure an access profile";
     leaf name {
       description "Access profile name used to authenticate with XAUTH/AAA server";
       type string;
     }
     uses apply-advanced;
     leaf config-payload-password {
       description "Common client password for IKEv2 config-payload with 1 to 128 characters";
       type string {
         length "1 .. 128";
       }
     }
   }
   grouping advpn-suggester-partner {
     description "Configure ADVPN Suggester Partner";
     uses apply-advanced;
     container suggester {
       presence "enable suggester";
       description "Configure Shortcut Suggester parameters";
       uses apply-advanced;
       leaf disable {
         description "Disable Suggester capability";
         type empty;
       }
     }
     container partner {
       presence "enable partner";
       description "Configure Shortcut Partner parameters";
       uses apply-advanced;
       leaf connection-limit {
         description "Maximum number of shortcut connections (default: varies per platform)";
         type union {
           type uint32;
           type string {
             pattern "<.*>|$.*";
           }
         }
       }
       leaf idle-time {
         description "The duration (in sec) after which shortcut is torn down (default: 300 sec)";
         default "300";
         units "seconds";
         type union {
           type string {
             pattern "<.*>|$.*";
           }
           type uint32 {
             range "60 .. 86400";
           }
         }
       }
       leaf idle-threshold {
         description "The packet rate below which shortcut is torn down (default: 5 packets/sec)";
         default "5";
         type union {
           type string {
             pattern "<.*>|$.*";
           }
           type uint32 {
             range "3 .. 5000";
           }
         }
       }
       leaf disable {
         description "Disable Partner capability";
         type empty;
       }
     }
   }
   grouping ike-policy {
     leaf name {
       description "Name of policy";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf reauth-frequency {
       description "Re-auth Peer after reauth-frequency times hard lifetime. (0-100) Default:0=Disabled";
       default "0";
       type union {
         type string {
           pattern "<.*>|$.*";
         }
         type uint32 {
           range "0 .. 100";
         }
       }
     }
     leaf description {
       description "Text description of IKE policy";
       type string {
         length "1 .. 80";
       }
     }
     leaf-list proposals {
       ordered-by user;
       description "Name of the proposal";
       type string {
         length "1 .. 32";
       }
     }
     container certificate {
       description "Certificate configuration";
       uses apply-advanced;
       leaf local-certificate {
         description "Local certificate identifier";
         type string {
         }
       }
       container trusted-ca {
         description "Specify the CA to use";
         choice ca {
           case case_1 {
             leaf ca-index {
               description "Index of the preferred CA to use";
               status deprecated;
               type union {
                 type uint32;
                 type string {
                   pattern "<.*>|$.*";
                 }
               }
             }
           }
           case case_2 {
             leaf use-all {
               description "Use all configured CAs";
               status deprecated;
               type empty;
             }
           }
           case case_3 {
             leaf ca-profile {
               description "Name of the preferred CA to use";
               type string;
             }
           }
           case case_4 {
             leaf trusted-ca-group {
               description "Name of the preferred CA group to use";
               type string;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
       leaf-list policy-oids {
         ordered-by user;
         description "Certificate policy object identifiers (maximum 5)";
         type string {
           length "1 .. 63";
         }
         max-elements 5;
       }
     }
     leaf proposal-set {
       description "Types of default IKE proposal-set";
       type enumeration {
         enum "basic" {
           description "IKE proposal-set for basic";
         }
         enum "compatible" {
           description "IKE proposal-set for compatible";
         }
         enum "standard" {
           description "IKE proposal-set for standard";
         }
         enum "suiteb-gcm-128" {
           description "IKE proposal-set for Suite-B-GCM-128";
         }
         enum "suiteb-gcm-256" {
           description "IKE proposal-set for Suite-B-GCM-256";
         }
         enum "prime-128" {
           description "IKE proposal-set for PRIME-128";
         }
         enum "prime-256" {
           description "IKE proposal-set for PRIME-256";
         }
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     container seeded-pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
   }
   grouping ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (256 bit modulus)";
         }
         enum "ecdsa-signatures-384" {
           description "ECDSA signatures (384 bit modulus)";
         }
         enum "ecdsa-signatures-521" {
           description "ECDSA signatures (521 bit modulus)";
         }
       }
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
         enum "group15" {
           description "Diffie-Hellman Group 15";
         }
         enum "group16" {
           description "Diffie-Hellman Group 16";
         }
         enum "group19" {
           description "Diffie-Hellman Group 19";
         }
         enum "group20" {
           description "Diffie-Hellman Group 20";
         }
         enum "group21" {
           description "Diffie-Hellman Group 21";
         }
         enum "group24" {
           description "Diffie-Hellman Group 24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
         enum "sha-512" {
           description "SHA 512-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
         }
         enum "aes-256-gcm" {
           description "AES-GCM 256-bit encryption algorithm";
         }
       }
     }
     leaf lifetime-seconds {
       description "Lifetime, in seconds";
       units "seconds";
       type union {
         type string {
           pattern "<.*>|$.*";
         }
         type uint32 {
           range "180 .. 86400";
         }
       }
     }
   }
   grouping security-ipsec-policies {
     uses apply-advanced;
     list from-zone {
       key "from-zone-name to-zone";
       ordered-by user;
       description "Define ipsec policy context";
       uses security-ipsec-policy;
     }
   }
   grouping security-ipsec-policy {
     leaf from-zone-name {
       description "Incoming zone";
       type string {
         length "1 .. 63";
       }
     }
     leaf to-zone {
       description "Outgoing zone";
       type string {
         length "1 .. 63";
       }
     }
     uses apply-advanced;
     leaf ipsec-group-vpn {
       description "Group VPN name";
       type string {
         length "1 .. 32";
       }
     }
   }
   grouping security-ipsec-vpn {
     uses apply-advanced;
     container internal {
       presence "enable internal";
       description "Define an IPSec SA for internal RE-RE communication";
       uses apply-advanced;
       container security-association {
         description "Define an IPsec security association";
         presence "enable security-association";
         uses ipsec-internal-sa;
       }
     }
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define a manual control plane SA ";
       uses ipsec-sa;
     }
     leaf anti-replay-window-size {
       description "Anti-replay window size Default 64";
       type union {
         type string {
           pattern "<.*>|$.*";
         }
         type uint32 {
           range "64 .. 8192";
         }
       }
     }
   }
   grouping ipsec-internal-sa {
     uses apply-advanced;
     container manual {
       description "Define a manual security association";
       uses apply-advanced;
       container encryption {
         description "Define encryption parameters";
         uses apply-advanced;
         leaf algorithm {
           description "Define encryption algorithm";
           type enumeration {
             enum "3des-cbc" {
               description "3DES-CBC encryption algorithm";
             }
             enum "aes-128-cbc" {
               description "AES-CBC 128-bit encryption algorithm";
             }
           }
         }
         leaf ike-ha-link-encryption {
           description "Enable HA link encryption IKE internal messages";
           type enumeration {
             enum "enable" {
               description "Enable HA link encryption IKE internal messages";
             }
           }
         }
         container key {
           description "Define an encryption key";
           choice key-choice {
             case case_1 {
               leaf ascii-text {
                 description "Format as text";
                 type jt:unreadable;
               }
             }
           }
         }
       }
     }
   }
   grouping ipsec-policy {
     leaf name {
       description "Name of the IPSec policy";
       type string {
         length "1 .. 32";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group 1";
           }
           enum "group2" {
             description "Diffie-Hellman Group 2";
           }
           enum "group5" {
             description "Diffie-Hellman Group 5";
           }
           enum "group14" {
             description "Diffie-Hellman Group 14";
           }
           enum "group15" {
             description "Diffie-Hellman Group 15";
           }
           enum "group16" {
             description "Diffie-Hellman Group 16";
           }
           enum "group19" {
             description "Diffie-Hellman Group 19";
           }
           enum "group20" {
             description "Diffie-Hellman Group 20";
           }
           enum "group21" {
             description "Diffie-Hellman Group 21";
           }
           enum "group24" {
             description "Diffie-Hellman Group 24";
           }
         }
       }
     }
     leaf-list proposals {
       ordered-by user;
       description "Name of the proposal";
       type string {
         length "1 .. 32";
       }
     }
     leaf proposal-set {
       description "Types of default IPSEC proposal-set";
       type enumeration {
         enum "basic" {
           description "IPSEC basic proposal-set";
         }
         enum "compatible" {
           description "IPSEC compatible proposal-set";
         }
         enum "standard" {
           description "IPSEC standard proposal-set";
         }
         enum "suiteb-gcm-128" {
           description "IPSec proposal-set for Suite-B-GCM-128";
         }
         enum "suiteb-gcm-256" {
           description "IPSec proposal-set for Suite-B-GCM-256";
         }
         enum "prime-128" {
           description "IPSec proposal-set for PRIME-128";
         }
         enum "prime-256" {
           description "IPSec proposal-set for PRIME-256";
         }
       }
     }
   }
   grouping ipsec-proposal {
     leaf name {
       description "Name of the IPSec proposal";
       type string {
         length "1 .. 32";
       }
     }
     uses apply-advanced;
     leaf extended-sequence-number {
       description "Extended Sequence Number enabled";
       type empty;
     }
     leaf description {
       description "Text description of IPSec proposal";
       type string {
         length "1 .. 80";
       }
     }
     leaf protocol {
       description "Define an IPSec protocol for the proposal";
       type enumeration {
         enum "ah" {
           description "Authentication header";
         }
         enum "esp" {
           description "Encapsulated Security Payload header";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
         }
         enum "hmac-sha-256-96" {
           description "HMAC-SHA-256-96 authentication algorithm (non-RFC compliant)";
         }
         enum "hmac-sha-384" {
           description "HMAC-SHA-384 authentication algorithm";
         }
         enum "hmac-sha-512" {
           description "HMAC-SHA-512 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm";
         }
         enum "aes-192-gcm" {
           description "AES-GCM 192-bit encryption algorithm";
         }
         enum "aes-256-gcm" {
           description "AES-GCM 256-bit encryption algorithm";
         }
       }
     }
     leaf lifetime-seconds {
       description "Lifetime, in seconds";
       units "seconds";
       type union {
         type string {
           pattern "<.*>|$.*";
         }
         type uint32 {
           range "180 .. 86400";
         }
       }
     }
   }
   grouping ipsec-sa {
     leaf name {
       description "Name of IPSec security association";
       type string {
         length "1 .. 32";
       }
     }
     uses apply-advanced;
     leaf description {
       description "Text description of security association";
       type string {
         length "1 .. 80";
       }
     }
     leaf mode {
       description "Define security association mode";
       default "transport";
       type enumeration {
         enum "transport" {
           description "Transport mode";
         }
       }
     }
     choice sa_choice {
       case case_1 {
         container manual {
           description "Define a manual security association";
           uses security-association-manual;
         }
       }
     }
   }
   grouping ipsec-traceoptions {
     description "Data-plane IPSec tracing options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events to include in data-plane IPSec trace output";
       leaf name {
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       type string {
         length "1 .. 32";
       }
     }
     uses apply-advanced;
     leaf ha-link-encryption {
       description "Enable HA link encryption";
       type empty;
     }
     leaf bind-interface {
       description "Bind to tunnel interface (route-based VPN)";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container multi-sa {
       presence "enable multi-sa";
       description "Negotiate multiple SAs based on configuration choice";
       uses apply-advanced;
       choice sa_map {
         case case_1 {
           list forwarding-class {
             key name;
             ordered-by user;
             leaf name {
               description "Name of forwarding classes";
               type string {
                 length "1 .. 32";
               }
             }
             uses apply-advanced;
           }
         }
       }
     }
     leaf copy-outer-dscp {
       description "Enable copying outer IP header DSCP and ECN to inner IP header";
       type empty;
     }
     container vpn-monitor {
       description "Monitor VPN liveliness";
       presence "enable vpn-monitor";
       uses ipsec-template-monitor;
     }
     choice negotiation {
       case case_1 {
         container manual {
           description "Define a manual security association";
           uses apply-advanced;
           leaf gateway {
             description "Define the IPSec peer";
             type jt:hostname;
           }
           leaf external-interface {
             description "External interface for the security association";
             type union {
               type jt:interface-unit;
               type string {
                 pattern "<.*>|$.*";
               }
             }
           }
           leaf protocol {
             description "Define an IPSec protocol for the security association";
             type enumeration {
               enum "ah" {
                 description "Authentication header";
               }
               enum "esp" {
                 description "Encapsulated Security Payload header";
               }
             }
           }
           leaf spi {
             description "Define security parameter index";
             type union {
               type string {
                 pattern "<.*>|$.*";
               }
               type uint32 {
                 range "256 .. 16639";
               }
             }
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
                 enum "hmac-sha-384" {
                   description "HMAC-SHA-384 authentication algorithm";
                 }
                 enum "hmac-sha-512" {
                   description "HMAC-SHA-512 authentication algorithm";
                 }
               }
             }
             container key {
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
                 enum "aes-128-gcm" {
                   description "AES-GCM 128-bit encryption algorithm";
                 }
                 enum "aes-256-gcm" {
                   description "AES-GCM 256-bit encryption algorithm";
                 }
               }
             }
             container key {
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                     }
                   }
                 }
               }
             }
           }
         }
       }
       case case_2 {
         container ike {
           description "Define an IKE-keyed IPSec vpn";
           uses apply-advanced;
           leaf gateway {
             description "Name of remote gateway";
             type string {
               length "1 .. 32";
             }
           }
           leaf anti-replay-window-size {
             description "Anti-replay window size Default 64";
             type union {
               type string {
                 pattern "<.*>|$.*";
               }
               type uint32 {
                 range "64 .. 8192";
               }
             }
           }
           leaf no-anti-replay {
             description "Disable the anti-replay check";
             type empty;
           }
           container proxy-identity {
             description "IPSec proxy-id to use in IKE negotiations";
             presence "enable proxy-identity";
             uses ipsec-template-proxy-id;
           }
           leaf ipsec-policy {
             description "Name of the IPSec policy";
             type string {
               length "1 .. 32";
             }
           }
           leaf install-interval {
             description "Delay installation of rekeyed outbound SAs on initiator";
             default "1";
             units "seconds";
             type union {
               type string {
                 pattern "<.*>|$.*";
               }
               type uint32 {
                 range "0 .. 10";
               }
             }
           }
         }
       }
     }
     list traffic-selector {
       key name;
       ordered-by user;
       description "Traffic selector";
       max-elements 200;
       leaf name {
         description "Name of traffic selector";
         type string {
           length "1 .. 31";
         }
       }
       uses apply-advanced;
       list term {
         key name;
         ordered-by user;
         description "Define a set of traffic selector rules";
         max-elements 200;
         uses traffic-selector-term-object;
       }
       leaf local-ip {
         description "IP address of local traffic-selector";
         type jt:ipprefix-mandatory;
       }
       leaf remote-ip {
         description "IP address of remote traffic-selector";
         type jt:ipprefix-mandatory;
       }
       leaf protocol {
         description "Define protocol";
         type string;
       }
       leaf source-port {
         description "Hyphenated source port range";
         type string;
       }
       leaf destination-port {
         description "Hyphenated destination port range";
         type string;
       }
       leaf metric {
         description "Metric value for st0 route";
         type union {
           type string {
             pattern "<.*>|$.*";
           }
           type uint32 {
             range "1 .. 4294967295";
           }
         }
       }
       leaf description {
         description "Describe the traffic selector";
         type string {
           length "1 .. 80";
         }
       }
     }
     leaf establish-tunnels {
       description "Define the criteria to establish tunnels";
       default "on-traffic";
       type enumeration {
         enum "immediately" {
           description "Establish tunnels immediately";
         }
         enum "on-traffic" {
           description "Establish tunnels on traffic";
         }
         enum "responder-only" {
           description "Establish tunnels only on receiving negotiation from peer";
         }
         enum "responder-only-no-rekey" {
           description "Disable rekey in responder-only mode";
         }
       }
     }
     leaf distribution-profile {
       description "Specify a distribution-profile to distribute tunnel";
       type string;
     }
     leaf tunnel-mtu {
       description "Maximum transmit packet size";
       type union {
         type string {
           pattern "<.*>|$.*";
         }
         type uint32 {
           range "256 .. 9192";
         }
       }
     }
     leaf no-icmp-packet-too-big {
       description "Disable ICMP packet too big notifications for IPv6 packets only";
       type empty;
     }
     leaf passive-mode-tunneling {
       description "No active IP packet checks before IPSec encapsulation";
       type empty;
     }
     leaf match-direction {
       description "Direction for which the rule match is applied";
       type enumeration {
         enum "input" {
           description "Match on input to interface";
         }
         enum "output" {
           description "Match on output from interface";
         }
       }
     }
     container udp-encapsulate {
       presence "enable udp-encapsulate";
       description "UDP encapsulation of IPsec data traffic";
       leaf dest-port {
         description "UDP destination port";
         default "4565";
         type union {
           type string {
             pattern "<.*>|$.*";
           }
           type uint32 {
             range "1025 .. 65536";
           }
         }
       }
     }
   }
   grouping ipsec-template-monitor {
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
     container verify-path {
       presence "enable verify-path";
       description "Verify IPSec path using vpn-monitor before bring up st0 state";
       uses apply-advanced;
       leaf destination-ip {
         description "Destination IP addres for verify IPSec path";
         type jt:ipaddr;
       }
       leaf packet-size {
         description "Size of the packet";
         default "64";
         type union {
           type string {
             pattern "<.*>|$.*";
           }
           type uint32 {
             range "64 .. 1350";
           }
         }
       }
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-association-manual {
     uses apply-advanced;
     list direction {
       key name;
       ordered-by user;
       description "Define the direction of the security association";
       leaf name {
         type enumeration {
           enum "bidirectional" {
             description "Bidirectional security association";
           }
         }
       }
       uses apply-advanced;
       leaf protocol {
         description "Define an IPSec protocol for the security association";
         type enumeration {
           enum "ah" {
             description "Authentication header";
           }
           enum "esp" {
             description "Encapsulated Security Payload header";
           }
         }
       }
       leaf spi {
         description "Define security parameter index";
         type union {
           type string {
             pattern "<.*>|$.*";
           }
           type uint32 {
             range "256 .. 16639";
           }
         }
       }
       container authentication {
         description "Define authentication parameters";
         uses apply-advanced;
         leaf algorithm {
           description "Define authentication algorithm";
           type enumeration {
             enum "hmac-md5-96" {
               description "HMAC-MD5-96 authentication algorithm";
             }
             enum "hmac-sha1-96" {
               description "HMAC-SHA1-96 authentication algorithm";
             }
           }
         }
         container key {
           description "Define an authentication key";
           choice key-choice {
             case case_1 {
               leaf ascii-text {
                 description "Format as text";
                 type string {
                   length "1 .. 255";
                 }
               }
             }
             case case_2 {
               leaf hexadecimal {
                 description "Format as hexadecimal";
                 type string {
                   length "1 .. 255";
                 }
               }
             }
           }
         }
       }
       container encryption {
         description "Define encryption parameters";
         uses apply-advanced;
         leaf algorithm {
           description "Define encryption algorithm";
           type enumeration {
             enum "des-cbc" {
               description "DES-CBC encryption algorithm";
             }
             enum "3des-cbc" {
               description "3DES-CBC encryption algorithm";
             }
           }
         }
         container key {
           description "Define an encryption key";
           choice key-choice {
             case case_1 {
               leaf ascii-text {
                 description "Format as text";
                 type string {
                   length "1 .. 255";
                 }
               }
             }
             case case_2 {
               leaf hexadecimal {
                 description "Format as hexadecimal";
                 type string {
                   length "1 .. 255";
                 }
               }
             }
           }
         }
       }
     }
   }
   grouping security-macsec {
     uses apply-advanced;
     container traceoptions {
       description "Tracing options for debugging protocol operation";
       presence "enable traceoptions";
       uses macsec-trace-options;
     }
     list connectivity-association {
       key name;
       ordered-by user;
       description "Configure connectivity association properties";
       leaf name {
         description "Connectivity association name";
         type string {
           length "1 .. 32";
         }
       }
       uses apply-advanced;
       leaf cipher-suite {
         description "Cipher suite to be used for encryption";
         type enumeration {
           enum "gcm-aes-128" {
             description "GCM-AES-128 cipher suite";
           }
           enum "gcm-aes-256" {
             description "GCM-AES-256 cipher suite";
           }
           enum "gcm-aes-xpn-128" {
             description "GCM-AES-XPN-128 cipher suite";
           }
           enum "gcm-aes-xpn-256" {
             description "GCM-AES-XPN-256 cipher suite";
           }
         }
       }
       leaf security-mode {
         description "Connectivity association mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
       }
       leaf sak-hash-128 {
         description "Configure to generate 128bit SAK hash to program HW";
         type empty;
       }
       list secure-channel {
         key name;
         ordered-by user;
         description "Configure secure channel properties";
         leaf name {
           description "Secure channel name";
           type string;
         }
         uses apply-advanced;
         container id {
           description "Secure channel identifier";
           uses apply-advanced;
           leaf mac-address {
             description "MAC addresses";
             type jt:mac-addr;
           }
           leaf port-id {
             description "Port identifier";
             type union {
               type string {
                 pattern "<.*>|$.*";
               }
               type uint32 {
                 range "1 .. 65535";
               }
             }
           }
         }
         leaf direction {
           description "Secure channel direction";
           type enumeration {
             enum "inbound" {
             }
             enum "outbound" {
             }
           }
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             type union {
               type string {
                 pattern "<.*>|$.*";
               }
               type uint32 {
                 range "0 .. 3";
               }
             }
           }
           uses apply-advanced;
           leaf key {
             description "Security association key in hexadecimal format of length 32";
             type string {
               length 32;
             }
           }
         }
       }
       container mka {
         presence "enable mka";
         description "Configure MAC Security Key Agreement protocol properties";
         uses apply-advanced;
         leaf transmit-interval {
           description "Configure MKA periodic transmit interval";
           default "2000";
           units "milliseconds";
           type union {
             type string {
               pattern "<.*>|$.*";
             }
             type uint32 {
               range "2000 .. 6000";
             }
           }
         }
         leaf sak-rekey-interval {
           description "Configure SAK rekeying interval";
           units "seconds";
           type union {
             type string {
               pattern "<.*>|$.*";
             }
             type uint32 {
               range "60 .. 86400";
             }
           }
         }
         leaf bounded-delay {
           description "Configure Bounded Hello Time";
           type empty;
         }
         leaf suspend-on-request {
           description "Configure on key-server to accept suspend-on-request during gres or issu";
           type empty;
         }
         leaf suspend-for {
           description "Configure to suspend MKA during gres or issu";
           type empty;
         }
         leaf key-server-priority {
           description "Configure MKA key server priority";
           default "16";
           type union {
             type string {
               pattern "<.*>|$.*";
             }
             type uint32 {
               range "0 .. 255";
             }
           }
         }
         leaf must-secure {
           description "Allows only secure traffic, by default enabled for static-cak";
           type empty;
         }
         leaf should-secure {
           description "Allows non-secure traffic if MKA session fails, by default enabled for dynamic mode";
           type empty;
         }
         leaf eapol-address {
           description "Configure EAPOL destination group address";
           default "pae";
           type string;
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
         }
       }
       leaf no-encryption {
         description "Disable encryption";
         type empty;
       }
       leaf disable-preceding-key {
         description "Disable CA preceding key duing key switch-over";
         type empty;
       }
       leaf offset {
         description "Confidentiality offset";
         default "0";
         type enumeration {
           enum "0" {
             description "Confidentiality provided for all octets of data";
           }
           enum "30" {
             description "Confidentiality not provided for initial 30 octets of data";
           }
           enum "50" {
             description "Confidentiality not provided for initial 50 octets of data";
           }
         }
       }
       leaf include-sci {
         description "Include secure channel identifier in MAC Security PDU";
         type empty;
       }
       container pre-shared-key {
         presence "enable pre-shared-key";
         description "Configure pre-shared connectivity association key";
         uses apply-advanced;
         leaf ckn {
           description "Connectivity association key name in hexadecimal format";
           type string {
             length "2 .. 64";
           }
         }
         leaf cak {
           description "Connectivity association key in hexadecimal format";
           type string {
             length "1 .. 64";
           }
         }
       }
       container fallback-key {
         presence "enable fallback-key";
         description "Configure fallback key for connectivity association";
         uses apply-advanced;
         leaf ckn {
           description "Connectivity association fallback key name in hexadecimal format";
           type string {
             length "2 .. 64";
           }
         }
         leaf cak {
           description "Connectivity association fallback key secret in hexadecimal format";
           type string {
             length "1 .. 64";
           }
         }
       }
       leaf pre-shared-key-chain {
         description "Pre-shared key chain name for connectivity association";
         type string {
         }
       }
       list exclude-protocol {
         key name;
         ordered-by user;
         description "Configure protocols to exclude from MAC Security";
         leaf name {
           type enumeration {
             enum "cdp" {
               description "Cisco Discovery Protocol";
             }
             enum "lldp" {
               description "Link Level Discovery Protocol";
             }
             enum "lacp" {
               description "Link Aggregation Control Protocol";
             }
           }
         }
       }
     }
     list interfaces {
       key name;
       description "Interfaces on which macsec configuration is applied";
       leaf name {
         type union {
           type jt:interface-device;
           type string {
             pattern "<.*>|$.*";
           }
         }
       }
       uses apply-advanced;
       list unit {
         key name;
         description "Logical interface";
         leaf name {
           description "Logical unit number";
           type union {
             type string {
               pattern "<.*>|$.*";
             }
             type uint32 {
               range "0 .. 16385";
             }
           }
         }
         uses apply-advanced;
         leaf connectivity-association {
           description "Connectivity association name";
           type string;
         }
         container traceoptions {
           description "Tracing options of MKA protocol";
           presence "enable traceoptions";
           uses mka-trace-options;
         }
       }
       leaf connectivity-association {
         description "Connectivity association name";
         type string;
       }
       leaf pre-shared-key-chain {
         description "Pre-shared key chain name for connectivity association";
         type string {
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
         }
       }
       container traceoptions {
         description "Tracing options of MKA protocol";
         presence "enable traceoptions";
         uses mka-trace-options;
       }
     }
     list cluster-control-port {
       key name;
       description "Cluster control port on which macsec configuration is applied";
       leaf name {
         description "Port identifier";
         type union {
           type string {
             pattern "<.*>|$.*";
           }
           type uint32 {
             range "0 .. 1";
           }
         }
       }
       uses apply-advanced;
       leaf connectivity-association {
         description "Connectivity association name";
         type string;
       }
       container traceoptions {
         description "Tracing options of MKA protocol";
         presence "enable traceoptions";
         uses mka-trace-options;
       }
     }
     list cluster-data-port {
       key name;
       description "Cluster data port on which macsec configuration is applied";
       leaf name {
         type union {
           type jt:interface-device;
           type string {
             pattern "<.*>|$.*";
           }
         }
       }
       uses apply-advanced;
       leaf connectivity-association {
         description "Connectivity association name";
         type string;
       }
       container traceoptions {
         description "Tracing options of MKA protocol";
         presence "enable traceoptions";
         uses mka-trace-options;
       }
     }
   }
   grouping macsec-trace-options {
     description "Trace options for MACSec Protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "config" {
             description "Trace configuration messages";
           }
           enum "debug" {
             description "Trace debug messages";
           }
           enum "telemetry" {
             description "Trace telemetry messages";
           }
           enum "normal" {
             description "Trace normal messages";
           }
           enum "all" {
             description "Trace all";
           }
         }
       }
     }
   }
   grouping mka-trace-options {
     description "Trace options for MKA protocol";
     uses apply-advanced;
     container file {
       description "Trace file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       description "Tracing parameters";
       leaf name {
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-pki {
     uses apply-advanced;
     list ca-profile {
       key name;
       ordered-by user;
       description "Certificate authority profile configuration";
       leaf name {
         description "Name of certificate authority profile";
         type string {
           length "1 .. 32";
         }
       }
       uses apply-advanced;
       leaf ca-identity {
         description "Certificate authority identifier";
         type string;
       }
       leaf source-address {
         description "Use specified address as source address";
         type jt:ipaddr;
       }
       leaf proxy-profile {
         description "Use specified proxy server";
         type string;
       }
       leaf routing-instance {
         description "Use specified routing instance";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             leaf on-download-failure {
               description "Check revocation status with existing CRL file if present, otherwise skip. This feature must be enabled for manual CRL download.";
               type empty;
             }
           }
           list url {
             key name;
             ordered-by user;
             leaf name {
               description "URL of CRL distribution point for certificate authority";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         type string {
           length "1 .. 63";
         }
       }
       uses apply-advanced;
       leaf-list ca-profiles {
         ordered-by user;
         description "Name of the CA profiles (maximum 20)";
         type string {
           length "1 .. 63";
         }
         max-elements 20;
       }
     }
     container trap {
       presence "enable trap";
       description "Trap options for PKI certificates";
       uses apply-advanced;
       list certificate-id {
         key name;
         ordered-by user;
         description "Local certificate identifier";
         leaf name {
           description "Local cert id";
           type string;
         }
         uses apply-advanced;
         leaf days {
           description "Number of days to generate trap (default 60)";
           default "60";
           type union {
             type string {
               pattern "<.*>|$.*";
             }
             type uint32 {
               range "1 .. 100";
             }
           }
         }
       }
       list ca-identity {
         key name;
         ordered-by user;
         description "CA identity";
         leaf name {
           description "CA profile";
           type string;
         }
         uses apply-advanced;
         leaf days {
           description "Number of days to generate trap (default 60)";
           default "60";
           type union {
             type string {
               pattern "<.*>|$.*";
             }
             type uint32 {
               range "1 .. 100";
             }
           }
         }
       }
       container all-certificates {
         presence "enable all-certificates";
         description "Trap config for all certificates";
         uses apply-advanced;
         leaf days {
           description "Number of days to generate trap (default 60)";
           default "60";
           type union {
             type string {
               pattern "<.*>|$.*";
             }
             type uint32 {
               range "1 .. 100";
             }
           }
         }
       }
     }
     container auto-re-enrollment {
       description "Auto re-enroll of certificate";
       uses apply-advanced;
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             type string {
             }
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days from now";
                   type union {
                     type uint32;
                     type string {
                       pattern "<.*>|$.*";
                     }
                   }
                 }
               }
               case case_2 {
                 leaf hours {
                   description "Re-enrollment trigger time in hours from now";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             type string {
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             type string {
             }
           }
           uses apply-advanced;
           container re-enroll-time {
             presence "enable re-enroll-time";
             description "Re-enroll time in days <value> | hours <value> | percentage <value>";
             uses apply-advanced;
             choice re-enroll-time-options {
               case case_1 {
                 leaf days {
                   description "Re-enrollment trigger time in days from now";
                   type union {
                     type uint32;
                     type string {
                       pattern "<.*>|$.*";
                     }
                   }
                 }
               }
               case case_2 {
                 leaf hours {
                   description "Re-enrollment trigger time in hours from now";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             type string {
             }
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         leaf name {
           description "Certificate identifier that needs auto re-enrollment";
           type string {
           }
         }
         uses apply-advanced;
         container re-enroll-time {
           presence "enable re-enroll-time";
           description "Re-enroll trigger time in days <value> | hours <value> | percentage <value>";
           uses apply-advanced;
           choice re-enroll-time-options {
             case case_1 {
               leaf days {
                 description "Re-enrollment trigger time in days from now";
                 type union {
                   type uint32;
                   type string {
                     pattern "<.*>|$.*";
                   }
                 }
               }
             }
             case case_2 {
               leaf hours {
                 description "Re-enrollment trigger time in hours from now";
                 type union {
                   type uint32;
                   type string {
                     pattern "<.*>|$.*";
                   }
                 }
               }
             }
             case case_3 {
               leaf percent {
                 description "Re-enrollment trigger time before expiration as percentage";
                 type union {
                   type string {
                     pattern "<.*>|$.*";
                   }
                   type uint32 {
                     range "1 .. 99";
                   }
                 }
               }
             }
           }
         }
         leaf ca-profile-name {
           description "Name of certificate authority profile";
           type string {
           }
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
         leaf validity-period {
           description "Certificate validity period in days from enrollment start date";
           status deprecated;
           type union {
             type string {
               pattern "<.*>|$.*";
             }
             type uint32 {
               range "1 .. 4095";
             }
           }
         }
       }
     }
     container traceoptions {
       description "PKI trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "certificate-verification" {
               description "PKI certificate verification tracing";
             }
             enum "online-crl-check" {
               description "PKI online crl tracing";
             }
             enum "enrollment" {
               description "PKI certificate enrollment tracing";
             }
             enum "all" {
               description "Trace with all flags enabled";
             }
           }
         }
       }
     }
   }
   grouping security-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     container filter {
       description "Filter parameters for IKE traceoptions";
       uses apply-advanced;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     list flag {
       key name;
       ordered-by user;
       description "Tracing parameters for IKE";
       leaf name {
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
         }
       }
     }
   }
   grouping security-zone-type {
     description "Security zone";
     leaf name {
       description "Name of the zone";
       type string {
         length "1 .. 63";
       }
     }
     uses apply-advanced;
     leaf description {
       description "Text description of zone";
       type string {
         length "1 .. 900";
       }
     }
     leaf tcp-rst {
       description "Send RST for NON-SYN packet not matching TCP session";
       type empty;
     }
     container address-book {
       description "Address book entries";
       uses address-book-type;
     }
     leaf screen {
       description "Name of ids option object applied to the zone";
       type string {
         length "1 .. 32";
       }
     }
     container host-inbound-traffic {
       description "Allowed system services & protocols";
       uses zone_host_inbound_traffic_t;
     }
     list interfaces {
       key name;
       ordered-by user;
       description "Interfaces that are part of this zone";
       uses zone-interface-list-type;
     }
     leaf application-tracking {
       description "Enable Application tracking support for this zone";
       type empty;
     }
     leaf source-identity-log {
       description "Show user and group info in session log for this zone";
       type empty;
     }
     container advance-policy-based-routing-profile {
       description "Enable Advance Policy Based Routing on this zone";
       uses apply-advanced;
       leaf profile {
         description "Advance policy based routing profile name";
         type string {
           length "1 .. 63";
         }
       }
     }
     leaf enable-reverse-reroute {
       description "Enable Reverse route lookup when there is change in ingress interface";
       type empty;
     }
     leaf unidirectional-session-refreshing {
       description "Enable unidirectional session refreshing on this zone";
       type empty;
     }
     container advanced-connection-tracking {
       description "Enable Advance Policy Based Routing on this zone";
       uses apply-advanced;
       leaf timeout {
         description "Timeout value in seconds for advanced-connection-tracking table for this zone";
         type union {
           type uint32;
           type string {
             pattern "<.*>|$.*";
           }
         }
       }
       leaf mode {
         type enumeration {
           enum "allow-any-host" {
             description "Create allow-any-host table, thus policies whose to-zone is this zone can lookup";
           }
           enum "allow-target-host" {
             description "Create allow-target-host table, thus policies whose to-zone is this zone can lookup";
           }
           enum "allow-target-host-port" {
             description "Create allow-target-host-port table, thus policies whose to-zone is this zone can lookup";
           }
         }
       }
       leaf track-all-policies-to-this-zone {
         description "Mandate all policies with to-zone set to this zone to do connection track table lookup";
         type empty;
       }
     }
   }
   grouping address-book-type {
     description "Configure security address book for the zone";
     uses apply-advanced;
     list address {
       key name;
       ordered-by user;
       description "Define a security address";
       uses address_type;
     }
     list address-set {
       key name;
       ordered-by user;
       description "Define a security address set";
       uses address_set_type;
     }
   }
   grouping security_intelligence_feeds {
     description "Specify the feed post action";
     uses apply-advanced;
     container add-source-ip-to-feed {
       description "Add Source IP to Feed";
       uses apply-advanced;
       leaf name-of-feed {
         description "Specify the desired feed-name";
         type string {
           length "1 .. 64";
         }
       }
     }
     container add-destination-ip-to-feed {
       description "Add Destination IP to Feed";
       uses apply-advanced;
       leaf name-of-feed {
         description "Specify the desired feed-name";
         type string {
           length "1 .. 64";
         }
       }
     }
     container add-source-identity-to-feed {
       description "Add Source Identity to Feed";
       uses apply-advanced;
       leaf name-of-feed {
         description "Specify the desired feed-name";
         type string {
           length "1 .. 64";
         }
       }
     }
     container add-destination-identity-to-feed {
       description "Add Destination Identity to Feed";
       uses apply-advanced;
       leaf name-of-feed {
         description "Specify the desired feed-name";
         type string {
           length "1 .. 64";
         }
       }
     }
   }
   grouping server {
     description "Server settings";
     uses apply-advanced;
     leaf host {
       description "Server host IP address or string host name";
       type string;
     }
     leaf port {
       description "Server port";
       type union {
         type string {
           pattern "<.*>|$.*";
         }
         type uint32 {
           range "1024 .. 65535";
         }
       }
     }
     leaf routing-instance {
       description "Routing instance name";
       type string;
     }
     leaf source-address {
       description "Source ip address used to connect server";
       type jt:ipaddr;
     }
   }
   grouping session_timeout_type {
     uses apply-advanced;
     leaf tcp {
       description "Timeout value for tcp sessions";
       units "seconds";
       type union {
         type string {
           pattern "<.*>|$.*";
         }
         type uint32 {
           range "4 .. 86400";
         }
       }
     }
     leaf udp {
       description "Timeout value for udp sessions";
       units "seconds";
       type union {
         type string {
           pattern "<.*>|$.*";
         }
         type uint32 {
           range "4 .. 86400";
         }
       }
     }
     leaf ospf {
       description "Timeout value for ospf sessions";
       units "seconds";
       type union {
         type string {
           pattern "<.*>|$.*";
         }
         type uint32 {
           range "4 .. 86400";
         }
       }
     }
     leaf icmp {
       description "Timeout value for icmp sessions";
       units "seconds";
       type union {
         type string {
           pattern "<.*>|$.*";
         }
         type uint32 {
           range "4 .. 86400";
         }
       }
     }
     leaf icmp6 {
       description "Timeout value for icmp6 sessions";
       units "seconds";
       type union {
         type string {
           pattern "<.*>|$.*";
         }
         type uint32 {
           range "4 .. 86400";
         }
       }
     }
     leaf others {
       description "Timeout value for other sessions";
       units "seconds";
       type union {
         type string {
           pattern "<.*>|$.*";
         }
         type uint32 {
           range "4 .. 86400";
         }
       }
     }
   }
   grouping sfw_match_object {
     uses apply-advanced;
     list source-address {
       key name;
       ordered-by user;
       description "Match IP source address";
       uses sfw_addr_object;
     }
     list destination-address {
       key name;
       ordered-by user;
       description "Match IP destination address";
       uses sfw_addr_object;
     }
     container destination-port {
       presence "enable destination-port";
       uses apply-advanced;
       choice port_choice {
         case case_1 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
           }
         }
       }
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list applications {
       ordered-by user;
       description "Match one or more applications";
       type string;
     }
     list application-sets {
       key name;
       ordered-by user;
       description "Match one or more application sets";
       leaf name {
         type string {
           length "1 .. 63";
         }
       }
       uses apply-advanced;
     }
     leaf-list application {
       ordered-by user;
       type string;
     }
   }
   grouping sfw_addr_object {
     leaf name {
       description "Match IP address";
       type string;
     }
     leaf except {
       description "Match address not in this prefix";
       type empty;
     }
   }
   grouping sla_policy_type {
     leaf name {
       description "APBR policy name";
       type string {
         length "1 .. 63";
       }
     }
     uses apply-advanced;
     leaf description {
       description "Text description of policy";
       type string {
         length "1 .. 900";
       }
     }
     container match {
       description "Specify sla policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             description "Specify application or application-set name to match";
             type string {
               length "1 .. 63";
             }
           }
         }
       }
       choice source_identity_choice {
         case case_1 {
           leaf-list source-identity {
             ordered-by user;
             type string;
           }
         }
       }
     }
     container then {
       description "Specify policy action to take when packet match criteria";
       uses apply-advanced;
       choice action {
         case case_1 {
           container application-services {
             description "Application Services";
             uses sla_application_services_type;
           }
         }
       }
     }
     leaf scheduler-name {
       description "Name of scheduler";
       type string {
         length "1 .. 63";
       }
     }
   }
   grouping sla_application_services_type {
     description "Application Services";
     uses apply-advanced;
     leaf advance-policy-based-routing-profile {
       description "Specify APBR profile name";
       type string {
         length "1 .. 63";
       }
     }
   }
   grouping softwires-object {
     description "Configure softwire feature";
     uses apply-advanced;
     list softwire-name {
       key name;
       description "Configure softwire object";
       uses softwire-option-type;
     }
     container softwire-types {
       description "Configure softwire objects";
       uses apply-advanced;
       list v6rd {
         key name;
         description "Configure v6rd object";
         uses softwire-option-type;
       }
       list ds-lite {
         key name;
         description "Configure ds-lite object";
         uses softwire-option-type;
       }
       list map-e {
         key name;
         ordered-by user;
         description "Configure Map-e object";
         uses map-e-domain;
       }
     }
     list map-e {
       key name;
       ordered-by user;
       description "Configure a MAP-E domain and domain rules";
       max-elements 1;
       uses map-e-domain;
     }
     container traceoptions {
       description "Trace options for Network Security DS-Lite";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping map-e-domain {
     description "Configure a MAP-E domain";
     leaf name {
       description "MAP-E domain name";
       type string {
         length "1 .. 11";
       }
     }
     uses apply-advanced;
     leaf confidentiality {
       description "Configure JUNOS MAP-E confidentiality";
       type empty;
     }
     leaf br-address {
       description "Ipv6 address of BR";
       type jt:unreadable;
     }
     container end-user-prefix {
       description "Configure end-user-prefix value or source interface for obtaining end-user-prefix";
       uses apply-advanced;
       leaf prefix-value {
         description "End user prefix";
         type jt:ipv6prefix;
       }
     }
     list rule {
       key name;
       ordered-by user;
       description "Configure a BMR or FMR rule for map-e ";
       max-elements 101;
       uses map-e-rule;
     }
     leaf role {
       description "Define a role of the MAP-E";
       type enumeration {
         enum "CE" {
           description "CE deployment";
         }
       }
     }
     leaf version {
       description "Define version of the MAP-E";
       type enumeration {
         enum "3" {
           description "Version 3: draft-ietf-softwire-map-03";
         }
       }
     }
   }
   grouping map-e-rule {
     description "Configure a MAP-E rule";
     leaf name {
       description "MAP-E rule name";
       type string {
         length "1 .. 11";
       }
     }
     uses apply-advanced;
     leaf rule-type {
       description "Define a rule type of MAP-E";
       type enumeration {
         enum "BMR" {
           description "Define BMR rule type";
         }
         enum "FMR" {
           description "Define FMR rule type";
         }
       }
     }
     leaf ipv4-prefix {
       description "Ipv4 prefix";
       type jt:unreadable;
     }
     leaf ipv6-prefix {
       description "Ipv6 prefix";
       type jt:unreadable;
     }
     leaf ea-bits-length {
       description "EA bits length";
       type union {
         type string {
           pattern "<.*>|$.*";
         }
         type uint32 {
           range "0 .. 48";
         }
       }
     }
     leaf psid-offset {
       description "PSID offset";
       type jt:unreadable;
     }
     leaf psid-len {
       description "PSID length";
       type union {
         type string {
           pattern "<.*>|$.*";
         }
         type uint32 {
           range "0 .. 16";
         }
       }
     }
     leaf mtu-v6 {
       description "MTU for the softwire tunnel";
       default "9192";
       type union {
         type string {
           pattern "<.*>|$.*";
         }
         type uint32 {
           range "1280 .. 9192";
         }
       }
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
     leaf mtu-v6 {
       description "MTU for the softwire tunnel";
       type union {
         type string {
           pattern "<.*>|$.*";
         }
         type uint32 {
           range "1280 .. 9192";
         }
       }
     }
     leaf auto-update-mtu {
       description "Auto update MTU from received ICMPv6 messages";
       type empty;
     }
     leaf copy-dscp {
       description "Copy DSCP (type of service) from IPv6 to IPv4 header";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       type union {
         type string {
           pattern "<.*>|$.*";
         }
         type uint32 {
           range "0 .. 16384";
         }
       }
     }
   }
   grouping sophos-scan-options {
     description "Anti-virus scan options";
     uses apply-advanced;
     choice uri-check-choice {
       leaf uri-check {
         description "Anti-virus uri-check";
         type empty;
       }
       leaf no-uri-check {
         description "Don't anti-virus uri-check";
         type empty;
       }
     }
     leaf content-size-limit {
       description "Content size limit";
       units "kilobytes";
       type string;
     }
     leaf timeout {
       description "Scan engine timeout";
       units "seconds";
       type union {
         type string {
           pattern "<.*>|$.*";
         }
         type uint32 {
           range "1 .. 1800";
         }
       }
     }
   }
   grouping ssg-destination-nat-object {
     uses apply-advanced;
     list pool {
       key name;
       ordered-by user;
       description "Define a destination address pool";
       leaf name {
         description "Pool name";
         type string {
           length "1 .. 63";
         }
       }
       uses apply-advanced;
       leaf description {
         description "Text description of pool";
         type string {
           length "1 .. 900";
         }
       }
       container routing-instance {
         description "Routing instance";
         uses apply-advanced;
         choice ri-name-choice {
           case case_1 {
             leaf default {
               description "Default routing-instance";
               type empty;
             }
           }
           case case_2 {
             leaf ri-name {
               description "Routing-instance name";
               type string {
               }
             }
           }
         }
       }
       container address {
         description "Add address or address range to pool";
         leaf ipaddr {
           description "IPv4 or IPv6 address or address range";
           type jt:ipprefix;
         }
         choice range-port-choice {
           case case_1 {
             container to {
               description "Upper limit of address range";
               uses apply-advanced;
               leaf ipaddr {
                 description "IPv4 or IPv6 upper limit of address range";
                 type jt:ipprefix;
               }
             }
           }
           case case_2 {
             leaf port {
               description "Specify the port value";
               type union {
                 type uint16;
                 type string {
                   pattern "<.*>|$.*";
                 }
               }
             }
           }
         }
       }
     }
     list port-forwarding {
       key name;
       ordered-by user;
       description "Define a port-forwarding mapping pool";
       leaf name {
         description "Port Forwarding mapping name";
         type string {
           length "1 .. 31";
         }
       }
       uses apply-advanced;
       leaf description {
         description "Text description of port forwarding mapping";
         type string {
           length "1 .. 900";
         }
       }
       list destined-port {
         key "port translated-port";
         ordered-by user;
         description "Port forwarding mappings";
         max-elements 32;
         leaf port {
           description "Destination port";
           type union {
             type string {
               pattern "<.*>|$.*";
             }
             type uint16 {
               range "1 .. 65535";
             }
           }
         }
         leaf translated-port {
           description "Translated port";
           type union {
             type string {
               pattern "<.*>|$.*";
             }
             type uint16 {
               range "1 .. 65535";
             }
           }
         }
       }
     }
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Destination NAT rule";
         uses dest-nat-rule-object;
       }
       leaf match-direction {
         description "Match direction";
         type enumeration {
           enum "input" {
             description "Match on input to interface";
           }
           enum "output" {
             description "Match on output from interface";
           }
         }
       }
     }
   }
   grouping dest-nat-rule-object {
     leaf name {
       description "Rule name";
       type string {
         length "1 .. 63";
       }
     }
     uses apply-advanced;
     leaf description {
       description "Text description of rule";
       type string {
         length "1 .. 900";
       }
     }
     container dest-nat-rule-match {
       description "Specify Destination NAT rule match criteria";
       uses apply-advanced;
       leaf-list source-address {
         ordered-by user;
         description "Source address";
         type string;
         max-elements 8;
       }
       leaf-list source-address-name {
         ordered-by user;
         description "Address/address-set from address book";
         type string;
         max-elements 8;
       }
       choice dst-choice {
         case case_1 {
           container destination-address {
             description "Destination address";
             choice dst-addr-choice {
               case case_1 {
                 leaf dst-addr {
                   description "IPv4 or IPv6 destination address";
                   type jt:ipprefix;
                 }
               }
               case case_2 {
                 leaf any-unicast {
                   description "Match any unicast address";
                   type empty;
                 }
               }
             }
           }
         }
         case case_2 {
           container destination-address-name {
             description "Address from address book";
             leaf dst-addr-name {
               description "Address from address book";
               type string {
                 length "1 .. 63";
               }
             }
           }
         }
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container destination-nat {
         description "Destination NAT action";
         uses apply-advanced;
         choice action {
           case case_1 {
             leaf off {
               description "No action";
               type empty;
             }
           }
           case case_2 {
             container pool {
               description "Use Destination NAT pool";
               uses apply-advanced;
               leaf pool-name {
                 description "Name of Destination NAT pool";
                 type string {
                   length "1 .. 63";
                 }
               }
             }
           }
           case case_3 {
             leaf destination-prefix {
               description "Destination prefix to be used for NAT64 and 464 translation type";
               type jt:ipprefix-only;
             }
           }
         }
         container xlat-source-rule {
           description "Set source nat rule to match for NAT464";
           uses apply-advanced;
           list rule-set {
             key name;
             ordered-by user;
             description "Source nat rule-set";
             max-elements 1;
             leaf name {
               description "Source nat rule-set name";
               type string {
                 length "1 .. 63";
               }
             }
             uses apply-advanced;
             leaf rule {
               description "Source NAT rule name";
               type string {
                 length "1 .. 63";
               }
             }
           }
         }
         container port-forwarding-mappings {
           description "Use Destination NAT port forwarding mapping pool";
           uses apply-advanced;
           leaf pf-name {
             description "Name of Port forwarding mappings";
             type string {
               length "1 .. 31";
             }
           }
         }
         container rule-session-count-alarm {
           description "Config rule-session-count-alarm to destination rule";
           uses nat-rule-session-count-alarm-object;
         }
       }
       leaf syslog {
         description "System log information about the packet";
         type empty;
       }
     }
   }
   grouping nat-rule-session-count-alarm-object {
     uses apply-advanced;
     leaf raise-threshold {
       description "Raise threshold for rule session count alarm";
       type union {
         type string {
           pattern "<.*>|$.*";
         }
         type uint32 {
           range "1 .. 4294967295";
         }
       }
     }
     leaf clear-threshold {
       description "Clear threshold for session count hit alarm";
       type union {
         type string {
           pattern "<.*>|$.*";
         }
         type uint32 {
           range "1 .. 4294967295";
         }
       }
     }
   }
   grouping ssg-proxy-arp-object {
     uses apply-advanced;
     list interface {
       key name;
       ordered-by user;
       description "Interface with proxy arp configured";
       uses ssg-interface-object;
     }
   }
   grouping ssg-interface-object {
     leaf name {
       description "Interface name";
       type union {
         type jt:interface-name;
         type string {
           pattern "<.*>|$.*";
         }
       }
     }
     uses apply-advanced;
     list address {
       key name;
       ordered-by user;
       description "Proxy ARP address";
       leaf name {
         description "Address or address range";
         type jt:ipv4prefix;
       }
       container to {
         description "Upper limit of address range";
         uses apply-advanced;
         leaf ipaddr {
           description "Upper limit of address range";
           type jt:ipv4prefix;
         }
       }
     }
   }
   grouping ssg-proxy-ndp-object {
     uses apply-advanced;
     list interface {
       key name;
       ordered-by user;
       description "Interface with proxy arp configured";
       uses ssg-proxy-ndp-interface-object;
     }
   }
   grouping ssg-proxy-ndp-interface-object {
     leaf name {
       description "Interface name";
       type union {
         type jt:interface-name;
         type string {
           pattern "<.*>|$.*";
         }
       }
     }
     uses apply-advanced;
     list address {
       key name;
       ordered-by user;
       description "Proxy ndp address";
       leaf name {
         description "Address or address range";
         type jt:ipv6prefix;
       }
       container to {
         description "Upper limit of address range";
         uses apply-advanced;
         leaf ipv6addr {
           description "Upper limit of address range";
           type jt:ipv6addr;
         }
       }
     }
   }
   grouping ssg-source-nat-object {
     uses apply-advanced;
     container persistent-nat {
       description "Persistent NAT info";
       container log {
         description "Configure persistent NAT log";
         choice enable-disable {
           case case_1 {
             leaf disable {
               description "Disable Persistent NAT log";
               type empty;
             }
           }
         }
       }
     }
     list pool {
       key name;
       ordered-by user;
       description "Define a source address pool";
       leaf name {
         description "Pool name";
         type string {
           length "1 .. 63";
         }
       }
       uses apply-advanced;
       leaf description {
         description "Text description of pool";
         type string {
           length "1 .. 900";
         }
       }
       container routing-instance {
         description "Routing instance";
         uses apply-advanced;
         leaf ri-name {
           description "Routing instance name";
           type string {
           }
         }
       }
       list address {
         key name;
         ordered-by user;
         description "Add address to pool";
         max-elements 64;
         leaf name {
           description "IPv4 or IPv6 address or address range";
           type jt:ipprefix;
         }
         container to {
           description "Upper limit of address range";
           uses apply-advanced;
           leaf ipaddr {
             description "IPv4 or IPv6 upper limit of address range";
             type jt:ipprefix;
           }
         }
       }
       container host-address-base {
         description "The base of host address";
         leaf ipaddr {
           description "IPv4 or IPv6 base address";
           type jt:ipprefix;
         }
       }
       container port {
         description "Config port attribute to pool";
         uses apply-advanced;
         choice port-choice {
           case case_1 {
             leaf no-translation {
               description "Do not perform port translation";
               type empty;
             }
           }
           case case_2 {
             container range {
               description "Port range";
               uses apply-advanced;
               choice port-assign-choice {
                 case case_1 {
                   leaf random-allocation {
                     description "Allocate port randomly";
                     type empty;
                   }
                 }
                 case case_2 {
                   leaf round-robin {
                     description "Allocate port round-robin";
                     type empty;
                   }
                 }
               }
               leaf low {
                 description "Lower limit of port range";
                 type union {
                   type string {
                     pattern "<.*>|$.*";
                   }
                   type uint16 {
                     range "1024 .. 65535";
                   }
                 }
               }
               container to {
                 description "Port range upper limit";
                 uses apply-advanced;
                 leaf high {
                   description "Upper limit of port range";
                   type union {
                     type string {
                       pattern "<.*>|$.*";
                     }
                     type uint16 {
                       range "1024 .. 65535";
                     }
                   }
                 }
               }
               container twin-port {
                 description "Twin port range";
                 uses apply-advanced;
                 leaf low {
                   description "Lower limit of twin port range";
                   type union {
                     type string {
                       pattern "<.*>|$.*";
                     }
                     type uint16 {
                       range "63488 .. 65535";
                     }
                   }
                 }
                 container to {
                   description "Twin port range upper limit";
                   uses apply-advanced;
                   leaf high {
                     description "Upper limit of twin port range";
                     type union {
                       type string {
                         pattern "<.*>|$.*";
                       }
                       type uint16 {
                         range "63488 .. 65535";
                       }
                     }
                   }
                 }
               }
             }
           }
           case case_3 {
             container automatic {
               description "Port assignment";
               uses apply-advanced;
               choice port-assign-choice {
                 case case_1 {
                   leaf random-allocation {
                     description "Allocate port randomly";
                     type empty;
                   }
                 }
                 case case_2 {
                   leaf round-robin {
                     description "Allocate port by round-robin";
                     type empty;
                   }
                 }
               }
             }
           }
         }
         leaf port-overloading-factor {
           description "Port overloading factor for each IP";
           type union {
             type string {
               pattern "<.*>|$.*";
             }
             type uint16 {
               range "2 .. 32";
             }
           }
         }
         container block-allocation {
           description "Port block allocation";
           presence "enable block-allocation";
           uses block-allocation-object;
         }
         container deterministic {
           description "Deterministic nat allocation";
           presence "enable deterministic";
           uses deterministic-object;
         }
         leaf preserve-parity {
           description "Allocate port as the same parity as incoming port";
           type empty;
         }
         leaf preserve-range {
           description "Allocate port from the same port range as incoming port";
           type empty;
         }
       }
       container overflow-pool {
         description "Specify an overflow pool";
         choice overflow-pool-choice {
           case case_1 {
             leaf pool-name {
               description "Name of source address pool";
               type string {
                 length "1 .. 63";
               }
             }
           }
           case case_2 {
             leaf interface {
               description "Allow interface pool to support overflow";
               type empty;
             }
           }
         }
       }
       leaf address-shared {
         description "Allow multiple hosts to share an externel address";
         type empty;
       }
       container address-pooling {
         description "Specify the address-pooling behavior";
         choice pooling-choice {
           case case_1 {
             leaf paired {
               description "Allow address-pooling paired for a source pool with port translation";
               type empty;
             }
           }
           case case_2 {
             leaf no-paired {
               description "Allow address-pooling no-paired for a source pool without port translation";
               type empty;
             }
           }
         }
       }
       container address-persistent {
         description "Specify the address-persistent behavior";
         container subscriber {
           description "Configure address persistent for subscriber";
           leaf ipv6-prefix-length {
             description "Ipv6 prefix length for address persistent";
             type union {
               type string {
                 pattern "<.*>|$.*";
               }
               type uint16 {
                 range "8 .. 128";
               }
             }
           }
         }
       }
       container pool-utilization-alarm {
         description "Config pool-utilization-alarm to pool";
         uses source-nat-pool-utilization-alarm-object;
       }
       leaf ei-mapping-timeout {
         description "Endpoint-independent mapping timeout";
         units "second";
         type union {
           type string {
             pattern "<.*>|$.*";
           }
           type uint32 {
             range "120 .. 86400";
           }
         }
       }
       leaf mapping-timeout {
         description "Address-pooling paired and endpoint-independent mapping timeout";
         units "second";
         type union {
           type string {
             pattern "<.*>|$.*";
           }
           type uint32 {
             range "120 .. 86400";
           }
         }
       }
       leaf limit-ports-per-host {
         description "Number of ports allocated per host";
         type union {
           type string {
             pattern "<.*>|$.*";
           }
           type uint16 {
             range "2 .. 65535";
           }
         }
       }
       container allocation-domain {
         description "Specify map-e domain name for pool";
         leaf mape-domain-name {
           description "Name of map-e domain";
           type string {
             length "1 .. 63";
           }
         }
         container allocation-rule {
           description "Specify map-e rule name for pool";
           leaf mape-rule-name {
             description "Name of map-e rule";
             type string {
               length "1 .. 63";
             }
           }
         }
       }
     }
     leaf address-persistent {
       description "Allow source address to maintain same translation";
       type empty;
     }
     leaf session-persistence-scan {
       description "Allow source to maintain session when session scan";
       type empty;
     }
     leaf session-drop-hold-down {
       description "Session drop hold down time";
       type union {
         type string {
           pattern "<.*>|$.*";
         }
         type uint16 {
           range "30 .. 28800";
         }
       }
     }
     container pool-utilization-alarm {
       description "Configure pool utilization alarm";
       uses source-nat-pool-utilization-alarm-object;
     }
     container port-randomization {
       description "Configure Source NAT port randomization";
       choice enable-disable {
         case case_1 {
           leaf disable {
             description "Disable Source NAT port randomization";
             type empty;
           }
         }
       }
     }
     container port-round-robin {
       description "Configure Source NAT port randomization";
       choice enable-disable {
         case case_1 {
           leaf disable {
             description "Disable Source NAT port randomization";
             type empty;
           }
         }
       }
     }
     leaf port-scaling-enlargement {
       description "Configure source port scaling to 2.4G only for NGSPC";
       type empty;
     }
     leaf pool-distribution {
       description "Configure Source pool distribution, the APPCP bottleneck of NAT CPS can be alleviated.";
       type empty;
     }
     container pool-default-port-range {
       description "Configure Source NAT default port range";
       leaf low {
         description "Lower limit of port range";
         type union {
           type string {
             pattern "<.*>|$.*";
           }
           type uint16;
         }
       }
       container to {
         description "Port range upper limit";
         uses apply-advanced;
         leaf high {
           description "Upper limit of port range";
           type union {
             type string {
               pattern "<.*>|$.*";
             }
             type uint16;
           }
         }
       }
     }
     container pool-default-twin-port-range {
       description "Configure Source NAT default twin port range";
       leaf low {
         description "Lower limit of twin port range";
         type union {
           type string {
             pattern "<.*>|$.*";
           }
           type uint16 {
             range "63488 .. 65535";
           }
         }
       }
       container to {
         description "Twin port range upper limit";
         uses apply-advanced;
         leaf high {
           description "Upper limit of twin port range";
           type union {
             type string {
               pattern "<.*>|$.*";
             }
             type uint16 {
               range "63488 .. 65535";
             }
           }
         }
       }
     }
     container interface {
       description "Configure interface port overloading for persistent NAT";
       uses apply-advanced;
       choice interface-choice {
         case case_1 {
           container port-overloading {
             description "Configure port overloading";
             leaf off {
               description "Turn off interface port over-loading";
               type empty;
             }
           }
         }
         case case_2 {
           leaf port-overloading-factor {
             description "Port overloading factor for interface NAT";
             type union {
               type uint16;
               type string {
                 pattern "<.*>|$.*";
               }
             }
           }
         }
       }
     }
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       container to {
         description "Where is the traffic to";
         choice from-context-choice {
           case case_1 {
             leaf-list routing-instance {
               description "Destination routing instance list";
               type string;
               max-elements 8;
             }
           }
           case case_2 {
             leaf-list routing-group {
               description "Destination routing group list";
               type string;
               max-elements 8;
             }
           }
           case case_3 {
             leaf-list zone {
               description "Destination zone list";
               type string;
               max-elements 8;
             }
           }
           case case_4 {
             leaf-list interface {
               description "Destination interface list";
               type union {
                 type jt:interface-name;
                 type string {
                   pattern "<.*>|$.*";
                 }
               }
               max-elements 8;
             }
           }
         }
       }
       list rule {
         key name;
         ordered-by user;
         description "Source NAT rule";
         uses src-nat-rule-object;
       }
       leaf match-direction {
         description "Match direction";
         type enumeration {
           enum "input" {
             description "Match on input to interface";
           }
           enum "output" {
             description "Match on output from interface";
           }
         }
       }
     }
   }
   grouping block-allocation-object {
     description "Port block allocation";
     uses apply-advanced;
     leaf block-size {
       description "Block size";
       type union {
         type string {
           pattern "<.*>|$.*";
         }
         type uint16 {
           range "1 .. 64512";
         }
       }
     }
     leaf maximum-blocks-per-host {
       description "Maximum block number per host";
       type union {
         type string {
           pattern "<.*>|$.*";
         }
         type uint16 {
           range "1 .. 512";
         }
       }
     }
     leaf active-block-timeout {
       description "Active block timeout interval";
       type union {
         type string {
           pattern "<.*>|$.*";
         }
         type uint32;
       }
     }
     leaf interim-logging-interval {
       description "Interim Logging interval";
       type union {
         type string {
           pattern "<.*>|$.*";
         }
         type uint32 {
           range "1800 .. 86400";
         }
       }
     }
     leaf last-block-recycle-timeout {
       description "Last Block recycle timeout interval";
       type union {
         type string {
           pattern "<.*>|$.*";
         }
         type uint32 {
           range "120 .. 864000";
         }
       }
     }
     container log {
       description "Configure port block log";
       choice enable-disable {
         case case_1 {
           leaf disable {
             description "Disable PBA port block log";
             type empty;
           }
         }
       }
     }
   }
   grouping deterministic-object {
     description "Deterministic nat allocation";
     uses apply-advanced;
     leaf block-size {
       description "Block size";
       type union {
         type string {
           pattern "<.*>|$.*";
         }
         type uint16;
       }
     }
     leaf det-nat-configuration-log-interval {
       description "Deterministic nat configuration logging interval";
       type union {
         type string {
           pattern "<.*>|$.*";
         }
         type uint32 {
           range "1800 .. 86400";
         }
       }
     }
     container host {
       description "Host address";
       leaf-list address {
         ordered-by user;
         description "Host ip address";
         type jt:ipprefix;
         max-elements 8;
       }
       leaf-list address-name {
         ordered-by user;
         description "Host address/address-set from address book";
         type string;
         max-elements 8;
       }
     }
     leaf include-boundary-addresses {
       description "Include network and broadcast in 'match' source address";
       type empty;
     }
   }
   grouping source-nat-pool-utilization-alarm-object {
     uses apply-advanced;
     leaf raise-threshold {
       description "Raise threshold for pool utilization alarm";
       type union {
         type string {
           pattern "<.*>|$.*";
         }
         type uint16 {
           range "50 .. 100";
         }
       }
     }
     leaf clear-threshold {
       description "Clear threshold for pool utilization alarm";
       type union {
         type string {
           pattern "<.*>|$.*";
         }
         type uint16 {
           range "40 .. 100";
         }
       }
     }
   }
   grouping src-nat-rule-object {
     leaf name {
       description "Source NAT Rule name";
       type string {
         length "1 .. 63";
       }
     }
     uses apply-advanced;
     leaf description {
       description "Text description of rule";
       type string {
         length "1 .. 900";
       }
     }
     container src-nat-rule-match {
       description "Specify Source NAT rule match criteria";
       uses apply-advanced;
       leaf-list source-address {
         ordered-by user;
         description "Source address";
         type string;
         max-elements 8;
       }
       leaf-list source-address-name {
         ordered-by user;
         description "Address/address-set from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list destination-address {
         ordered-by user;
         description "Destination address";
         type string;
         max-elements 8;
       }
       leaf-list destination-address-name {
         ordered-by user;
         description "Address/address-set from address book";
         type string;
         max-elements 8;
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container source-nat {
         description "Source NAT action";
         uses apply-advanced;
         choice action {
           case case_1 {
             leaf off {
               description "No action";
               type empty;
             }
           }
           case case_2 {
             container pool {
               description "Use Source NAT pool";
               uses apply-advanced;
               leaf pool-name {
                 description "Name of Source NAT pool";
                 type string {
                   length "1 .. 63";
                 }
               }
               container persistent-nat {
                 description "Persistent NAT info";
                 presence "enable persistent-nat";
                 uses persistent-nat-object;
               }
             }
           }
           case case_3 {
             container interface {
               presence "enable interface";
               description "Use egress interface address";
               uses apply-advanced;
               container persistent-nat {
                 description "Persistent NAT info";
                 presence "enable persistent-nat";
                 uses persistent-nat-object;
               }
             }
           }
         }
         leaf clat-prefix {
           description "An IPv6 prefix to be used for XLAT464 and prefix length can only be 32/40/48/56/64/96";
           type jt:ipprefix-only;
         }
         leaf clat-ipv6-prefix-length {
           description "The ipv6 prefix length for CLAT source address";
           type enumeration {
             enum "32" {
               description "The ipv6 prefix length of 32";
             }
             enum "40" {
               description "The ipv6 prefix length of 40";
             }
             enum "48" {
               description "The ipv6 prefix length of 48";
             }
             enum "56" {
               description "The ipv6 prefix length of 56";
             }
             enum "64" {
               description "The ipv6 prefix length of 64";
             }
             enum "96" {
               description "The ipv6 prefix length of 96";
             }
           }
         }
         container rule-session-count-alarm {
           description "Config rule-session-count-alarm to source rule";
           uses nat-rule-session-count-alarm-object;
         }
         container mapping-type {
           description "Source nat mapping type";
           leaf endpoint-independent {
             description "Endpoint independent mapping";
             type empty;
           }
           leaf address-pooling-paired {
             description "Address pooling paired mapping";
             type empty;
           }
         }
         container secure-nat-mapping {
           description "Mapping options for enhanced security";
           leaf eif-flow-limit {
             description "Number of inbound flows to be allowed for a EIF mapping";
             type union {
               type string {
                 pattern "<.*>|$.*";
               }
               type uint16 {
                 range "0 .. 65534";
               }
             }
           }
           container mapping-refresh {
             description "Enable timer refresh option";
             choice refresh-choice {
               case case_1 {
                 leaf inbound {
                   description "Enable timer refresh for inbound connections only";
                   type empty;
                 }
               }
               case case_2 {
                 leaf outbound {
                   description "Enable timer refresh for outbound connections only";
                   type empty;
                 }
               }
               case case_3 {
                 leaf inbound-outbound {
                   description "Enable timer refresh for inbound & outbound connections";
                   type empty;
                 }
               }
             }
           }
         }
         container filtering-type {
           description "Source NAT filtering type";
           uses apply-advanced;
           container endpoint-independent {
             presence "enable endpoint-independent";
             description "Endpoint independent filtering";
             uses apply-advanced;
             list prefix-list {
               key name;
               ordered-by user;
               description "One or more named lists of source prefixes to match";
               leaf name {
                 description "Name of prefix list to match against";
                 type string {
                   length "1 .. 63";
                 }
               }
               leaf except {
                 description "Name of prefix list not to match against";
                 type empty;
               }
             }
           }
         }
       }
       leaf syslog {
         description "System log information about the packet";
         type empty;
       }
     }
   }
   grouping persistent-nat-object {
     uses apply-advanced;
     container permit {
       description "Persistent NAT permit configure";
       choice persistent-nat-type-choice {
         case case_1 {
           leaf any-remote-host {
             description "Permit any remote host";
             type empty;
           }
         }
         case case_2 {
           leaf target-host {
             description "Permit target host";
             type empty;
           }
         }
         case case_3 {
           leaf target-host-port {
             description "Permit target host port";
             type empty;
           }
         }
       }
     }
     leaf block-ext-session {
       description "Block sessions from external hosts";
       type empty;
     }
     leaf address-mapping {
       description "Address-to-address mapping";
       type empty;
     }
     leaf inactivity-timeout {
       description "Inactivity timeout value";
       type union {
         type string {
           pattern "<.*>|$.*";
         }
         type uint16 {
           range "60 .. 7200";
         }
       }
     }
     leaf max-session-number {
       description "The maximum session number value";
       type union {
         type string {
           pattern "<.*>|$.*";
         }
         type uint32 {
           range "8 .. 65536";
         }
       }
     }
   }
   grouping ssg-static-nat-object {
     uses apply-advanced;
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Static NAT rule";
         uses static-nat-rule-object;
       }
       leaf match-direction {
         description "Match direction";
         type enumeration {
           enum "input" {
             description "Match on input to interface";
           }
           enum "output" {
             description "Match on output from interface";
           }
         }
       }
     }
   }
   grouping static-nat-rule-object {
     leaf name {
       description "Static Rule name";
       type string {
         length "1 .. 63";
       }
     }
     uses apply-advanced;
     leaf description {
       description "Text description of rule";
       type string {
         length "1 .. 900";
       }
     }
     container static-nat-rule-match {
       description "Specify Static NAT rule match criteria";
       uses apply-advanced;
       leaf-list source-address {
         ordered-by user;
         description "Source address";
         type jt:ipprefix;
         max-elements 8;
       }
       leaf-list source-address-name {
         ordered-by user;
         description "Address from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       choice dst-choice {
         case case_1 {
           container destination-address {
             description "Destination address";
             leaf dst-addr {
               description "IPv4 or IPv6 Destination address prefix";
               type jt:ipprefix;
             }
           }
         }
         case case_2 {
           container destination-address-name {
             description "Address from address book";
             leaf dst-addr-name {
               description "Address from address book";
               type string {
                 length "1 .. 63";
               }
             }
           }
         }
       }
       container destination-port {
         description "Destination port";
         leaf low {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
     }
     container then {
       description "Then action";
       uses apply-advanced;
       container static-nat {
         description "Static NAT action";
         uses apply-advanced;
         choice prefix-choice {
           case case_1 {
             container inet {
               presence "enable inet";
               description "Translated to IPv4 address";
               uses apply-advanced;
               leaf routing-instance {
                 description "Routing instance";
                 type string;
               }
             }
           }
           case case_2 {
             container prefix {
               description "Address prefix";
               uses apply-advanced;
               leaf addr-prefix {
                 description "IPv4 or IPv6 address prefix value";
                 type jt:ipprefix;
               }
               container mapped-port {
                 description "Mapped port";
                 uses static-nat-rule-mapped-port-object;
               }
               leaf routing-instance {
                 description "Routing instance";
                 type string;
               }
             }
           }
           case case_3 {
             container prefix-name {
               description "Address from address book";
               uses apply-advanced;
               leaf addr-prefix-name {
                 description "Address from address book";
                 type string {
                   length "1 .. 63";
                 }
               }
               container mapped-port {
                 description "Mapped port";
                 uses static-nat-rule-mapped-port-object;
               }
               leaf routing-instance {
                 description "Routing instance";
                 type string;
               }
             }
           }
           case case_4 {
             container nptv6-prefix {
               description "NPTv6 address prefix, the longest prefix will be supported is /64";
               uses apply-advanced;
               leaf addr-prefix {
                 description "IPv6 address prefix value, the longest prefix will be supported is /64";
                 type jt:ipprefix;
               }
               leaf routing-instance {
                 description "Routing instance";
                 type string;
               }
             }
           }
           case case_5 {
             container nptv6-prefix-name {
               description "NPTv6 address from address book";
               uses apply-advanced;
               leaf addr-prefix-name {
                 description "IPv6 address from address book";
                 type string {
                   length "1 .. 63";
                 }
               }
               leaf routing-instance {
                 description "Routing instance";
                 type string;
               }
             }
           }
         }
         container rule-session-count-alarm {
           description "Config rule-session-count-alarm to static rule";
           uses nat-rule-session-count-alarm-object;
         }
       }
     }
   }
   grouping static-nat-rule-mapped-port-object {
     uses apply-advanced;
     leaf low {
       description "Port or lower limit of port range";
       type union {
         type uint16;
         type string {
           pattern "<.*>|$.*";
         }
       }
     }
     container to {
       description "Port range upper limit";
       uses apply-advanced;
       leaf high {
         description "Upper limit of port range";
         type union {
           type uint16;
           type string {
             pattern "<.*>|$.*";
           }
         }
       }
     }
   }
   grouping sw-rule-set-object {
     leaf name {
       description "Define Rule Set name";
       type string {
         length "1 .. 63";
       }
     }
     uses apply-advanced;
     list rule {
       key name;
       ordered-by user;
       description "Define a rule term";
       leaf name {
         description "Rule name";
         type string {
           length "1 .. 63";
         }
       }
       uses apply-advanced;
       container then {
         description "Action to take if the condition is matched";
         uses apply-advanced;
         choice designation {
           case case_1 {
             leaf ds-lite {
               description "Apply DS-Lite softwire";
               type string {
                 length "1 .. 63";
               }
             }
           }
           case case_2 {
             leaf v6rd {
               description "Apply 6rd softwire";
               type string {
                 length "1 .. 63";
               }
             }
           }
           case case_3 {
             leaf map-e {
               description "Apply MAP-E softwire";
               type string {
                 length "1 .. 63";
               }
             }
           }
         }
       }
     }
     leaf match-direction {
       description "Match direction";
       type enumeration {
         enum "input" {
           description "Match on input to interface";
         }
         enum "output" {
           description "Match on output from interface";
         }
       }
     }
   }
   grouping tenant-system-type {
     description "Tenant name";
     leaf name {
       description "Tenant name";
       type string;
     }
     uses apply-advanced;
     leaf max-sessions {
       description "Max number of IDP sessions";
       type union {
         type uint32;
         type string {
           pattern "<.*>|$.*";
         }
       }
     }
   }
   grouping time-format-object {
     uses apply-advanced;
     leaf year {
       description "Year in time format for syslog";
       type empty;
     }
     leaf millisecond {
       description "Millisecond in time format for syslog";
       type empty;
     }
   }
   grouping traffic-selector-term-object {
     description "Traffic Selector term details";
     leaf name {
       description "Rule name";
       type string {
         length "1 .. 63";
       }
     }
     uses apply-advanced;
     leaf local-ip {
       description "IP address of local traffic-selector";
       type jt:ipprefix-mandatory;
     }
     leaf remote-ip {
       description "IP address of remote traffic-selector";
       type jt:ipprefix-mandatory;
     }
     leaf protocol {
       description "Define protocol";
       type string;
     }
     leaf source-port {
       description "Hyphenated source port range";
       type string;
     }
     leaf destination-port {
       description "Hyphenated destination port range";
       type string;
     }
   }
   grouping tunable-object {
     leaf name {
       type string;
     }
     uses apply-advanced;
     leaf tunable-value {
       description "Protocol tunable value";
       type union {
         type uint32;
         type string {
           pattern "<.*>|$.*";
         }
       }
     }
   }
   grouping tunnel-inspection-profile-type {
     description "Configure tunnel-inspection profile";
     leaf name {
       description "Tunnel-inspection profile name";
       type string {
         length "1 .. 63";
       }
     }
     uses apply-advanced;
     choice inspection-type {
       case case_1 {
         list vxlan {
           key name;
           ordered-by user;
           description "Define a vxlan tunnel";
           uses vxlan-tunnel-type;
         }
       }
     }
   }
   grouping tunnel-inspection-vni-type {
     description "VNI config";
     leaf name {
       description "VNI name";
       type string {
         length "1 .. 64";
       }
     }
     uses apply-advanced;
     choice vni-type {
       case case_1 {
         list vni-range {
           key name;
           ordered-by user;
           description "VNI range";
           uses vni-range-type;
         }
       }
       case case_2 {
         leaf-list vni-id {
           ordered-by user;
           description "VNI ID";
           type union {
             type uint32;
             type string {
               pattern "<.*>|$.*";
             }
           }
         }
       }
     }
   }
   grouping tunnel_type {
     description "Tunnel packets";
     uses apply-advanced;
     choice ipsec-vpn-choice {
       case case_1 {
         leaf ipsec-vpn {
           description "Enable VPN with name";
           type string {
             length "1 .. 63";
           }
         }
       }
       case case_2 {
         leaf ipsec-group-vpn {
           description "Enable dynamic IPSEC group with name";
           status deprecated;
           type string {
             length "1 .. 63";
           }
         }
       }
     }
     leaf pair-policy {
       description "Policy in the reverse direction, to form a pair";
       type string {
         length "1 .. 63";
       }
     }
   }
   grouping url-list-type {
     description "Configure url-list object";
     leaf name {
       description "Configure name of url-list object";
       type string {
         length "1 .. 29";
       }
     }
     uses apply-advanced;
     leaf-list value {
       ordered-by user;
       description "Configure value of url-list object";
       type string {
         length "1 .. 249";
       }
     }
   }
   grouping usf-range-address-type {
     description "Range address";
     leaf name {
       description "Lower limit of address range";
       type jt:ipprefix;
     }
     uses apply-advanced;
     container to {
       description "Port range upper limit";
       uses apply-advanced;
       leaf range-high {
         description "Upper limit of address range";
         type jt:ipprefix;
       }
     }
   }
   grouping utm-apppxy-traceoptions {
     description "Traceoptions for utm application proxy process";
     uses apply-advanced;
     list flag {
       key name;
       ordered-by user;
       description "Tracing parameters for utm application proxy";
       leaf name {
         description "Tracing parameters for utm application proxy flag name";
         type enumeration {
           enum "abort" {
             description "Trace application-proxy session abort";
           }
           enum "application-objects" {
             description "Trace application-proxy objects information";
           }
           enum "utm-realtime" {
             description "Trace application-proxy realtime-thread information";
           }
           enum "anti-virus" {
             description "Trace anti-virus information";
           }
           enum "basic" {
             description "Trace application-proxy basic information";
           }
           enum "buffer" {
             description "Trace application-proxy data buffer information";
           }
           enum "detail" {
             description "Trace application-proxy detailed information";
           }
           enum "ftp-data" {
             description "Trace FTP data connection information";
           }
           enum "ftp-control" {
             description "Trace FTP control connection information";
           }
           enum "http" {
             description "Trace HTTP protocol information";
           }
           enum "imap" {
             description "Trace IMAP protocol information";
           }
           enum "memory" {
             description "Trace memory usage";
           }
           enum "parser" {
             description "Trace protocol parser";
           }
           enum "pfe" {
             description "Trace communication with PFE";
           }
           enum "pop3" {
             description "Trace POP3 protocol information";
           }
           enum "queue" {
             description "Trace queue information";
           }
           enum "smtp" {
             description "Trace SMTP protocol information";
           }
           enum "tcp" {
             description "Trace TCP level information";
           }
           enum "timer" {
             description "Trace timer processing";
           }
           enum "connection-rating" {
             description "Trace connection rating information";
           }
           enum "mime" {
             description "Trace MIME parser information";
           }
           enum "regex-engine" {
             description "Trace Pattern Match Engine (PME) information";
           }
           enum "sophos-anti-virus" {
             description "Trace anti-virus sophos engine information";
           }
           enum "all" {
             description "Enable all application-proxy trace options";
           }
         }
       }
     }
   }
   grouping utm-ipc-traceoptions {
     description "Traceoptions for utm IPC";
     uses apply-advanced;
     list flag {
       key name;
       ordered-by user;
       description "Traceoptions for utm IPC flag";
       leaf name {
         description "Trace options for utm IPC flag name";
         type enumeration {
           enum "basic" {
             description "Trace basic IPC related information";
           }
           enum "detail" {
             description "Trace detail IPC related information";
           }
           enum "connection-manager" {
             description "Trace IPC connection manager";
           }
           enum "connection-status" {
             description "Trace IPC connection status";
           }
           enum "pfe" {
             description "Trace communication with pfe";
           }
           enum "utm-realtime" {
             description "Trace IPC realtime-thread information";
           }
           enum "all" {
             description "Enable all IPC trace options";
           }
         }
       }
     }
   }
   grouping utm-traceoptions {
     description "Trace options for utm process";
     uses apply-advanced;
     list flag {
       key name;
       ordered-by user;
       description "Tracing UTM information";
       leaf name {
         description "Flag name";
         type enumeration {
           enum "cli" {
             description "Trace CLI";
           }
           enum "daemon" {
             description "Trace daemon information";
           }
           enum "ipc" {
             description "Trace IPC information";
           }
           enum "pfe" {
             description "Trace pfe information";
           }
           enum "all" {
             description "Enable all utm trace options";
           }
         }
       }
     }
   }
   grouping vendor-object {
     leaf name {
       description "Values for vendor field";
       type string;
     }
     uses apply-advanced;
     leaf product-name {
       description "Values for product field";
       type string;
     }
   }
   grouping vni-range-type {
     leaf name {
       description "VNI range Lower limit";
       type union {
         type string {
           pattern "<.*>|$.*";
         }
         type uint32 {
           range "0 .. 16777215";
         }
       }
     }
     uses apply-advanced;
     container to {
       description "VNI range upper limit";
       uses apply-advanced;
       leaf range-high {
         description "Upper limit of vni range";
         type union {
           type string {
             pattern "<.*>|$.*";
           }
           type uint32 {
             range "0 .. 16777215";
           }
         }
       }
     }
   }
   grouping vrf-group-type {
     description "Configure vrf group object";
     leaf name {
       description "Vrf group name";
       type string {
         length "1 .. 64";
       }
     }
     uses apply-advanced;
     leaf-list vrf {
       ordered-by user;
       description "L3vpn vrf name";
       type string;
     }
   }
   grouping vxlan-tunnel-type {
     description "Configure vxlan tunnel";
     leaf name {
       description "Vxlan tunnel name";
       type string {
         length "1 .. 63";
       }
     }
     uses apply-advanced;
     leaf policy-set {
       description "Define a security policy set";
       type string {
         length "1 .. 63";
       }
     }
     list vni {
       key name;
       ordered-by user;
       description "Define VNI";
       max-elements 4096;
       uses vni-list-type;
     }
   }
   grouping vni-list-type {
     leaf name {
       description "VNI name";
       type string;
     }
   }
   grouping web-filtering-fallback-setting {
     description "Web-filtering fallback settings";
     uses apply-advanced;
     leaf default {
       description "Fallback default settings";
       type enumeration {
         enum "log-and-permit" {
         }
         enum "block" {
         }
       }
     }
     leaf server-connectivity {
       description "Fallback action when device cannot connect to server";
       type enumeration {
         enum "log-and-permit" {
         }
         enum "block" {
         }
       }
     }
     leaf timeout {
       description "Fallback action when connection to server timeout";
       type enumeration {
         enum "log-and-permit" {
         }
         enum "block" {
         }
       }
     }
     leaf too-many-requests {
       description "Fallback action when requests exceed the limit of engine";
       type enumeration {
         enum "log-and-permit" {
         }
         enum "block" {
         }
       }
     }
   }
   grouping web-filtering-traceoptions {
     description "Trace options for web-filtering feature";
     uses apply-advanced;
     list flag {
       key name;
       ordered-by user;
       description "Trace options for web-filtering feature trace flag";
       leaf name {
         description "Trace options for web-filtering feature trace flag name";
         type enumeration {
           enum "basic" {
             description "Trace web-filtering module generic basic information";
           }
           enum "session-manager" {
             description "Trace session management information";
           }
           enum "heartbeat" {
             description "Trace connectivity information with web-filter server";
           }
           enum "packet" {
             description "Trace packet information from session management";
           }
           enum "profile" {
             description "Trace profile config information";
           }
           enum "requests" {
             description "Trace requests sent to web-filter server";
           }
           enum "response" {
             description "Trace response received from web-filter server";
           }
           enum "socket" {
             description "Trace communication socket with web-filter server";
           }
           enum "timer" {
             description "Trace aging information for requests sent to server";
           }
           enum "ipc" {
             description "Trace communication events with PFE";
           }
           enum "cache" {
             description "Trace category cache operations";
           }
           enum "enhanced" {
             description "Trace Juniper enhanced web-filtering operations";
           }
           enum "all" {
             description "Enable trace all anti-virus trace options";
           }
         }
       }
     }
   }
   grouping webfilter-feature {
     description "Web-filtering feature settings";
     uses apply-advanced;
     container surf-control-integrated {
       description "Configure web-filtering surf-control integrated engine";
       status deprecated;
       uses surf-control-integrated-type;
     }
     container websense-redirect {
       description "Configure web-filtering websense redirect engine";
       uses websense-type;
     }
     container juniper-local {
       description "Configure web-filtering juniper local engine";
       uses juniper-local-type;
     }
     container juniper-enhanced {
       description "Configure web-filtering juniper enhanced engine";
       uses juniper-enhanced-type;
     }
   }
   grouping juniper-enhanced-type {
     description "Juniper Enhanced";
     uses apply-advanced;
     list profile {
       key name;
       ordered-by user;
       description "Juniper enhanced profile";
       leaf name {
         description "Juniper enhanced profile name";
         type string {
           length "1 .. 29";
         }
       }
       uses apply-advanced;
       leaf base-filter {
         description "Juniper base filter";
         type string;
       }
       list category {
         key name;
         ordered-by user;
         description "Juniper enhanced category";
         uses juniper-enhanced-category-type;
       }
       container site-reputation-action {
         description "Juniper enhanced site reputation action";
         presence "enable site-reputation-action";
         uses juniper-enhanced-site-reputation-setting;
       }
       leaf default {
         description "Juniper enhanced profile default";
         type enumeration {
           enum "permit" {
             description "Permit action";
           }
           enum "block" {
             description "Block action";
           }
           enum "log-and-permit" {
             description "Log and permit action";
           }
           enum "quarantine" {
             description "Quarantine action";
           }
         }
       }
       leaf custom-message {
         description "Custom message";
         type string;
       }
       container fallback-settings {
         description "Juniper enhanced fallback settings";
         presence "enable fallback-settings";
         uses web-filtering-fallback-setting;
       }
       leaf timeout {
         description "Juniper enhanced timeout";
         units "seconds";
         type union {
           type string {
             pattern "<.*>|$.*";
           }
           type uint32;
         }
       }
       leaf no-safe-search {
         description "Do not perform safe-search for Juniper enhanced protocol";
         type empty;
       }
     }
   }
   grouping juniper-local-type {
     description "Juniper local";
     uses apply-advanced;
     list profile {
       key name;
       ordered-by user;
       description "Juniper local profile";
       leaf name {
         description "Juniper local profile name";
         type string {
           length "1 .. 29";
         }
       }
       uses apply-advanced;
       leaf default {
         description "Juniper local profile default";
         type enumeration {
           enum "permit" {
             description "Permit action";
           }
           enum "block" {
             description "Block action";
           }
           enum "log-and-permit" {
             description "Log and permit action";
           }
         }
       }
       list category {
         key name;
         ordered-by user;
         description "Custom category";
         uses custom-category-type;
       }
       leaf custom-message {
         description "Custom message";
         type string;
       }
       leaf no-safe-search {
         description "Do not perform safe-search for Juniper local protocol";
         type empty;
       }
       container fallback-settings {
         description "Juniper local fallback settings";
         presence "enable fallback-settings";
         uses web-filtering-fallback-setting;
       }
       leaf timeout {
         description "Juniper local timeout";
         units "seconds";
         type union {
           type string {
             pattern "<.*>|$.*";
           }
           type uint32 {
             range "1 .. 1800";
           }
         }
       }
     }
   }
   grouping surf-control-integrated-type {
     description "Surf control integrated";
     uses apply-advanced;
     container cache {
       presence "enable cache";
       uses apply-advanced;
       leaf timeout {
         description "Surf control integrated cache timeout";
         default "1440";
         units "minutes";
         type union {
           type string {
             pattern "<.*>|$.*";
           }
           type uint32 {
             range "1 .. 1800";
           }
         }
       }
       leaf size {
         description "Surf control integrated cache size";
         default "1024";
         units "kilobytes";
         type string;
       }
     }
     container server {
       description "Surf control server";
       presence "enable server";
       uses server;
     }
     list profile {
       key name;
       ordered-by user;
       description "Surf control integrated profile";
       leaf name {
         description "Surf control integrated profile name";
         type string {
           length "1 .. 29";
         }
       }
       uses apply-advanced;
       list category {
         key name;
         ordered-by user;
         description "Surf control integrated category";
         uses surf-control-integrated-category-type;
       }
       leaf default {
         description "Surf control integrated profile default";
         type enumeration {
           enum "permit" {
             description "Permit action";
           }
           enum "block" {
             description "Block action";
           }
           enum "log-and-permit" {
             description "Log and permit action";
           }
         }
       }
       leaf custom-block-message {
         description "Surf control integrated custom block message";
         type string {
           length "1 .. 512";
         }
       }
       container fallback-settings {
         description "Surf control integrated fallback settings";
         presence "enable fallback-settings";
         uses web-filtering-fallback-setting;
       }
       leaf timeout {
         description "Surf control integrated timeout";
         default "15";
         units "seconds";
         type union {
           type string {
             pattern "<.*>|$.*";
           }
           type uint32 {
             range "1 .. 1800";
           }
         }
       }
     }
   }
   grouping surf-control-integrated-category-type {
     description "Surf control integrated category type";
     leaf name {
       description "Surf control integrated category type name";
       type string {
         length "1 .. 59";
       }
     }
     uses apply-advanced;
     leaf action {
       description "Surf control integrated category type action";
       type enumeration {
         enum "permit" {
           description "Permit action";
         }
         enum "block" {
           description "Block action";
         }
         enum "log-and-permit" {
           description "Log and permit action";
         }
       }
     }
   }
   grouping websense-type {
     description "Websense redirect";
     uses apply-advanced;
     list profile {
       key name;
       ordered-by user;
       description "Websense redirect profile";
       leaf name {
         description "Websense redirect profile name";
         type string {
           length "1 .. 29";
         }
       }
       uses apply-advanced;
       container server {
         description "Websense redirect server";
         presence "enable server";
         uses server;
       }
       list category {
         key name;
         ordered-by user;
         description "Custom category";
         uses custom-category-type;
       }
       leaf custom-message {
         description "Custom message";
         type string;
       }
       leaf no-safe-search {
         description "Do not perform safe-search for websense redirect protocol";
         type empty;
       }
       container fallback-settings {
         description "Websense redirect fallback settings";
         presence "enable fallback-settings";
         uses web-filtering-fallback-setting;
       }
       leaf timeout {
         description "Websense redirect timeout";
         units "seconds";
         type union {
           type string {
             pattern "<.*>|$.*";
           }
           type uint32 {
             range "1 .. 1800";
           }
         }
       }
       leaf sockets {
         description "Websense redirect sockets number";
         type union {
           type string {
             pattern "<.*>|$.*";
           }
           type uint32 {
             range "1 .. 32";
           }
         }
       }
       leaf account {
         description "Websense redirect account";
         type string {
           length "1 .. 28";
         }
       }
     }
   }
   grouping wildcard-address-type {
     description "Wildcard address and mask";
     leaf name {
       description "Numeric IPv4 wildcard address with in the form of a.d.d.r/netmask";
       type string {
         length "1 .. 63";
       }
     }
     uses apply-advanced;
   }
   grouping zone-interface-list-type {
     description "Logical interfaces in this zone";
     leaf name {
       description "Logical interface";
       type union {
         type jt:interface-name;
         type string {
           pattern "<.*>|$.*";
         }
       }
     }
     uses apply-advanced;
     container host-inbound-traffic {
       uses interface_host_inbound_traffic_t;
     }
   }
   grouping interface_host_inbound_traffic_t {
     uses apply-advanced;
     list system-services {
       key name;
       ordered-by user;
       description "Type of incoming system-service traffic to accept";
       uses interface-system-services-object-type;
     }
     list protocols {
       key name;
       ordered-by user;
       description "Protocol type of incoming traffic to accept";
       uses host-inbound-protocols-object-type;
     }
   }
   grouping host-inbound-protocols-object-type {
     description "Protocol type of incoming traffic to accept";
     leaf name {
       description "Protocol name";
       type enumeration {
         enum "all" {
           description "All protocols";
         }
         enum "bfd" {
           description "Bidirectional Forwarding Detection";
         }
         enum "bgp" {
           description "Border Gateway Protocol";
         }
         enum "dvmrp" {
           description "Distance Vector Multicast Routing Protocol";
         }
         enum "igmp" {
           description "Internet Group Management Protocol";
         }
         enum "ldp" {
           description "Label Distribution Protocol";
         }
         enum "msdp" {
           description "Multicast Source Discovery Protocol";
         }
         enum "ndp" {
           description "IPv6 Neighbor Discovery Protocol";
         }
         enum "nhrp" {
           description "Next Hop Resolution Protocol";
         }
         enum "ospf" {
           description "Open Shortest Path First";
         }
         enum "ospf3" {
           description "Open Shortest Path First version 3";
         }
         enum "pgm" {
           description "Pragmatic General Multicast";
         }
         enum "pim" {
           description "Protocol Independent Multicast";
         }
         enum "rip" {
           description "Routing Information Protocol";
         }
         enum "ripng" {
           description "Routing Information Protocol next generation";
         }
         enum "router-discovery" {
           description "Router Discovery";
         }
         enum "rsvp" {
           description "Resource Reservation Protocol";
         }
         enum "sap" {
           description "Session Announcement Protocol";
         }
         enum "vrrp" {
           description "Virtual Router Redundancy Protocol";
         }
       }
     }
     uses apply-advanced;
     leaf except {
       description "Protocol type of incoming traffic to disallow";
       type empty;
     }
   }
   grouping interface-system-services-object-type {
     description "Type of incoming system-service traffic to accept";
     leaf name {
       type enumeration {
         enum "all" {
           description "All system services";
         }
         enum "bootp" {
           description "Bootp and dhcp relay-agent service";
         }
         enum "dhcp" {
           description "Dynamic Host Configuration Protocol";
         }
         enum "dhcpv6" {
           description "Enable Dynamic Host Configuration Protocol for IPv6";
         }
         enum "dns" {
           description "DNS service";
         }
         enum "finger" {
           description "Finger service";
         }
         enum "ftp" {
           description "FTP";
         }
         enum "ident-reset" {
           description "Send back TCP RST to IDENT request for port 113";
         }
         enum "http" {
           description "Web management service using HTTP";
         }
         enum "https" {
           description "Web management service using HTTP secured by SSL";
         }
         enum "ike" {
           description "Internet Key Exchange";
         }
         enum "netconf" {
           description "NETCONF service";
         }
         enum "ping" {
           description "Internet Control Message Protocol echo requests";
         }
         enum "rlogin" {
           description "Rlogin service";
         }
         enum "reverse-telnet" {
           description "Reverse telnet service";
         }
         enum "reverse-ssh" {
           description "Reverse SSH service";
         }
         enum "rpm" {
           description "Real-time performance monitoring";
         }
         enum "rsh" {
           description "Rsh service";
         }
         enum "snmp" {
           description "Simple Network Management Protocol service";
         }
         enum "snmp-trap" {
           description "Simple Network Management Protocol traps";
         }
         enum "ssh" {
           description "SSH service";
         }
         enum "telnet" {
           description "Telnet service";
         }
         enum "traceroute" {
           description "Traceroute service";
         }
         enum "xnm-ssl" {
           description "JUNOScript API service over SSL";
         }
         enum "xnm-clear-text" {
           description "JUNOScript API for unencrypted traffic over TCP";
         }
         enum "tftp" {
           description "TFTP";
         }
         enum "lsping" {
           description "Label Switched Path ping service";
         }
         enum "lsselfping" {
           description "Label Switched Path self ping service";
         }
         enum "ntp" {
           description "Network Time Protocol service";
         }
         enum "sip" {
           description "Enable Session Initiation Protocol service";
         }
         enum "r2cp" {
           description "Enable Radio-Router Control Protocol service";
         }
         enum "webapi-clear-text" {
           description "Webapi service using http";
         }
         enum "webapi-ssl" {
           description "Webapi service using HTTP secured by SSL";
         }
         enum "tcp-encap" {
           description "Tcp encapsulation service";
         }
         enum "appqoe" {
           description "APPQOE active probe service";
         }
         enum "high-availability" {
           description "High Availability service";
         }
         enum "any-service" {
           description "Enable services on entire port range";
         }
       }
     }
     uses apply-advanced;
     leaf except {
       description "Type of incoming system-service traffic to disallow";
       type empty;
     }
   }
   grouping zone_host_inbound_traffic_t {
     uses apply-advanced;
     list system-services {
       key name;
       ordered-by user;
       description "Type of incoming system-service traffic to accept";
       uses zone-system-services-object-type;
     }
     list protocols {
       key name;
       ordered-by user;
       description "Protocol type of incoming traffic to accept";
       uses host-inbound-protocols-object-type;
     }
   }
   grouping zone-system-services-object-type {
     description "Type of incoming system-service traffic to accept";
     leaf name {
       type enumeration {
         enum "all" {
           description "All system services";
         }
         enum "bootp" {
           description "Bootp and dhcp relay-agent service";
         }
         enum "dhcp" {
           description "Dynamic Host Configuration Protocol";
         }
         enum "dhcpv6" {
           description "Enable Dynamic Host Configuration Protocol for IPv6";
         }
         enum "dns" {
           description "DNS service";
         }
         enum "finger" {
           description "Finger service";
         }
         enum "ftp" {
           description "FTP";
         }
         enum "ident-reset" {
           description "Send back TCP RST to IDENT request for port 113";
         }
         enum "http" {
           description "Web management service using HTTP";
         }
         enum "https" {
           description "Web management service using HTTP secured by SSL";
         }
         enum "ike" {
           description "Internet Key Exchange";
         }
         enum "netconf" {
           description "NETCONF service";
         }
         enum "ping" {
           description "Internet Control Message Protocol echo requests";
         }
         enum "rlogin" {
           description "Rlogin service";
         }
         enum "reverse-telnet" {
           description "Reverse telnet service";
         }
         enum "reverse-ssh" {
           description "Reverse SSH service";
         }
         enum "rpm" {
           description "Real-time performance monitoring";
         }
         enum "rsh" {
           description "Rsh service";
         }
         enum "snmp" {
           description "Simple Network Management Protocol service";
         }
         enum "snmp-trap" {
           description "Simple Network Management Protocol traps";
         }
         enum "ssh" {
           description "SSH service";
         }
         enum "telnet" {
           description "Telnet service";
         }
         enum "traceroute" {
           description "Traceroute service";
         }
         enum "xnm-ssl" {
           description "JUNOScript API service over SSL";
         }
         enum "xnm-clear-text" {
           description "JUNOScript API for unencrypted traffic over TCP";
         }
         enum "tftp" {
           description "TFTP";
         }
         enum "lsping" {
           description "Label Switched Path ping service";
         }
         enum "lsselfping" {
           description "Label Switched Path self ping service";
         }
         enum "ntp" {
           description "Network Time Protocol service";
         }
         enum "sip" {
           description "Enable Session Initiation Protocol service";
         }
         enum "r2cp" {
           description "Enable Radio-Router Control Protocol service";
         }
         enum "webapi-clear-text" {
           description "Webapi service using http";
         }
         enum "webapi-ssl" {
           description "Webapi service using HTTP secured by SSL";
         }
         enum "tcp-encap" {
           description "Tcp encapsulation service";
         }
         enum "appqoe" {
           description "APPQOE active probe service";
         }
         enum "high-availability" {
           description "High Availability service";
         }
         enum "any-service" {
           description "Enable services on entire port range";
         }
       }
     }
     uses apply-advanced;
     leaf except {
       description "Type of incoming system-service traffic to disallow";
       type empty;
     }
   }
 }
