/*
 * Copyright (c) 2023 Juniper Networks, Inc.
 * All rights reserved.
 */
 module junos-common-odl-extensions {
   namespace "http://yang.juniper.net/junos/common/odl-extensions";

   prefix junos-odl;

   organization "Juniper Networks, Inc.";

   contact "yang-support@juniper.net";

   description "This module contains definitions for Junos YANG ODL extensions";

   revision 2023-01-01 {
     description "Junos: 23.1R1.8";
   }

   extension header {
     argument "header";
     description "ODL format header";
   }
   extension header-group {
     argument "header-group";
     description "ODL format header group";
   }
   extension picture {
     argument "picture";
     description "ODL format picture";
   }
   extension line {
     description "ODL line statement";
   }
   extension field {
     argument "field";
     description "ODL field statement";
   }
   extension style {
     argument "style";
     description "ODL format style";
   }
   extension template {
     argument "template";
     description "ODL format template";
   }
   extension indent {
     argument "indent";
     description "Indent the display to right";
   }
   extension default-text {
     argument "default-text";
     description "ODL default text for missing field";
   }
   extension formal-name {
     argument "formal-name";
     description "ODL formal name for rendering";
   }
   extension capitalize {
     description "ODL flag to capitalize the text output";
   }
   extension colon {
     description "ODL flag for colon";
   }
   extension explicit {
     description "ODL flag for explicit";
   }
   extension fieldwrap {
     description "ODL flag for fieldwrap";
   }
   extension float {
     description "ODL flag for float";
   }
   extension leading {
     description "ODL flag for leading";
   }
   extension space {
     description "ODL flag for space";
   }
   extension truncate {
     description "ODL flag for truncate";
   }
   extension wordwrap {
     description "ODL flag for wordwrap";
   }
   extension comma {
     description "ODL flag for comma";
   }
   extension cli-format {
     description "Flag for container used for cli rendering";
   }
   extension no-line-break {
     description "ODL flag for no linebreak";
   }
   extension blank-line {
     description "ODL flag for no blank line";
   }
 }
