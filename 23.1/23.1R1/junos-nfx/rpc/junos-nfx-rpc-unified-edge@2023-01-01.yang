/*
 * Copyright (c) 2023 Juniper Networks, Inc.
 * All rights reserved.
 */
 module junos-nfx-rpc-unified-edge {
   namespace "http://yang.juniper.net/junos-nfx/rpc/unified-edge";

   prefix unified-edge;

   import junos-common-types {
     prefix jt;
     revision-date 2023-01-01;
   }

   organization "Juniper Networks, Inc.";

   contact "yang-support@juniper.net";

   description "Junos RPC YANG module for unified-edge command(s)";

   revision 2023-01-01 {
     description "Junos: 23.1R1.8";
   }

   rpc get-mobile-gateway-aaa-statistics {
     description "Show AAA statistics";
     input {
       leaf statistics-type {
         description "Specify statistics type";
         type enumeration {
           enum "authentication" {
             description "Authentication statistics";
           }
           enum "accounting" {
             description "Accounting statistics";
           }
           enum "dynamic-requests" {
             description "Dynamic Authorization requests statistics";
           }
         }
         mandatory true;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
           enum "extensive" {
             description "Display extensive output";
           }
         }
       }
     }
     output {
       container mobile-gateway-aaa-statistics {
         uses mobile-gateway-aaa-statistics-block;
       }
     }
   }
   rpc get-mobile-gateway-aaa-radius-statistics {
     description "Show RADIUS server statistics";
     input {
       leaf statistics-type {
         description "Specify statistics type";
         type enumeration {
           enum "authentication" {
             description "Authentication statistics";
           }
           enum "accounting" {
             description "Accounting statistics";
           }
           enum "dynamic-requests" {
             description "Dynamic Authorization requests statistics";
           }
         }
         mandatory true;
       }
       leaf radius-server-name {
         description "Show statistics related to the RADIUS server";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       container mobile-gateway-aaa-radius-statistics {
         uses mobile-gateway-aaa-radius-statistics-block;
       }
     }
   }
   rpc get-mobile-gateway-aaa-network-element-status {
     description "Display network element status";
     input {
       leaf network-element-name {
         description "Show status related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
     }
     output {
       container mobile-gateway-aaa-network-element-status {
         uses mobile-gateway-aaa-network-element-status-block;
       }
     }
   }
   rpc get-mobile-gateway-aaa-network-element-group-status {
     description "Display network element group status";
     input {
       leaf network-element-name {
         description "Show status related to the network element group";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       container mobile-gateway-aaa-network-element-group-status {
         uses mobile-gateway-aaa-network-element-group-status-block;
       }
     }
   }
   rpc get-mobile-gateway-charging-xfer-stats {
     description "Show charging transfer statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging stats of transport-profile name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-charging-xfer-status {
     description "Show charging transfer status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging transport-profile name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-charging-path-stats {
     description "Show charging path statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-charging-path-status {
     description "Show charging path status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-charging-local-persist-stats {
     description "Show charging local-persistent-storage statistics";
     input {
       leaf gateway {
         description "Gateway name";
         type string {
           length "1 .. 64";
         }
       }
     }
   }
   rpc get-ggsn-pgw-charging-service-mode {
     description "Show service mode status for a profile";
     input {
       leaf gateway {
         description "Gateway name";
         type string {
           length "1 .. 64";
         }
         mandatory true;
       }
       leaf charging-profile {
         description "Charging profile name";
         type string {
           length "1 .. 128";
         }
       }
       leaf transport-profile {
         description "Transport profile name";
         type string {
           length "1 .. 128";
         }
       }
       leaf verbosity_level {
         default "brief";
         type enumeration {
           enum "brief" {
             description "Display brief output (default)";
           }
           enum "detail" {
             description "Display detailed output";
           }
         }
       }
     }
     output {
       container ggsn-pgw-charging-service-mode {
         uses ggsn-pgw-charging-service-mode-block;
       }
     }
   }
   rpc get-mobile-gateway-charging-global-stats {
     description "Show charging global statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
   }
   rpc get-gtpc-statistics {
     description "Show GTP statistics";
     input {
       leaf gateway {
         description "Show statistics for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtp-show-interface-stats {
         description "Specify the GTP interface to display statistics";
         type enumeration {
           enum "gn" {
             description "GTP gn interface statistics";
           }
           enum "gp" {
             description "GTP gp interface statistics";
           }
           enum "s5" {
             description "GTP s5 interface statistics";
           }
           enum "s8" {
             description "GTP s8 interface statistics";
           }
         }
       }
       leaf gtp-show-stats-version {
         description "Specify the GTP version to display statistics";
         type enumeration {
           enum "v0" {
             description "GTP version 0 statistics";
           }
           enum "v1" {
             description "GTP version 1 statistics";
           }
           enum "v2" {
             description "GTP version 2 statistics";
           }
         }
       }
       leaf detail {
         description "GTP cause stats included";
         type empty;
       }
     }
     output {
       container gtpc-statistics {
         uses gtpc-statistics-block;
       }
     }
   }
   rpc get-gtpc-peer-information {
     description "Show GTP Peer Information ";
     input {
       leaf gateway {
         description "Show gtp peer information for a gateway";
         type string {
           length "1 .. 64";
         }
       }
       leaf local-address {
         description "Local IP address for peer";
         type string;
       }
       leaf remote-address {
         description "Remote IP address of peer";
         type string;
       }
       leaf routing-instance {
         description "Routing Instance of peer";
         type string;
       }
       leaf detail {
         description "Scratch pad statistics included";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gn {
         description "GTP gn Interface Peers";
         type empty;
       }
       leaf gp {
         description "GTP gp Interface Peers";
         type empty;
       }
       leaf s5 {
         description "GTP s5 Interface Peers";
         type empty;
       }
       leaf s8 {
         description "GTP s8 Interface Peers";
         type empty;
       }
     }
   }
   rpc get-gtpc-peer-history-information-pgw {
     description "History of previous peers ";
     input {
       leaf local-address {
         description "Local IP address for peer";
         type string;
       }
       leaf remote-address {
         description "Remote IP address of peer";
         type string;
       }
       leaf routing-instance {
         description "Routing Instance of peer";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show gtp peer information for a gateway";
         type string {
           length "1 .. 64";
         }
       }
       leaf detail {
         description "Scratch pad statistics included";
         type empty;
       }
     }
   }
   rpc get-gtpc-peer-count {
     description "Show GTP Peer Count";
     output {
       container gtpc-peer-count {
         uses gtpc-peer-count-block;
       }
     }
   }
   rpc get-gtpc-peer-statistics {
     description "Show GTP Peer statistics";
     input {
       leaf gateway {
         description "Show gtp peer statistics for a gateway";
         type string {
           length "1 .. 64";
         }
       }
       leaf remote-address {
         description "Remote IP address of peer";
         type string;
         mandatory true;
       }
       leaf local-address {
         description "Local IP address for peer";
         type string;
       }
       leaf routing-instance {
         description "Routing Instance of peer";
         type string;
       }
       leaf fpc-slot {
         description "FPC slot number";
         type union {
           type uint32;
           type string {
             pattern "<.*>|$.*";
           }
         }
       }
       leaf history {
         description "History of previous peers";
         type empty;
       }
       leaf pic-slot {
         description "PIC slot number";
         type union {
           type uint32;
           type string {
             pattern "<.*>|$.*";
           }
         }
       }
       leaf gtp-version {
         description "Specify the GTP version to display statistics";
         default "gtp-all";
         type enumeration {
           enum "v0" {
             description "GTP version 0 statistics";
           }
           enum "v1" {
             description "GTP version 1 statistics";
           }
           enum "v2" {
             description "GTP version 2 statistics";
           }
           enum "gtp-all" {
             description "GTP all version statistics";
           }
         }
       }
       leaf detail {
         description "GTP cause stats included";
         type empty;
       }
     }
     output {
       container gtpc-peer-statistics {
         uses gtpc-peer-statistics-block;
       }
     }
   }
   rpc get-mobile-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       container mobile-gateway-service-mode {
         uses mobile-gateway-service-mode-block;
       }
     }
   }
   rpc get-ggsn-pdn-gateway-interfaces-information {
     description "Show system interfaces";
     input {
       leaf gateway {
         description "Show system interfaces for a gateway";
         type string {
           length "1 .. 64";
         }
       }
     }
   }
   rpc get-mobile-ggsn-pdn-gateway-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       container gateway-system-interface-service-mode {
         uses gateway-system-interface-service-mode-block;
       }
     }
   }
   rpc get-mobile-gateways-ip-reassembly-statistics {
     description "Show IP reassembly statistics";
     input {
       leaf family {
         type enumeration {
           enum "inet" {
             description "Family inet";
           }
         }
       }
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       container mobile-gateways-ip-reassembly-statistics {
         uses mobile-gateways-ip-reassembly-statistics-block;
       }
     }
   }
   rpc get-cac-statistics {
     description "Display CAC statistics";
     input {
       leaf gateway {
         description "Show statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       container cac-statistics {
         uses cac-statistics-block;
       }
     }
   }
   rpc get-mobile-gateway-aaa-diam-stats-gx {
     description "Show diameter statistics related to Gx";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
   }
   rpc get-mobile-gateway-aaa-diam-stats-gy {
     description "Show diameter statistics related to Gy";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
   }
   rpc get-mobile-gateway-aaa-diam-ne-statistics {
     description "Show network-element specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-ne-statistics {
         uses mobile-gateway-aaa-diam-ne-statistics-block;
       }
     }
   }
   rpc get-mobile-gateway-aaa-diam-ne-status {
     description "Show Diameter network-element status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
     }
     output {
       container mobile-gateway-aaa-diam-ne-status {
         uses mobile-gateway-aaa-diam-ne-status-block;
       }
     }
   }
   rpc get-mobile-gateway-aaa-diam-peer-statistics {
     description "Show peer specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-peer-statistics {
         uses mobile-gateway-aaa-diam-peer-statistics-block;
       }
     }
   }
   rpc get-mobile-gateway-aaa-diam-peer-status {
     description "Show the peer status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-peer-status {
         uses mobile-gateway-aaa-diam-peer-status-block;
       }
     }
   }
   rpc get-mobile-ggsn-pdn-gateway-status {
     description "Show gateway status";
     input {
       leaf gateway {
         description "Show subscriber for a gateway";
         type string {
           length "1 .. 64";
         }
       }
       leaf apn-name {
         description "Name of APN";
         type string {
           length "1 .. 100";
         }
       }
       leaf qci {
         description "Show status per QCI";
         type empty;
       }
       leaf gtpv2-priority-level {
         description "Show status per gtpv2 priority level";
         type empty;
       }
       leaf traffic-class {
         description "Show status for a traffic class level";
         type empty;
       }
       leaf gtpv1-arp {
         description "Show status per gtp v1 ARP";
         type empty;
       }
       leaf rat-type {
         description "Show status per RAT-Type";
         type empty;
       }
       leaf pdn-type {
         description "Display status per PDN-Type";
         type empty;
       }
       leaf roaming-status {
         description "Display status per roaming status type";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       container mobile-gateway-status {
         uses mobile-gateway-status-block;
       }
     }
   }
   rpc get-mobile-gateways-preemption-list-pgw {
     description "Show gateway preemption list";
     input {
       leaf gateway {
         description "Show preemption list for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
   }
   rpc get-mobile-gateway-gtp-peer-apfe-distribution-pgw {
     description "Show bearer anchor PFE distribution per GTP peer";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show bearer APFE distribution per GTP peer for gateway";
         type string {
           length "1 .. 64";
         }
       }
       leaf remote-address {
         description "Remote IP address of peer";
         type string;
         mandatory true;
       }
       leaf local-address {
         description "Local IP address for peer";
         type string;
       }
       leaf routing-instance {
         description "Routing Instance of Peer";
         type union {
           type uint32;
           type string {
             pattern "<.*>|$.*";
           }
         }
       }
     }
   }
   rpc get-mobile-gateways-session-state-pgw {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       container mobile-gateway-status {
         uses mobile-gateway-status-block;
       }
     }
   }
   rpc get-mobile-ggsn-pdn-gateway-subscriber-traffic-class {
     description "Show subscribers at traffic class level";
     input {
       leaf gtpv1-traffic-class {
         description "Show subscribers for a particular traffic class";
         type enumeration {
           enum "background" {
             description "Traffic class background";
           }
           enum "conversational" {
             description "Traffic class conversational";
           }
           enum "streaming" {
             description "Traffic class streaming";
           }
           enum "interactive" {
             description "Traffic class interactive";
           }
         }
         mandatory true;
       }
       leaf traffic-handling-priority {
         description "Traffic handling priority";
         type union {
           type string {
             pattern "<.*>|$.*";
           }
           type uint32 {
             range "1 .. 3";
           }
         }
       }
     }
   }
   rpc get-mobile-gateways-apn-statistics {
     description "Show APN statistics";
     input {
       leaf gateway {
         description "Show apn statistics of the gateway";
         type string {
           length "1 .. 64";
         }
       }
       leaf access-point-name {
         description "APN name";
         type string {
           length "1 .. 100";
         }
         mandatory true;
       }
     }
   }
   rpc get-mobile-gateways-apn-call-rate-statistics {
     input {
       leaf gateway {
         description "Show apn call rate statistics of the gateway";
         type string {
           length "1 .. 64";
         }
         mandatory true;
       }
       leaf apn-name {
         description "APN name";
         type string {
           length "1 .. 100";
         }
         mandatory true;
       }
     }
     output {
       container mobile-gateway-call-rate-statistics {
         uses mobile-gateway-call-rate-statistics-block;
       }
     }
   }
   rpc get-mobile-gateways-apn-service-mode {
     description "Show service mode status for an APN";
     input {
       leaf gateway {
         description "Gateway name";
         type string {
           length "1 .. 64";
         }
       }
       leaf apn-name {
         description "APN name";
         type string {
           length "1 .. 100";
         }
       }
       leaf verbosity_level {
         default "brief";
         type enumeration {
           enum "brief" {
             description "Display brief output (default)";
           }
           enum "detail" {
             description "Display detailed output";
           }
         }
       }
     }
     output {
       container mobile-gateways-apn-service-mode {
         uses mobile-gateways-apn-service-mode-block;
       }
     }
   }
   rpc get-mobile-gateways-statistics {
     description "Show statistics";
     input {
       leaf gateway {
         description "Show statistics for a gateway";
         type string {
           length "1 .. 64";
         }
       }
       leaf apn {
         description "APN name";
         type string {
           length "1 .. 100";
         }
       }
       leaf qci {
         description "QCI value";
         type union {
           type string {
             pattern "<.*>|$.*";
           }
           type int32 {
             range "1 .. 9";
           }
         }
       }
       leaf gtpv2-priority-level {
         description "GTPv2 priority level";
         type union {
           type string {
             pattern "<.*>|$.*";
           }
           type uint32 {
             range "1 .. 15";
           }
         }
       }
       leaf gtpv1-arp {
         description "GTPv1 ARP Value";
         type union {
           type string {
             pattern "<.*>|$.*";
           }
           type uint32 {
             range "1 .. 3";
           }
         }
       }
     }
   }
   rpc get-mobile-ggsn-pdn-gateway-statistics-traffic-class {
     description "Show statistics at traffic class level";
     input {
       leaf gtpv1-traffic-class {
         description "Show statistics for a traffic class level";
         type enumeration {
           enum "background" {
             description "Traffic class background";
           }
           enum "conversational" {
             description "Traffic class conversational";
           }
           enum "streaming" {
             description "Traffic class streaming";
           }
           enum "interactive" {
             description "Traffic class interactive";
           }
         }
         mandatory true;
       }
       leaf traffic-handling-priority {
         description "Traffic handling priority";
         type union {
           type string {
             pattern "<.*>|$.*";
           }
           type uint32 {
             range "1 .. 3";
           }
         }
       }
     }
   }
   rpc get-mobile-ggsn-pdn-gateway-call-rate-statistics {
     description "Show gateway call-rate statistics";
     input {
       leaf history {
         description "History of statistics collected";
         type empty;
       }
       leaf gateway {
         description "Gateway name";
         type string {
           length "1 .. 64";
         }
       }
     }
     output {
       container mobile-gateway-call-rate-statistics {
         uses mobile-gateway-call-rate-statistics-block;
       }
     }
   }
   rpc get-ggssn-pgw-address-assign-service-mode {
     description "Show service mode status for a pool";
     input {
       leaf pool {
         description "Address pool name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       container ggsn-pgw-address-assign-service-mode {
         uses ggsn-pgw-address-assign-service-mode-block;
       }
     }
   }
   rpc get-mobile-gateway-sm-ippool-pool-information {
     description "Show pool specific information";
     input {
       leaf pool-name {
         description "Show information for a specific pool";
         type string {
           length "1 .. 64";
         }
       }
       leaf all_ranges {
         type enumeration {
           enum "ranges" {
             description "Show information for all ranges in the pool";
           }
         }
       }
       leaf range-name {
         description "Show information for a range in the pool";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "summary" {
             description "Display summary output";
           }
           enum "brief" {
             description "Display brief output (default)";
           }
           enum "detail" {
             description "Display detailed output";
           }
         }
       }
     }
     output {
       container mobile-gateway-sm-ippool-pool-information {
         uses mobile-gateway-sm-ippool-pool-information-block;
       }
     }
   }
   rpc get-mobile-gateway-sm-ippool-group-information {
     description "Show group specific information";
     input {
       leaf group-name {
         description "Show information for a specific group";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       container mobile-gateway-sm-ippool-group-information {
         uses mobile-gateway-sm-ippool-group-information-block;
       }
     }
   }
   rpc get-mobile-gateway-sm-ippool-statistics {
     description "Show address assignment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf verbosity_level {
         default "brief";
         type enumeration {
           enum "brief" {
             description "Display brief output (default)";
           }
           enum "detail" {
             description "Display detailed output";
           }
         }
       }
     }
     output {
       container mobile-gateway-sm-ippool-statistics {
         uses mobile-gateway-sm-ippool-statistics-block;
       }
     }
   }
   rpc get-mobile-gateway-pgw-rmm-client-status {
     description "Show all the resource controller clients state info";
     input {
       leaf gateway {
         description "Show resource controller clients state info for a gateway";
         type string {
           length "1 .. 64";
         }
       }
     }
     output {
       container rmpsd-show-rmm-client-command {
         uses rmpsd-show-rmm-client-command-block;
       }
     }
   }
   rpc get-tdf-gateway-aaa-statistics {
     description "TDF aaa statistics";
     input {
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       container tdf-gateway-aaa-statistics {
         uses tdf-gateway-aaa-statistics-block;
       }
     }
   }
   rpc radius-client-statistics {
     description "TDF radius client statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf client {
         description "Radius client name";
         type string {
           length "1 .. 32";
         }
       }
       leaf verbosity_level {
         default "brief";
         type enumeration {
           enum "brief" {
             description "Display brief output (default)";
           }
           enum "detail" {
             description "Display detailed output";
           }
         }
       }
     }
     output {
       container radius-client-statistics {
         uses radius-client-statistics-block;
       }
     }
   }
   rpc get-aaa-radius-client-status {
     description "Display radius client status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf client {
         description "Radius client name";
         type string {
           length "1 .. 32";
         }
       }
     }
   }
   rpc get-aaa-radius-element-status {
     description "Display radius network-element status";
     input {
       leaf network-element-name {
         description "Show status related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
     }
   }
   rpc get-aaa-radius-element-statistics {
     description "Display radius network-element statistics";
     input {
       leaf network-element-name {
         description "Show statistics related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
   }
   rpc radius-server-statistics {
     description "TDF radius server statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf radius-server-name {
         description "Show statistics related to the radius server";
         type string {
           length "1 .. 32";
         }
       }
       leaf verbosity_level {
         default "brief";
         type enumeration {
           enum "brief" {
             description "Display brief output (default)";
           }
           enum "detail" {
             description "Display detailed output";
           }
         }
       }
     }
   }
   rpc get-aaa-radius-server-status {
     description "Display radius server status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf radius-server-name {
         description "Show status related to the radius server";
         type string {
           length "1 .. 32";
         }
       }
       leaf verbosity_level {
         default "brief";
         type enumeration {
           enum "brief" {
             description "Display brief output (default)";
           }
           enum "detail" {
             description "Display detailed output";
           }
         }
       }
     }
   }
   rpc radius-snoop-segment-statistics {
     description "TDF radius snoop-segment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf segment {
         description "Radius snoop-segment";
         type string {
           length "1 .. 32";
         }
       }
       leaf verbosity_level {
         default "brief";
         type enumeration {
           enum "brief" {
             description "Display brief output (default)";
           }
           enum "detail" {
             description "Display detailed output";
           }
         }
       }
     }
     output {
       container radius-snoop-segment-statistics {
         uses radius-snoop-segment-statistics-block;
       }
     }
   }
   rpc get-tdf-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
   }
   rpc get-tdf-interfaces-information {
     description "Show system interfaces";
     input {
       leaf gateway {
         description "Show system interfaces for a gateway";
         type string {
           length "1 .. 64";
         }
       }
     }
   }
   rpc get-mobile-tdf-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       container gateway-system-interface-service-mode {
         uses gateway-system-interface-service-mode-block;
       }
     }
   }
   rpc get-tdf-cac-statistics {
     description "Display CAC statistics";
     input {
       leaf gateway {
         description "Show statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       container cac-statistics {
         uses cac-statistics-block;
       }
     }
   }
   rpc get-diameter-statistics-gx {
     description "Show diameter statistics related to gx";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
   }
   rpc get-diameter-network-element-statistics {
     description "Show network-element specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-ne-statistics {
         uses mobile-gateway-aaa-diam-ne-statistics-block;
       }
     }
   }
   rpc get-diamieter-network-element-status {
     description "Show diameter network-element status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
     }
     output {
       container mobile-gateway-aaa-diam-ne-status {
         uses mobile-gateway-aaa-diam-ne-status-block;
       }
     }
   }
   rpc get-gateway-diameter-peer-statistics {
     description "Show peer specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-peer-statistics {
         uses mobile-gateway-aaa-diam-peer-statistics-block;
       }
     }
   }
   rpc get-diameter-peer-status {
     description "Show the peer status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       container mobile-gateway-aaa-diam-peer-status {
         uses mobile-gateway-aaa-diam-peer-status-block;
       }
     }
   }
   rpc get-tdf-gateway-subscribers {
     description "Show information related to subscribers";
     input {
       leaf gateway {
         description "Show subscribers for a gateway";
         type string {
           length "1 .. 64";
         }
       }
       leaf domain {
         description "Name of TDF domain";
         type string {
           length "1 .. 63";
         }
       }
       leaf subscriber-name {
         description "IFL subscriber name";
         type string;
       }
       leaf business-subscribers {
         description "Show only business subscribers";
         type empty;
       }
       leaf v4-addr {
         description "Show  subscribers for matching address";
         type jt:ipaddr;
       }
       leaf routing-instance {
         description "Name of routing instance";
         type string;
       }
       leaf v6-addr {
         description "Show subscribers for matching address";
         type jt:ipv6addr;
       }
       leaf pdn-type {
         description "Show subscribers by PDN-Type";
         type enumeration {
           enum "ipv4" {
             description "Show ipv4 subscribers";
           }
           enum "ipv6" {
             description "Show ipv6 subscribers";
           }
           enum "ipv4-v6" {
             description "Show ipv4-v6 subscribers";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case multichassis-tag {
           anyxml multi-routing-engine-results;
         }
       }
     }
   }
   rpc get-tdf-gateway-subscriber-dataplane-statistics {
     description "Show dataplane statistics";
     input {
       leaf gateway {
         description "Show subscribers for a gateway";
         type string {
           length "1 .. 64";
         }
       }
       leaf subscriber-name {
         description "IFL subscriber name";
         type string;
       }
       leaf v4-addr {
         description "Show  subscribers for matching address";
         type jt:ipaddr;
       }
       leaf routing-instance {
         description "Name of data routing instance";
         type string;
       }
       leaf business-subscribers {
         description "Show only business subscribers";
         type empty;
       }
       leaf v6-addr {
         description "Show subscribers for matching address";
         type jt:ipv6addr;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc get-tdf-gateway-stuck-subscribers {
     description "Show stuck subscribers";
     output {
       choice output_c {
         case output-tag {
           leaf output {
             type string;
           }
         }
         case multichassis-tag {
           anyxml multi-routing-engine-results;
         }
       }
     }
   }
   rpc get-tdf-gateway-status {
     description "Show gateway status";
     input {
       leaf gateway {
         description "Show subscriber for a gateway";
         type string {
           length "1 .. 64";
         }
       }
       leaf domain {
         description "Name of TDF domain";
         type string {
           length "1 .. 100";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       container tdf-gateway-status {
         uses tdf-gateway-status-block;
       }
     }
   }
   rpc get-tdf-gateways-status-state {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       container tdf-gateway-status {
         uses tdf-gateway-status-block;
       }
     }
   }
   rpc get-tdf-statistics {
     description "Show TDF statistics";
     input {
       leaf gateway {
         description "Gateway name";
         type string {
           length "1 .. 64";
         }
       }
       leaf domain {
         description "Domain name";
         type string {
           length "1 .. 63";
         }
       }
     }
   }
   rpc get-tdf-call-rate-statistics {
     description "Show TDF call rate statistics";
     input {
       leaf gateway {
         description "Gateway name";
         type string {
           length "1 .. 64";
         }
         mandatory true;
       }
       leaf domain {
         description "Domain name";
         type string {
           length "1 .. 63";
         }
       }
     }
     output {
       container tdf-call-rate-statistics-root {
         uses tdf-call-rate-statistics-root-block;
       }
     }
   }
   rpc get-mobile-gateways-domain-service-mode {
     description "Show service mode status for a domain";
     input {
       leaf gateway {
         description "Gateway name";
         type string {
           length "1 .. 64";
         }
       }
       leaf domain-name {
         description "Domain name";
         type string {
           length "1 .. 63";
         }
       }
       leaf verbosity_level {
         default "brief";
         type enumeration {
           enum "brief" {
             description "Display brief output (default)";
           }
           enum "detail" {
             description "Display detailed output";
           }
         }
       }
     }
     output {
       container mobile-gateways-domain-service-mode {
         uses mobile-gateways-domain-service-mode-block;
       }
     }
   }
   rpc get-mobile-gateways-domain-statistics {
     description "Show statistics for a tdf domain";
     input {
       leaf gateway {
         description "Gateway name";
         type string {
           length "1 .. 64";
         }
       }
       leaf domain-name {
         description "Domain name";
         type string {
           length "1 .. 63";
         }
         mandatory true;
       }
     }
   }
   rpc get-tdf-address-assign-service-mode {
     description "Show service mode status for a pool";
     input {
       leaf pool {
         description "Address pool name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       container ggsn-pgw-address-assign-service-mode {
         uses ggsn-pgw-address-assign-service-mode-block;
       }
     }
   }
   rpc get-tdf-gateway-sm-ippool-pool-information {
     description "Show pool specific information";
     input {
       leaf pool-name {
         description "Show information for a specific pool";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "summary" {
             description "Display summary output";
           }
           enum "brief" {
             description "Display brief output (default)";
           }
           enum "detail" {
             description "Display detailed output";
           }
         }
       }
     }
     output {
       container mobile-gateway-sm-ippool-pool-information {
         uses mobile-gateway-sm-ippool-pool-information-block;
       }
     }
   }
   rpc get-tdf-gateway-sm-ippool-statistics {
     description "Show address assignment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf verbosity_level {
         default "brief";
         type enumeration {
           enum "brief" {
             description "Display brief output (default)";
           }
           enum "detail" {
             description "Display detailed output";
           }
         }
       }
     }
     output {
       container mobile-gateway-sm-ippool-statistics {
         uses mobile-gateway-sm-ippool-statistics-block;
       }
     }
   }
   rpc get-mobile-gateway-tdf-client-status-information {
     description "Show all the resource controller clients state info";
     input {
       leaf gateway {
         description "Show resource controller clients state info for a gateway";
         type string {
           length "1 .. 64";
         }
       }
     }
   }
   rpc get-mobile-gateway-sgw-charging-xfer-stats {
     description "Show charging transfer statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging stats of transport-profile name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-sgw-charging-xfer-status {
     description "Show charging transfer status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging transport-profile name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-sgw-charging-path-stats {
     description "Show charging path statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-sgw-charging-path-status {
     description "Show charging path status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-sgw-charging-local-persist-stats {
     description "Show charging local-persistent-storage statistics";
     input {
       leaf gateway {
         description "Gateway name";
         type string {
           length "1 .. 64";
         }
       }
     }
   }
   rpc get-mobile-gateway-sgw-charging-trigger-profile {
     description "Show information of trigger profile";
     input {
       leaf gateway {
         description "Gateway name";
         type string {
           length "1 .. 64";
         }
       }
       leaf trigger-profile-name {
         description "Charging trigger profile matching this name";
         type string {
           length "1 .. 128";
         }
       }
     }
     output {
       container mobile-gateway-charging-trigger-profile {
         uses mobile-gateway-charging-trigger-profile-block;
       }
     }
   }
   rpc get-sgw-charging-service-mode {
     description "Show service mode status for a profile";
     input {
       leaf gateway {
         description "Gateway name";
         type string {
           length "1 .. 64";
         }
         mandatory true;
       }
       leaf charging-profile {
         description "Charging profile name";
         type string {
           length "1 .. 128";
         }
       }
       leaf transport-profile {
         description "Transport profile name";
         type string {
           length "1 .. 128";
         }
       }
       leaf verbosity_level {
         default "brief";
         type enumeration {
           enum "brief" {
             description "Display brief output (default)";
           }
           enum "detail" {
             description "Display detailed output";
           }
         }
       }
     }
   }
   rpc get-mobile-gateway-sgw-charging-global-stats {
     description "Show charging global statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
   }
   rpc get-sgw-gtpc-statistics {
     description "Show GTP statistics";
     input {
       leaf gateway {
         description "Show gtp statistics for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtp-show-interface-stats {
         description "Specify the GTP interface to display statistics";
         type enumeration {
           enum "s5" {
             description "GTP s5 interface statistics";
           }
           enum "s8" {
             description "GTP s8 interface statistics";
           }
           enum "s11" {
             description "GTP s11 interface statistics";
           }
           enum "s4" {
             description "GTP s4 interface statistics";
           }
         }
       }
       leaf gtp-show-stats-version {
         description "Specify the GTP version to display statistics";
         type enumeration {
           enum "v1" {
             description "GTP version 1 statistics";
           }
           enum "v2" {
             description "GTP version 2 statistics";
           }
         }
       }
       leaf detail {
         description "GTP cause stats included";
         type empty;
       }
     }
     output {
       container gtpc-statistics {
         uses gtpc-statistics-block;
       }
     }
   }
   rpc get-sgw-gtpc-peer-information {
     description "Show GTP Peer Information ";
     input {
       leaf gateway {
         description "Show gtp peer information for a gateway";
         type string {
           length "1 .. 64";
         }
       }
       leaf local-address {
         description "Local IP address for peer";
         type string;
       }
       leaf remote-address {
         description "Remote IP address of peer";
         type string;
       }
       leaf routing-instance {
         description "Routing Instance of peer";
         type string;
       }
       leaf detail {
         description "Scratch pad statistics included";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf s11 {
         description "GTP s11 Interface Peers";
         type empty;
       }
       leaf s4 {
         description "GTP s4 Interface Peers";
         type empty;
       }
       leaf s11-s4 {
         description "GTP s11-s4 Interface Peers";
         type empty;
       }
       leaf s5 {
         description "GTP s5 Interface Peers";
         type empty;
       }
       leaf s8 {
         description "GTP s8 Interface Peers";
         type empty;
       }
       leaf s1u {
         description "GTP s1u Interface Peers";
         type empty;
       }
       leaf s12 {
         description "GTP s12 Interface Peers";
         type empty;
       }
     }
   }
   rpc get-gtpc-peer-history-information-sgw {
     description "History of previous peers ";
     input {
       leaf local-address {
         description "Local IP address for peer";
         type string;
       }
       leaf remote-address {
         description "Remote IP address of peer";
         type string;
       }
       leaf routing-instance {
         description "Routing Instance of peer";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show gtp peer information for a gateway";
         type string {
           length "1 .. 64";
         }
       }
       leaf detail {
         description "Scratch pad statistics included";
         type empty;
       }
     }
   }
   rpc get-sgw-gtpc-peer-count {
     description "Show GTP Peer Count";
     output {
       container gtpc-peer-count {
         uses gtpc-peer-count-block;
       }
     }
   }
   rpc get-sgw-gtpc-peer-statistics {
     description "Show GTP Peer statistics";
     input {
       leaf gateway {
         description "Show gtp peer statistics for a gateway";
         type string {
           length "1 .. 64";
         }
       }
       leaf remote-address {
         description "Remote IP address of peer";
         type string;
         mandatory true;
       }
       leaf local-address {
         description "Local IP address for peer";
         type string;
       }
       leaf routing-instance {
         description "Routing Instance of peer";
         type string;
       }
       leaf fpc-slot {
         description "FPC slot number";
         type union {
           type uint32;
           type string {
             pattern "<.*>|$.*";
           }
         }
       }
       leaf history {
         description "History of previous peers";
         type empty;
       }
       leaf pic-slot {
         description "PIC slot number";
         type union {
           type uint32;
           type string {
             pattern "<.*>|$.*";
           }
         }
       }
       leaf detail {
         description "GTP cause stats included";
         type empty;
       }
     }
     output {
       container gtpc-peer-statistics {
         uses gtpc-peer-statistics-block;
       }
     }
   }
   rpc get-sgw-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
   }
   rpc get-serving-gateway-interfaces-information {
     description "Show system interfaces";
     input {
       leaf gateway {
         description "Show system interfaces for a gateway";
         type string {
           length "1 .. 64";
         }
       }
     }
   }
   rpc get-mobile-serving-gateway-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       container gateway-system-interface-service-mode {
         uses gateway-system-interface-service-mode-block;
       }
     }
   }
   rpc get-mobile-gateways-sgw-ip-reassembly-statistics {
     description "Show IP reassembly statistics";
     input {
       leaf family {
         type enumeration {
           enum "inet" {
             description "Family inet";
           }
         }
       }
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       container mobile-gateways-ip-reassembly-statistics {
         uses mobile-gateways-ip-reassembly-statistics-block;
       }
     }
   }
   rpc get-sgw-cac-statistics {
     description "Display CAC statistics";
     input {
       leaf gateway {
         description "Show cac statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       container cac-statistics {
         uses cac-statistics-block;
       }
     }
   }
   rpc get-mobile-gw-sgw-idle-mode-buffering-statistics {
     description "Idle mode buffering statistics";
     input {
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       container mobile-gateways-sgw-idle-mode-buffering-statistics {
         uses mobile-gateways-sgw-idle-mode-buffering-statistics-block;
       }
     }
   }
   rpc get-mobile-serving-gateway-status {
     description "Show gateway status";
     input {
       leaf gateway {
         description "Show subscriber for a gateway";
         type string {
           length "1 .. 64";
         }
       }
       leaf roaming-status {
         description "Display status per roaming status type";
         type empty;
       }
       leaf qci {
         description "Show status per QCI";
         type empty;
       }
       leaf gtpv2-priority-level {
         description "Show status per gtpv2 priority-level";
         type empty;
       }
       leaf rat-type {
         description "Display status per RAT-Type";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       container mobile-gateway-status {
         uses mobile-gateway-status-block;
       }
     }
   }
   rpc get-mobile-gateways-preemption-list-sgw {
     description "Show gateway preemption list";
     input {
       leaf gateway {
         description "Show preemption list for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
   }
   rpc get-mobile-gateway-gtp-peer-apfe-distribution-sgw {
     description "Show bearer anchor PFE distribution per GTP peer";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show bearer APFE distribution per GTP peer for gateway";
         type string {
           length "1 .. 64";
         }
       }
       leaf remote-address {
         description "Remote IP address of peer";
         type string;
         mandatory true;
       }
       leaf local-address {
         description "Local IP address for peer";
         type string;
       }
       leaf routing-instance {
         description "Routing Instance of Peer";
         type union {
           type uint32;
           type string {
             pattern "<.*>|$.*";
           }
         }
       }
     }
   }
   rpc get-mobile-gateways-session-state-sgw {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       container mobile-gateway-status {
         uses mobile-gateway-status-block;
       }
     }
   }
   rpc get-mobile-gateways-sgw-statistics {
     description "Show statistics";
     input {
       leaf gateway {
         description "Show statistics for a gateway";
         type string {
           length "1 .. 64";
         }
       }
     }
   }
   rpc get-mobile-serving-gateway-call-rate-statistics {
     description "Show gateway call-rate statistics";
     input {
       leaf history {
         description "History of statistics collected";
         type empty;
       }
       leaf gateway {
         description "Gateway name";
         type string {
           length "1 .. 64";
         }
       }
     }
     output {
       container mobile-gateway-call-rate-statistics {
         uses mobile-gateway-call-rate-statistics-block;
       }
     }
   }
   rpc get-mobile-gateway-sgw-rmm-client-status {
     description "Show all the resource controller clients state info";
     input {
       leaf gateway {
         description "Show resource controller clients state info for a gateway";
         type string {
           length "1 .. 64";
         }
       }
     }
     output {
       container rmpsd-show-rmm-client-command {
         uses rmpsd-show-rmm-client-command-block;
       }
     }
   }
   rpc get-mobile-gateway-information {
     description "Display information about all configured gateways";
     input {
       leaf level {
         default "brief";
         type enumeration {
           enum "brief" {
             description "Display brief output (default)";
           }
           enum "detail" {
             description "Display detail output";
           }
         }
       }
     }
     output {
       container mobile-gateway-information {
         uses mobile-gateway-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping mobile-gateway-aaa-statistics-block {
     list aaa-authentication-statistics {
       leaf aaa-mobile-gateway-name {
         type string;
         description "Gateway Name";
       }
       leaf aaa-auth-requests {
         type uint64;
         description "Number of authentication requests";
       }
       leaf aaa-auth-accepts {
         type uint64;
         description "Number of successful authentication responses";
       }
       leaf aaa-auth-rejects {
         type uint64;
         description "Number of authentication rejects";
       }
       leaf aaa-auth-challenges {
         type uint64;
         description "Number of authentication challenges";
       }
       leaf aaa-auth-timeouts {
         type uint64;
         description "Number of timeouts";
       }
       leaf aaa-auth-req-retransmissions {
         type int32;
         description "Number of retransmissions of authentication requests";
       }
       leaf aaa-auth-transmit-errors {
         type uint64;
         description "Number of transmit errors";
       }
       leaf aaa-auth-response-errors {
         type uint64;
         description "Number of response errors";
       }
       leaf aaa-fpc-pic {
         type string;
         description "FPC/PIC slot information";
       }
     }
     list aaa-accounting-statistics {
       leaf aaa-mobile-gateway-name {
         type string;
         description "Gateway Name";
       }
       leaf aaa-acct-requests {
         type uint64;
         description "Number of accounting requests";
       }
       leaf aaa-acct-responses {
         type uint64;
         description "Number of successful responses";
       }
       leaf aaa-acct-timeouts {
         type uint64;
         description "Number of accounting request timeouts";
       }
       leaf aaa-acct-req-retransmissions {
         type int32;
         description "Number of retransmissions of accounting requests";
       }
       leaf aaa-acct-transmit-errors {
         type uint64;
         description "Number of transmit errors for accounting requests";
       }
       leaf aaa-acct-response-errors {
         type uint64;
         description "Number of response errors for accounting responses";
       }
       leaf aaa-fpc-pic {
         type string;
         description "FPC/PIC slot information";
       }
     }
     list aaa-dynamic-requests-statistics {
       leaf aaa-mobile-gateway-name {
         type string;
         description "Gateway Name";
       }
       leaf aaa-dyn-req-received {
         type uint64;
         description "Number of dynamic requests received";
       }
       leaf aaa-dyn-req-coa {
         type uint64;
         description "Number of CoA requests received";
       }
       leaf aaa-dyn-req-dm {
         type uint64;
         description "Number of DM requests received";
       }
       leaf aaa-dyn-req-coa-ack {
         type uint64;
         description "Number of CoA Acks sent";
       }
       leaf aaa-dyn-req-dm-ack {
         type uint64;
         description "Number of DM Acks sent";
       }
       leaf aaa-dyn-req-coa-nack {
         type uint64;
         description "Number of CoA Nacks sent";
       }
       leaf aaa-dyn-req-dm-nack {
         type uint64;
         description "Number of DM Nacks sent";
       }
       leaf aaa-dyn-req-dropped {
         type uint64;
         description "Number of dynamic requests dropped";
       }
       leaf aaa-fpc-pic {
         type string;
         description "FPC/PIC slot information";
       }
       leaf aaa-dyn-req-duplicate {
         type uint64;
         description "Number of duplicate dynamic requests received";
       }
       leaf aaa-dyn-req-dispatched {
         type uint64;
         description "Number of dynamic requests forwarded to anchor instance";
       }
       leaf aaa-dyn-req-timed-out {
         type uint64;
         description "Number of dynamic requests timed out";
       }
       leaf aaa-dyn-req-to-smd {
         type uint64;
         description "Number of requests delivered to application";
       }
       leaf aaa-dyn-req-errors {
         type uint64;
         description "Number of errors during processing dynamic requests";
       }
       leaf aaa-dyn-req-unknown-client {
         type uint64;
         description "Number of dynamic requests received from unknown clients";
       }
       leaf aaa-dyn-req-invalid-code {
         type uint64;
         description "Number of dynamic requests received with invalid RADIUS code";
       }
       leaf aaa-dyn-req-invalid-authenticator {
         type uint64;
         description "Number of dynamic requests received with invalid authenticator";
       }
       leaf aaa-dyn-req-invalid-charging-id {
         type uint64;
         description "Number of dynamic requests with invalid or missing Charging Id";
       }
       leaf aaa-dyn-req-rcm-error {
         type uint64;
         description "Number of session mapping errors during dynamic request processing";
       }
       leaf aaa-dyn-req-invalid-trans-id {
         type uint64;
         description "Number of errors with invalid transaction id during processing ";
       }
     }
   }
   grouping mobile-gateway-aaa-radius-statistics-block {
     list aaa-radius-server-stats {
       leaf aaa-radius-server-name {
         type string;
         description "RADIUS server name";
       }
       leaf aaa-radius-server-address {
         type jt:ipaddr;
         description "RADIUS server address";
       }
       leaf aaa-radius-server-port {
         type jt:ipaddr;
         description "RADIUS server port";
       }
       leaf aaa-radius-server-access-requests {
         type int32;
         description "Number of access requests sent to this RADIUS server";
       }
       leaf aaa-radius-server-access-req-retransmissions {
         type int32;
         description "Number of retransmissions of access requests";
       }
       leaf aaa-radius-server-access-accepts {
         type int32;
         description "Number of access accepts received from this RADIUS server";
       }
       leaf aaa-radius-server-access-rejects {
         type int32;
         description "Number of access rejects received from this RADIUS server";
       }
       leaf aaa-radius-server-malformed-responses {
         type int32;
         description "Number of malformed responses received from this RADIUS server";
       }
       leaf aaa-radius-server-bad-authenticators {
         type int32;
         description "Number of responses with bad authenticators received from this RADIUS server";
       }
       leaf aaa-radius-server-timeouts {
         type int32;
         description "Number of requests which timed out";
       }
       leaf aaa-radius-server-unknown-types {
         type int32;
         description "Number of unknown type responses received from this server";
       }
       leaf aaa-radius-server-pkts-dropped {
         type int32;
         description "Number of responses from this RADIUS which were dropped";
       }
       leaf aaa-radius-server-acct-port {
         type jt:ipaddr;
         description "RADIUS server accounting port";
       }
       leaf aaa-radius-server-acct-requests {
         type int32;
         description "Number of acounting requests sent to this RADIUS server";
       }
       leaf aaa-radius-server-acct-req-start {
         type int32;
         description "Number of accounting start requests sent to this RADIUS server";
       }
       leaf aaa-radius-server-acct-req-stop {
         type int32;
         description "Number of accounting stop requests sent to this RADIUS server";
       }
       leaf aaa-radius-server-acct-req-interim {
         type int32;
         description "Number of accounting interim requests sent to this RADIUS server";
       }
       leaf aaa-radius-server-acct-req-on {
         type int32;
         description "Number of accounting on requests sent to this RADIUS server";
       }
       leaf aaa-radius-server-acct-req-off {
         type int32;
         description "Number of accounting off requests sent to this RADIUS server";
       }
       leaf aaa-radius-server-acct-req-retransmissions {
         type int32;
         description "Number of retransmissions of accounting requests";
       }
       leaf aaa-radius-server-acct-responses {
         type int32;
         description "Number of acounting responses received from this RADIUS server";
       }
       leaf aaa-radius-server-acct-malformed-responses {
         type int32;
         description "Number of malformed responses received from this RADIUS server";
       }
       leaf aaa-radius-server-acct-bad-authenticators {
         type int32;
         description "Number of responses with bad authenticators received from this RADIUS server";
       }
       leaf aaa-radius-server-acct-timeouts {
         type int32;
         description "Number of accounting requests which timed out";
       }
       leaf aaa-radius-server-acct-unknown-types {
         type int32;
         description "Number of unknown type accounting responses received from this server";
       }
       leaf aaa-radius-server-acct-pkts-dropped {
         type int32;
         description "Number of accounting responses from this RADIUS which were dropped";
       }
       leaf aaa-radius-client-dyn-req-coa {
         type uint64;
         description "Number of CoA requests received from this RADIUS client";
       }
       leaf aaa-radius-client-dyn-req-dm {
         type uint64;
         description "Number of DM requests received from this RADIUS client";
       }
       leaf aaa-radius-client-dyn-req-coa-ack {
         type uint64;
         description "Number of CoA Acks sent to this RADIUS client";
       }
       leaf aaa-radius-client-dyn-req-dm-ack {
         type uint64;
         description "Number of DM Acks sent to this RADIUS client";
       }
       leaf aaa-radius-client-dyn-req-coa-nack {
         type uint64;
         description "Number of CoA Nacks sent to this RADIUS client";
       }
       leaf aaa-radius-client-dyn-req-dm-nack {
         type uint64;
         description "Number of DM Nacks sent to this RADIUS client";
       }
       leaf aaa-radius-client-dyn-req-dropped {
         type uint64;
         description "Number of dropped dynamic requests from this RADIUS client";
       }
       leaf aaa-mobile-gateway-name {
         type string;
         description "Gateway Name";
       }
       leaf aaa-radius-server-total-requests {
         type int32;
         description "Total requests";
       }
       leaf aaa-radius-server-total-responses {
         type int32;
         description "Total responses";
       }
       leaf aaa-radius-server-access-challenges {
         type int32;
         description "Number of access challenges received from this RADIUS server";
       }
       leaf aaa-fpc-pic {
         type string;
         description "FPC/PIC slot information";
       }
       leaf aaa-comment {
         type string;
         description "Comment";
       }
       leaf aaa-radius-server-routing-instance {
         type string;
         description "Routing instance through which the RADIUS server is reachable";
       }
       leaf aaa-radius-client-dyn-req-duplicate {
         type uint64;
         description "Number of duplicate dynamic requests received from this RADIUS client";
       }
       leaf aaa-radius-client-dyn-req-dispatched {
         type uint64;
         description "Number of requests from this RADIUS client forwarded to anchor instance";
       }
       leaf aaa-radius-client-dyn-req-timed-out {
         type uint64;
         description "Number of timed out dynamic requests from this RADIUS client";
       }
       leaf aaa-radius-client-dyn-req-to-smd {
         type uint64;
         description "Number of requests from this RADIUS client delivered to application";
       }
       leaf aaa-radius-client-dyn-req-errors {
         type uint64;
         description "Number of errors during processing requests from this RADIUS client";
       }
       leaf aaa-radius-client-dyn-req-invalid-code {
         type uint64;
         description "Number of requests from this RADIUS client with invalid code";
       }
       leaf aaa-radius-client-dyn-req-invalid-authenticator {
         type uint64;
         description "Number of requests from this RADIUS client with invalid authenticator";
       }
       leaf aaa-radius-client-dyn-req-invalid-charging-id {
         type uint64;
         description "Number of requests from this RADIUS client with invalid or missing Charging Id";
       }
       leaf aaa-radius-client-dyn-req-rcm-error {
         type uint64;
         description "Number of session mapping errors during request processing for this RADIUS client";
       }
     }
   }
   grouping mobile-gateway-aaa-network-element-status-block {
     list aaa-network-element-status {
       leaf aaa-network-element-name {
         type string;
         description "Network-element name";
       }
       leaf aaa-fpc-pic {
         type string;
         description "FPC/PIC slot information";
       }
       leaf aaa-comment {
         type string;
         description "Comment";
       }
     }
   }
   grouping mobile-gateway-aaa-network-element-group-status-block {
     list aaa-network-element-group-status {
       leaf aaa-network-element-group-name {
         type string;
         description "Network-element-group name";
       }
       leaf aaa-network-element-group-broadcast {
         type string;
         description "Network-element-group broadcast";
       }
       leaf aaa-empty {
         type empty;
       }
       leaf aaa-fpc-pic {
         type string;
         description "FPC/PIC slot information";
       }
       leaf aaa-comment {
         type string;
         description "Comment";
       }
     }
   }
   grouping ggsn-pgw-charging-service-mode-block {
     leaf cg-profile-name {
       type string;
       description "Profile Name";
     }
     leaf mm-service-mode {
       type string;
       description "Service Mode Maintenance status for a profile";
     }
     leaf gateway-name {
       type string;
       description "Mobile Gateway Name";
     }
     container service-mode-status-brief-header {
       leaf dummy {
         type string;
         description "Dummy Tag";
       }
     }
     container gw-mm-display {
       leaf gateway-name {
         type string;
         description "Mobile Gateway Name";
       }
       leaf mm-service-mode {
         type string;
         description "Service Mode Maintenance status for a profile";
       }
     }
     list cg-cp-mm-brief {
       leaf cg-profile-name {
         type string;
         description "Profile Name";
       }
       leaf mm-service-mode {
         type string;
         description "Service Mode Maintenance status for a profile";
       }
     }
     list cg-tsp-mm-brief {
       leaf cg-profile-name {
         type string;
         description "Profile Name";
       }
       leaf mm-service-mode {
         type string;
         description "Service Mode Maintenance status for a profile";
       }
     }
     list cg-cp-mm-detail {
       container mm-service-mode-description {
         leaf mm-service-mode {
           type string;
           description "Service Mode Maintenance status for a profile";
         }
         leaf mm-service-mode-pending-mm-ack {
           type string;
         }
         leaf mm-service-mode-pending-ready-ack {
           type string;
         }
         list mobiled-session-description {
           leaf mobiled-client {
             type string;
             description "Mobiled Client - Could be RE or one of the SPICs";
           }
           leaf mobiled-peer-list {
             type string;
             description "Mobiled Peer List - Apps separated by commas";
           }
         }
         list mobiled-session-description2 {
           leaf mobiled-client {
             type string;
             description "Mobiled Client - Could be RE or one of the SPICs";
           }
           leaf mobiled-peer-list {
             type string;
             description "Mobiled Peer List - Apps separated by commas";
           }
         }
       }
       leaf cg-profile-name {
         type string;
         description "Profile Name";
       }
     }
     list cg-tsp-mm-detail {
       container mm-service-mode-description {
         leaf mm-service-mode {
           type string;
           description "Service Mode Maintenance status for a profile";
         }
         leaf mm-service-mode-pending-mm-ack {
           type string;
         }
         leaf mm-service-mode-pending-ready-ack {
           type string;
         }
         list mobiled-session-description {
           leaf mobiled-client {
             type string;
             description "Mobiled Client - Could be RE or one of the SPICs";
           }
           leaf mobiled-peer-list {
             type string;
             description "Mobiled Peer List - Apps separated by commas";
           }
         }
         list mobiled-session-description2 {
           leaf mobiled-client {
             type string;
             description "Mobiled Client - Could be RE or one of the SPICs";
           }
           leaf mobiled-peer-list {
             type string;
             description "Mobiled Peer List - Apps separated by commas";
           }
         }
       }
       leaf cg-profile-name {
         type string;
         description "Profile Name";
       }
     }
   }
   grouping gtpc-statistics-block {
     leaf gw-name {
       type string;
       description "Gateway name";
     }
     list gtp-global-pkt-stats {
       leaf drop-counter {
         type int32;
         description "Drop Counter";
       }
       leaf pkt-alloc-fail {
         type int32;
         description "Pkt Alloc Fail";
       }
       leaf pkt-send-fail {
         type int32;
         description "Pkt Send Fail";
       }
       leaf ip-ver-error-rx {
         type int32;
         description "Ip Ver Error Rx";
       }
       leaf ip-proto-error-rx {
         type int32;
         description "Ip Proto Error Rx";
       }
       leaf gtp-port-error-rx {
         type int32;
         description "Gtp Port Error Rx";
       }
       leaf gtp-unknown-ver-rx {
         type int32;
         description "Gtp Uknown Version Rx";
       }
       leaf pkt-len-error-rx {
         type int32;
         description "Pkt Len Error Rx";
       }
       leaf unknown-msg-rx {
         type int32;
         description "Unknown Msg Rx";
       }
     }
     list gtpv0-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv0v1-msg-stats {
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf create-pdp-req-rx {
           type int32;
           description "Create PDP Req Rx";
         }
         leaf create-pdp-req-tx {
           type int32;
           description "Create PDP Req Tx";
         }
         leaf create-pdp-rsp-rx {
           type int32;
           description "Create PDP Rsp Rx";
         }
         leaf create-pdp-rsp-tx {
           type int32;
           description "Create PDP Rsp Tx";
         }
         leaf update-pdp-req-rx {
           type int32;
           description "Update PDP Req Rx";
         }
         leaf update-pdp-req-tx {
           type int32;
           description "Update PDP Req Tx";
         }
         leaf update-pdp-rsp-rx {
           type int32;
           description "Update PDP Rsp Rx";
         }
         leaf update-pdp-rsp-tx {
           type int32;
           description "Update PDP Rsp Tx";
         }
         leaf delete-pdp-req-rx {
           type int32;
           description "Delete PDP Req Rx";
         }
         leaf delete-pdp-req-tx {
           type int32;
           description "Delete PDP Req Tx";
         }
         leaf delete-pdp-rsp-rx {
           type int32;
           description "Delete PDP Rsp Rx";
         }
         leaf delete-pdp-rsp-tx {
           type int32;
           description "Delete PDP Rsp Tx";
         }
         leaf init-pdp-req-rx {
           type int32;
           description "Initiate PDP Req Rx";
         }
         leaf init-pdp-req-tx {
           type int32;
           description "Initiate PDP Req Tx";
         }
         leaf init-pdp-rsp-rx {
           type int32;
           description "Initiate PDP Rsp Rx";
         }
         leaf init-pdp-rsp-tx {
           type int32;
           description "Initiate PDP Rsp Tx";
         }
         leaf gtp-error-ind-rx {
           type int32;
           description "Gtp Error Indication Rx";
         }
         leaf gtp-error-ind-tx {
           type int32;
           description "Gtp Error Indication Tx";
         }
       }
       container gtpv0-cause-code-stats {
         leaf cause-req-accepted-rx {
           type int32;
           description "Cause Code Request Accepted Rx";
         }
         leaf cause-req-accepted-tx {
           type int32;
           description "Cause Code Request Accepted Tx";
         }
         leaf cause-non-exist-rx {
           type int32;
           description "Cause Code Non Existant Rx";
         }
         leaf cause-non-exist-tx {
           type int32;
           description "Cause Code Non Existant Tx";
         }
         leaf cause-invalid-msg-fmt-rx {
           type int32;
           description "Cause Code Invalid Message Format Rx";
         }
         leaf cause-invalid-msg-fmt-tx {
           type int32;
           description "Cause Code Invalid Message Format Tx";
         }
         leaf cause-imsi-not-known-rx {
           type int32;
           description "Cause Code IMSI Not Known Rx";
         }
         leaf cause-imsi-not-known-tx {
           type int32;
           description "Cause Code IMSI Not Known Tx";
         }
         leaf cause-ms-gprs-detach-rx {
           type int32;
           description "Cause Code MS GPRS Detached Rx";
         }
         leaf cause-ms-gprs-detach-tx {
           type int32;
           description "Cause Code MS GPRS Detached Tx";
         }
         leaf cause-ms-not-gprs-resp-rx {
           type int32;
           description "Cause Code MS Not GPRS Response Rx";
         }
         leaf cause-ms-not-gprs-resp-tx {
           type int32;
           description "Cause Code MS Not GPRS Response Tx";
         }
         leaf cause-ms-refuses-rx {
           type int32;
           description "Cause Code MS Refuses Rx";
         }
         leaf cause-ms-refuses-tx {
           type int32;
           description "Cause Code MS Refuses Tx";
         }
         leaf cause-ver-not-supported-rx {
           type int32;
           description "Cause Code Version Not Supported Rx";
         }
         leaf cause-ver-not-supported-tx {
           type int32;
           description "Cause Code Version Not Supported Tx";
         }
         leaf cause-no-resp-rx {
           type int32;
           description "Cause Code No Response Rx";
         }
         leaf cause-no-resp-tx {
           type int32;
           description "Cause Code No Response Tx";
         }
         leaf cause-serv-not-supp-rx {
           type int32;
           description "Cause Code Service Not Supported Rx";
         }
         leaf cause-serv-not-supp-tx {
           type int32;
           description "Cause Code Service Not Supported Tx";
         }
         leaf cause-man-ie-incrt-rx {
           type int32;
           description "Cause Code Mandatory IE Incorrect Rx";
         }
         leaf cause-man-ie-incrt-tx {
           type int32;
           description "Cause Code Mandatory IE Incorrect Tx";
         }
         leaf cause-man-ie-miss-rx {
           type int32;
           description "Cause Code Mandatory IE Missing Rx";
         }
         leaf cause-man-ie-miss-tx {
           type int32;
           description "Cause Code Mandatory IE Missing Tx";
         }
         leaf cause-opt-ie-incrt-rx {
           type int32;
           description "Cause Code Optional IE Incorrect Rx";
         }
         leaf cause-opt-ie-incrt-tx {
           type int32;
           description "Cause Code Optional IE Incorrect Tx";
         }
         leaf cause-sys-fail-rx {
           type int32;
           description "Cause Code System Failure Rx";
         }
         leaf cause-sys-fail-tx {
           type int32;
           description "Cause Code System Failure Tx";
         }
         leaf cause-roam-restrict-rx {
           type int32;
           description "Cause Code Roaming Restricted Rx";
         }
         leaf cause-roam-restrict-tx {
           type int32;
           description "Cause Code Roaming Restricted Tx";
         }
         leaf cause-ptmsi-sig-mismatch-rx {
           type int32;
           description "Cause Code PTMSI Signature Mismatch Rx";
         }
         leaf cause-ptmsi-sig-mismatch-tx {
           type int32;
           description "Cause Code PTMSI Signature Mismatch Tx";
         }
         leaf cause-gprs-conn-supp-rx {
           type int32;
           description "Cause Code GPRS Connection not Supported Rx";
         }
         leaf cause-gprs-conn-supp-tx {
           type int32;
           description "Cause Code GPRS Connection not Supported Tx";
         }
         leaf cause-auth-fail-rx {
           type int32;
           description "Cause Code Auth Failure Rx";
         }
         leaf cause-auth-fail-tx {
           type int32;
           description "Cause Code Auth Failure Tx";
         }
         leaf cause-user-auth-fail-rx {
           type int32;
           description "Cause Code User Auth Failure Rx";
         }
         leaf cause-user-auth-fail-tx {
           type int32;
           description "Cause Code User Auth Failure Tx";
         }
       }
     }
     list gtpv1-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv0v1-msg-stats {
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf create-pdp-req-rx {
           type int32;
           description "Create PDP Req Rx";
         }
         leaf create-pdp-req-tx {
           type int32;
           description "Create PDP Req Tx";
         }
         leaf create-pdp-rsp-rx {
           type int32;
           description "Create PDP Rsp Rx";
         }
         leaf create-pdp-rsp-tx {
           type int32;
           description "Create PDP Rsp Tx";
         }
         leaf update-pdp-req-rx {
           type int32;
           description "Update PDP Req Rx";
         }
         leaf update-pdp-req-tx {
           type int32;
           description "Update PDP Req Tx";
         }
         leaf update-pdp-rsp-rx {
           type int32;
           description "Update PDP Rsp Rx";
         }
         leaf update-pdp-rsp-tx {
           type int32;
           description "Update PDP Rsp Tx";
         }
         leaf delete-pdp-req-rx {
           type int32;
           description "Delete PDP Req Rx";
         }
         leaf delete-pdp-req-tx {
           type int32;
           description "Delete PDP Req Tx";
         }
         leaf delete-pdp-rsp-rx {
           type int32;
           description "Delete PDP Rsp Rx";
         }
         leaf delete-pdp-rsp-tx {
           type int32;
           description "Delete PDP Rsp Tx";
         }
         leaf init-pdp-req-rx {
           type int32;
           description "Initiate PDP Req Rx";
         }
         leaf init-pdp-req-tx {
           type int32;
           description "Initiate PDP Req Tx";
         }
         leaf init-pdp-rsp-rx {
           type int32;
           description "Initiate PDP Rsp Rx";
         }
         leaf init-pdp-rsp-tx {
           type int32;
           description "Initiate PDP Rsp Tx";
         }
         leaf gtp-error-ind-rx {
           type int32;
           description "Gtp Error Indication Rx";
         }
         leaf gtp-error-ind-tx {
           type int32;
           description "Gtp Error Indication Tx";
         }
       }
       container gtp-v2v1-stats {
         leaf gtpv1-end-mark-rx {
           type int32;
           description "Gtpv1 End Marker Rx";
         }
         leaf gtpv1-end-mark-tx {
           type int32;
           description "Gtpv1 End Marker Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf gtp-error-ind-rx {
           type int32;
           description "Gtp Error Indication Rx";
         }
         leaf gtp-error-ind-tx {
           type int32;
           description "Gtp Error Indication Tx";
         }
       }
       container gtpv0-cause-code-stats {
         leaf cause-req-accepted-rx {
           type int32;
           description "Cause Code Request Accepted Rx";
         }
         leaf cause-req-accepted-tx {
           type int32;
           description "Cause Code Request Accepted Tx";
         }
         leaf cause-non-exist-rx {
           type int32;
           description "Cause Code Non Existant Rx";
         }
         leaf cause-non-exist-tx {
           type int32;
           description "Cause Code Non Existant Tx";
         }
         leaf cause-invalid-msg-fmt-rx {
           type int32;
           description "Cause Code Invalid Message Format Rx";
         }
         leaf cause-invalid-msg-fmt-tx {
           type int32;
           description "Cause Code Invalid Message Format Tx";
         }
         leaf cause-imsi-not-known-rx {
           type int32;
           description "Cause Code IMSI Not Known Rx";
         }
         leaf cause-imsi-not-known-tx {
           type int32;
           description "Cause Code IMSI Not Known Tx";
         }
         leaf cause-ms-gprs-detach-rx {
           type int32;
           description "Cause Code MS GPRS Detached Rx";
         }
         leaf cause-ms-gprs-detach-tx {
           type int32;
           description "Cause Code MS GPRS Detached Tx";
         }
         leaf cause-ms-not-gprs-resp-rx {
           type int32;
           description "Cause Code MS Not GPRS Response Rx";
         }
         leaf cause-ms-not-gprs-resp-tx {
           type int32;
           description "Cause Code MS Not GPRS Response Tx";
         }
         leaf cause-ms-refuses-rx {
           type int32;
           description "Cause Code MS Refuses Rx";
         }
         leaf cause-ms-refuses-tx {
           type int32;
           description "Cause Code MS Refuses Tx";
         }
         leaf cause-ver-not-supported-rx {
           type int32;
           description "Cause Code Version Not Supported Rx";
         }
         leaf cause-ver-not-supported-tx {
           type int32;
           description "Cause Code Version Not Supported Tx";
         }
         leaf cause-no-resp-rx {
           type int32;
           description "Cause Code No Response Rx";
         }
         leaf cause-no-resp-tx {
           type int32;
           description "Cause Code No Response Tx";
         }
         leaf cause-serv-not-supp-rx {
           type int32;
           description "Cause Code Service Not Supported Rx";
         }
         leaf cause-serv-not-supp-tx {
           type int32;
           description "Cause Code Service Not Supported Tx";
         }
         leaf cause-man-ie-incrt-rx {
           type int32;
           description "Cause Code Mandatory IE Incorrect Rx";
         }
         leaf cause-man-ie-incrt-tx {
           type int32;
           description "Cause Code Mandatory IE Incorrect Tx";
         }
         leaf cause-man-ie-miss-rx {
           type int32;
           description "Cause Code Mandatory IE Missing Rx";
         }
         leaf cause-man-ie-miss-tx {
           type int32;
           description "Cause Code Mandatory IE Missing Tx";
         }
         leaf cause-opt-ie-incrt-rx {
           type int32;
           description "Cause Code Optional IE Incorrect Rx";
         }
         leaf cause-opt-ie-incrt-tx {
           type int32;
           description "Cause Code Optional IE Incorrect Tx";
         }
         leaf cause-sys-fail-rx {
           type int32;
           description "Cause Code System Failure Rx";
         }
         leaf cause-sys-fail-tx {
           type int32;
           description "Cause Code System Failure Tx";
         }
         leaf cause-roam-restrict-rx {
           type int32;
           description "Cause Code Roaming Restricted Rx";
         }
         leaf cause-roam-restrict-tx {
           type int32;
           description "Cause Code Roaming Restricted Tx";
         }
         leaf cause-ptmsi-sig-mismatch-rx {
           type int32;
           description "Cause Code PTMSI Signature Mismatch Rx";
         }
         leaf cause-ptmsi-sig-mismatch-tx {
           type int32;
           description "Cause Code PTMSI Signature Mismatch Tx";
         }
         leaf cause-gprs-conn-supp-rx {
           type int32;
           description "Cause Code GPRS Connection not Supported Rx";
         }
         leaf cause-gprs-conn-supp-tx {
           type int32;
           description "Cause Code GPRS Connection not Supported Tx";
         }
         leaf cause-auth-fail-rx {
           type int32;
           description "Cause Code Auth Failure Rx";
         }
         leaf cause-auth-fail-tx {
           type int32;
           description "Cause Code Auth Failure Tx";
         }
         leaf cause-user-auth-fail-rx {
           type int32;
           description "Cause Code User Auth Failure Rx";
         }
         leaf cause-user-auth-fail-tx {
           type int32;
           description "Cause Code User Auth Failure Tx";
         }
       }
       container gtpv1-cause-code-stats {
         leaf cause-ctx-not-found-rx {
           type int32;
           description "Cause Code Context Not Found Rx";
         }
         leaf cause-ctx-not-found-tx {
           type int32;
           description "Cause Code Context Not Found tx";
         }
         leaf cause-dyn-pdp-addr-rx {
           type int32;
           description "Cause Code Dynamic PDP Address Rx";
         }
         leaf cause-dyn-pdp-addr-tx {
           type int32;
           description "Cause Code Dynamic PDP Address tx";
         }
         leaf cause-no-mem-rx {
           type int32;
           description "Cause Code No Memory Rx";
         }
         leaf cause-no-mem-tx {
           type int32;
           description "Cause Code No Memory tx";
         }
         leaf cause-reloc-fail-rx {
           type int32;
           description "Cause Code Relocation Failed Rx";
         }
         leaf cause-reloc-fail-tx {
           type int32;
           description "Cause Code Relocation Failed tx";
         }
         leaf cause-unk-man-exthdr-rx {
           type int32;
           description "Cause Code Unknown Extension Header Rx";
         }
         leaf cause-unk-man-exthdr-tx {
           type int32;
           description "Cause Code Unknown Extension Header tx";
         }
         leaf cause-semantic-tft-err1-rx {
           type int32;
           description "Cause Code Symantic TFT Error 1 Rx";
         }
         leaf cause-semantic-tft-err1-tx {
           type int32;
           description "Cause Code Symantic TFT Error 1 tx";
         }
         leaf cause-syn-tft-err2-rx {
           type int32;
           description "Cause Code Syntactic TFT Error 2 Rx";
         }
         leaf cause-syn-tft-err2-tx {
           type int32;
           description "Cause Code Syntactic TFT Error 2 tx";
         }
         leaf cause-semantic-pkt-fltr-err1-rx {
           type int32;
           description "Cause Code Semantic Packet Filter Error 1 Rx";
         }
         leaf cause-semantic-pkt-fltr-err1-tx {
           type int32;
           description "Cause Code Semantic Packet Filter Error 1 tx";
         }
         leaf cause-syn-pkt-fltr-err2-rx {
           type int32;
           description "Cause Code Syntactic Packet Filter Error 2 Rx";
         }
         leaf cause-syn-pkt-fltr-err2-tx {
           type int32;
           description "Cause Code Syntactic Packet Filter Error 2 tx";
         }
         leaf cause-miss-unk-apn-rx {
           type int32;
           description "Cause Code Missing Unknown APN Rx";
         }
         leaf cause-miss-unk-apn-tx {
           type int32;
           description "Cause Code Missing Unknown APN tx";
         }
         leaf cause-unk-pdp-addr-rx {
           type int32;
           description "Cause Code Unknown PDP Address Rx";
         }
         leaf cause-unk-pdp-addr-tx {
           type int32;
           description "Cause Code Unknown PDP Address tx";
         }
         leaf cause-no-tft-ctx-exist-rx {
           type int32;
           description "Cause Code No TFT Context Exists Rx";
         }
         leaf cause-no-tft-ctx-exist-tx {
           type int32;
           description "Cause Code No TFT Context Exists tx";
         }
       }
     }
     container gtpv2-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv2-msg-stats {
         leaf gtpv2-cause-req-accept-rx {
           type int32;
           description "GTPv2 Cause Code Request Accepted Rx";
         }
         leaf gtpv2-cause-accept-part-rx {
           type int32;
           description "GTPv2 Cause Code Accept Partial Rx";
         }
         leaf gtpv2-cause-new-pt-npref-rx {
           type int32;
           description "GTPv2 Cause Code New PDN Type Due to Network Preference Rx";
         }
         leaf gtpv2-cause-new-pt-si-addr-br-rx {
           type int32;
           description "GTPv2 Cause Code New PDN Type Due To Single Address Bearer Rx";
         }
         leaf gtpv2-cause-ctx-not-fnd-rx {
           type int32;
           description "GTPv2 Cause Code Context Not Found Rx";
         }
         leaf gtpv2-cause-inv-msg-fmt-rx {
           type int32;
           description "GTPv2 Cause Code Invalid Message Format Rx";
         }
         leaf gtpv2-cause-ver-not-supp-rx {
           type int32;
           description "GTPv2 Cause Code Version Not Supported Rx";
         }
         leaf gtpv2-cause-inv-len-rx {
           type int32;
           description "GTPv2 Cause Code Invalid Length Rx";
         }
         leaf gtpv2-cause-serv-not-supp-rx {
           type int32;
           description "GTPv2 Cause Code Service Not Supported Rx";
         }
         leaf gtpv2-cause-man-ie-incorr-rx {
           type int32;
           description "GTPv2 Cause Code Mandatory IE Incorrect Rx";
         }
         leaf gtpv2-cause-man-ie-miss-rx {
           type int32;
           description "GTPv2 Cause Code Mandatory IE Missing Rx";
         }
         leaf gtpv2-cause-opt-ie-incorr-rx {
           type int32;
           description "GTPv2 Cause Code Optional IE Incorrect Rx";
         }
         leaf gtpv2-cause-sys-fail-rx {
           type int32;
           description "GTPv2 Cause Code System Failure Rx";
         }
         leaf gtpv2-cause-no-res-rx {
           type int32;
           description "GTPv2 Cause Code No Resources Rx";
         }
         leaf gtpv2-cause-tft-semantic-err-rx {
           type int32;
           description "GTPv2 Cause Code TFT Semantic Error Rx";
         }
         leaf gtpv2-cause-tft-syn-err-rx {
           type int32;
           description "GTPv2 Cause Code TFT Syntactic Error Rx";
         }
         leaf gtpv2-cause-pkt-fltr-semantic-err-rx {
           type int32;
           description "GTPv2 Cause Code Packet Filter Semantic Error Rx";
         }
         leaf gtpv2-cause-pkt-fltr-syn-err-rx {
           type int32;
           description "GTPv2 Cause Code Packet Filter Syntatctic Error Rx";
         }
         leaf gtpv2-cause-miss-unkown-apn-rx {
           type int32;
           description "GTPv2 Cause Code Missing or Unknown APN Rx";
         }
         leaf gtpv2-cause-unexp-repeat-ie-rx {
           type int32;
           description "GTPv2 Cause Code Unexpected Repeated IE Rx";
         }
         leaf gtpv2-cause-gre-key-not-fnd-rx {
           type int32;
           description "GTPv2 Cause Code GRE Key Not Found Rx";
         }
         leaf gtpv2-cause-reloc-fail-rx {
           type int32;
           description "GTPv2 Cause Code Reallocation Failure Rx";
         }
         leaf gtpv2-cause-denied-in-rat-rx {
           type int32;
           description "GTPv2 Cause Code Denied In RAT Rx";
         }
         leaf gtpv2-cause-pt-not-supp-rx {
           type int32;
           description "GTPv2 Cause Code PDN Type Not Supported Rx";
         }
         leaf gtpv2-cause-all-dyn-addr-occ-rx {
           type int32;
           description "GTPv2 Cause Code All Dynamic Addresses Occupied Rx";
         }
         leaf gtpv2-cause-no-tft-ue-ctx-exist-rx {
           type int32;
           description "GTPv2 Cause Code UE Context Without TFT Activation Rx";
         }
         leaf gtpv2-cause-proto-not-supp-rx {
           type int32;
           description "GTPv2 Cause Code Protocol Not Supported Rx";
         }
         leaf gtpv2-cause-ue-not-resp-rx {
           type int32;
           description "GTPv2 Cause Code UE Not Responding Rx";
         }
         leaf gtpv2-cause-ue-refuses-rx {
           type int32;
           description "GTPv2 Cause Code UE Refuses Rx";
         }
         leaf gtpv2-cause-serv-denied-rx {
           type int32;
           description "GTPv2 Cause Code Service Denied Rx";
         }
         leaf gtpv2-cause-unable-page-ue-rx {
           type int32;
           description "GTPv2 Cause Code Unable To Page UE Rx";
         }
         leaf gtpv2-cause-no-mem-rx {
           type int32;
           description "GTPv2 Cause Code No Memory Rx";
         }
         leaf gtpv2-cause-user-auth-fail-rx {
           type int32;
           description "GTPv2 Cause Code User Auth Failure Rx";
         }
         leaf gtpv2-cause-apn-access-denied-rx {
           type int32;
           description "GTPv2 Cause Code APN Access Denied Rx";
         }
         leaf gtpv2-cause-req-rej-rx {
           type int32;
           description "GTPv2 Cause Code Request Rejected Rx";
         }
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf s11-piggyback-rx {
           type int32;
           description "S11 piggyback Rx";
         }
         leaf s11-piggyback-tx {
           type int32;
           description "S11 piggyback Tx";
         }
         leaf s4-piggyback-rx {
           type int32;
           description "S4 piggyback Rx";
         }
         leaf s4-piggyback-tx {
           type int32;
           description "S4 piggyback Tx";
         }
         leaf s5-piggyback-rx {
           type int32;
           description "S5 piggyback Rx";
         }
         leaf s5-piggyback-tx {
           type int32;
           description "S5 piggyback Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf gtpv2-create-sess-req-rx {
           type int32;
           description "Gtpv2 Create Session Req Rx";
         }
         leaf gtpv2-create-sess-req-tx {
           type int32;
           description "Gtpv2 Create Session Req Tx";
         }
         leaf gtpv2-create-sess-rsp-rx {
           type int32;
           description "Gtpv2 Create Session Rsp Rx";
         }
         leaf gtpv2-create-sess-rsp-tx {
           type int32;
           description "Gtpv2 Create Session Rsp Tx";
         }
         leaf gtpv2-modify-bearer-req-rx {
           type int32;
           description "Gtpv2 Modify Bearer Req Rx";
         }
         leaf gtpv2-modify-bearer-req-tx {
           type int32;
           description "Gtpv2 Modify Bearer Req Tx";
         }
         leaf gtpv2-modify-bearer-rsp-rx {
           type int32;
           description "Gtpv2 Modify Bearer Rsp Rx";
         }
         leaf gtpv2-modify-bearer-rsp-tx {
           type int32;
           description "Gtpv2 Modify Bearer Rsp Tx";
         }
         leaf gtpv2-delete-sess-req-rx {
           type int32;
           description "Gtpv2 Delete Session Req Rx";
         }
         leaf gtpv2-delete-sess-req-tx {
           type int32;
           description "Gtpv2 Delete Session Req Tx";
         }
         leaf gtpv2-delete-sess-rsp-rx {
           type int32;
           description "Gtpv2 Delete Session Rsp Rx";
         }
         leaf gtpv2-delete-sess-rsp-tx {
           type int32;
           description "Gtpv2 Delete Session Rsp Tx";
         }
         leaf gtpv2-create-bearer-req-rx {
           type int32;
           description "Gtpv2 Create Bearer Req Rx";
         }
         leaf gtpv2-create-bearer-req-tx {
           type int32;
           description "Gtpv2 Create Bearer Req Tx";
         }
         leaf gtpv2-create-bearer-rsp-rx {
           type int32;
           description "Gtpv2 Create Bearer Rsp Rx";
         }
         leaf gtpv2-create-bearer-rsp-tx {
           type int32;
           description "Gtpv2 Create Bearer Rsp Tx";
         }
         leaf gtpv2-update-bearer-req-rx {
           type int32;
           description "Gtpv2 Update Bearer Req Rx";
         }
         leaf gtpv2-update-bearer-req-tx {
           type int32;
           description "Gtpv2 Update Bearer Req Tx";
         }
         leaf gtpv2-update-bearer-rsp-rx {
           type int32;
           description "Gtpv2 Update Bearer Rsp Rx";
         }
         leaf gtpv2-update-bearer-rsp-tx {
           type int32;
           description "Gtpv2 Update Bearer Rsp Tx";
         }
         leaf gtpv2-delete-bearer-req-rx {
           type int32;
           description "Gtpv2 Delete Bearer Req Rx";
         }
         leaf gtpv2-delete-bearer-req-tx {
           type int32;
           description "Gtpv2 Delete Bearer Req Tx";
         }
         leaf gtpv2-delete-bearer-rsp-rx {
           type int32;
           description "Gtpv2 Delete Bearer Rsp Rx";
         }
         leaf gtpv2-delete-bearer-rsp-tx {
           type int32;
           description "Gtpv2 Delete Bearer Rsp Tx";
         }
         leaf gtpv2-delete-pdn-conn-set-req-rx {
           type int32;
           description "Gtpv2 Delete PDN connection set req rx";
         }
         leaf gtpv2-delete-pdn-conn-set-req-tx {
           type int32;
           description "Gtpv2 Delete PDN connection set req tx";
         }
         leaf gtpv2-delete-pdn-conn-set-rsp-rx {
           type int32;
           description "Gtpv2 Delete PDN connection set rsp rx";
         }
         leaf gtpv2-delete-pdn-conn-set-rsp-tx {
           type int32;
           description "Gtpv2 Delete PDN connection set rsp tx";
         }
         leaf gtpv2-update-pdn-conn-set-req-rx {
           type int32;
           description "Gtpv2 Update PDN connection set req rx";
         }
         leaf gtpv2-update-pdn-conn-set-req-tx {
           type int32;
           description "Gtpv2 Update PDN connection set req tx";
         }
         leaf gtpv2-update-pdn-conn-set-rsp-rx {
           type int32;
           description "Gtpv2 Update PDN connection set rsp rx";
         }
         leaf gtpv2-update-pdn-conn-set-rsp-tx {
           type int32;
           description "Gtpv2 Update PDN connection set rsp tx";
         }
         leaf gtpv2-modify-bearer-cmd-rx {
           type int32;
           description "Gtpv2 Modify bearer command rx";
         }
         leaf gtpv2-modify-bearer-cmd-tx {
           type int32;
           description "Gtpv2 Modify bearer command tx";
         }
         leaf gtpv2-modify-bearer-fail-ind-rx {
           type int32;
           description "Gtpv2 Modify bearer failure indication rx";
         }
         leaf gtpv2-modify-bearer-fail-ind-tx {
           type int32;
           description "Gtpv2 Modify bearer failure indication tx";
         }
         leaf gtpv2-delete-bearer-cmd-rx {
           type int32;
           description "Gtpv2 Delete bearer command rx";
         }
         leaf gtpv2-delete-bearer-cmd-tx {
           type int32;
           description "Gtpv2 Delete bearer command tx";
         }
         leaf gtpv2-delete-bearer-fail-ind-rx {
           type int32;
           description "Gtpv2 Delete bearer failure indication rx";
         }
         leaf gtpv2-delete-bearer-fail-ind-tx {
           type int32;
           description "Gtpv2 Delete bearer failure indication tx";
         }
         leaf gtpv2-bearer-resource-cmd-rx {
           type int32;
           description "Gtpv2 Bearer resource command rx";
         }
         leaf gtpv2-bearer-resource-cmd-tx {
           type int32;
           description "Gtpv2 Bearer resource command tx";
         }
         leaf gtpv2-bearer-resource-fail-ind-rx {
           type int32;
           description "Gtpv2 Bearer resource failure indication rx";
         }
         leaf gtpv2-bearer-resource-fail-ind-tx {
           type int32;
           description "Gtpv2 Bearer resource failure indication tx";
         }
         leaf gtpv2-chg-notif-req-rx {
           type int32;
           description "Gtpv2 Change notification req rx";
         }
         leaf gtpv2-chg-notif-req-tx {
           type int32;
           description "Gtpv2 Change notification req tx";
         }
         leaf gtpv2-chg-notif-rsp-rx {
           type int32;
           description "Gtpv2 Change notification rsp rx";
         }
         leaf gtpv2-chg-notif-rsp-tx {
           type int32;
           description "Gtpv2 Change notification rsp tx";
         }
         leaf gtpv2-release-access-bearer-req-rx {
           type int32;
           description "Gtpv2 Release Access Bearer Req Rx";
         }
         leaf gtpv2-release-access-bearer-req-tx {
           type int32;
           description "Gtpv2 Release Access Bearer Req Tx";
         }
         leaf gtpv2-release-access-bearer-rsp-rx {
           type int32;
           description "Gtpv2 Release Access Bearer Resp Rx";
         }
         leaf gtpv2-release-access-bearer-rsp-tx {
           type int32;
           description "Gtpv2 Release Access Bearer Resp Tx";
         }
         leaf gtpv2-suspend-notification-rx {
           type int32;
           description "Gtpv2 suspend notification Rx";
         }
         leaf gtpv2-suspend-notification-tx {
           type int32;
           description "Gtpv2 suspend notification Tx";
         }
         leaf gtpv2-suspend-acknowledge-rx {
           type int32;
           description "Gtpv2 suspend acknowledge Rx";
         }
         leaf gtpv2-suspend-acknowledge-tx {
           type int32;
           description "Gtpv2 suspend acknowledge Tx";
         }
         leaf gtpv2-resume-notification-rx {
           type int32;
           description "Gtpv2 resume notification Rx";
         }
         leaf gtpv2-resume-notification-tx {
           type int32;
           description "Gtpv2 resume notification Tx";
         }
         leaf gtpv2-resume-acknowledge-rx {
           type int32;
           description "Gtpv2 resume acknowledge Rx";
         }
         leaf gtpv2-resume-acknowledge-tx {
           type int32;
           description "Gtpv2 resume acknowledge Tx";
         }
         leaf gtpv2-create-indirect-data-forward-tunnel-req-rx {
           type int32;
           description "Gtpv2 Create Indirect Data Forward Tunnel Req Rx";
         }
         leaf gtpv2-create-indirect-data-forward-tunnel-req-tx {
           type int32;
           description "Gtpv2 Create Indirect Data Forward Tunnel Req Tx";
         }
         leaf gtpv2-create-indirect-data-forward-tunnel-resp-rx {
           type int32;
           description "Gtpv2 Create Indirect Data Forward Tunnel Resp Rx";
         }
         leaf gtpv2-create-indirect-data-forward-tunnel-resp-tx {
           type int32;
           description "Gtpv2 Create Indirect Data Forward Tunnel Resp Tx";
         }
         leaf gtpv2-delete-indirect-data-forward-tunnel-req-rx {
           type int32;
           description "Gtpv2 Delete Indirect Data Forward Tunnel Req Rx";
         }
         leaf gtpv2-delete-indirect-data-forward-tunnel-req-tx {
           type int32;
           description "Gtpv2 Delete Indirect Data Forward Tunnel Req Tx";
         }
         leaf gtpv2-delete-indirect-data-forward-tunnel-resp-rx {
           type int32;
           description "Gtpv2 Delete Indirect Data Forward Tunnel Resp Rx";
         }
         leaf gtpv2-delete-indirect-data-forward-tunnel-resp-tx {
           type int32;
           description "Gtpv2 Delete Indirect Data Forward Tunnel Resp Tx";
         }
         leaf gtpv2-downlink-data-notif-rx {
           type int32;
           description "Gtpv2 Downlink data notification rx";
         }
         leaf gtpv2-downlink-data-notif-tx {
           type int32;
           description "Gtpv2 Downlink data notification tx";
         }
         leaf gtpv2-downlink-data-notif-ack-rx {
           type int32;
           description "Gtpv2 Downlink data notification ack rx";
         }
         leaf gtpv2-downlink-data-notif-ack-tx {
           type int32;
           description "Gtpv2 Downlink data notification ack tx";
         }
         leaf gtpv2-downlink-data-notif-fail-rx {
           type int32;
           description "Gtpv2 Downlink data notification fail rx";
         }
         leaf gtpv2-downlink-data-notif-fail-tx {
           type int32;
           description "Gtpv2 Downlink data notification fail tx";
         }
         leaf gtpv2-stop-paging-ind-rx {
           type int32;
           description "Gtpv2 Stop Paging Indication rx";
         }
         leaf gtpv2-stop-paging-ind-tx {
           type int32;
           description "Gtpv2 Stop Paging Indication tx";
         }
         leaf gtpv2-cause-req-accept-tx {
           type int32;
           description "GTPv2 Cause Code Request Accepted tx";
         }
         leaf gtpv2-cause-accept-part-tx {
           type int32;
           description "GTPv2 Cause Code Accept Partial tx";
         }
         leaf gtpv2-cause-new-pt-npref-tx {
           type int32;
           description "GTPv2 Cause Code New PDN Type Due to Network Preference tx";
         }
         leaf gtpv2-cause-new-pt-si-addr-br-tx {
           type int32;
           description "GTPv2 Cause Code New PDN Type Due To Single Address Bearer tx";
         }
         leaf gtpv2-cause-local-detach-rx {
           type int32;
           description "GTPv2 Cause Code Local Detach Rx";
         }
         leaf gtpv2-cause-local-detach-tx {
           type int32;
           description "GTPv2 Cause Code Local Detach Tx";
         }
         leaf gtpv2-cause-complete-detach-rx {
           type int32;
           description "GTPv2 Cause Code Complete Detach Rx";
         }
         leaf gtpv2-cause-complete-detach-tx {
           type int32;
           description "GTPv2 Cause Code Complete Detach Tx";
         }
         leaf gtpv2-cause-rat-changed-3gpp-to-non-3gpp-rx {
           type int32;
           description "GTPv2 Cause Code RAT Changed 3GPP to Non 3GPP Rx";
         }
         leaf gtpv2-cause-rat-changed-3gpp-to-non-3gpp-tx {
           type int32;
           description "GTPv2 Cause Code RAT Changed 3GPP to Non 3GPP Tx";
         }
         leaf gtpv2-cause-isr-deactivated-rx {
           type int32;
           description "GTPv2 Cause Code ISR Deactivated Rx";
         }
         leaf gtpv2-cause-isr-deactivated-tx {
           type int32;
           description "GTPv2 Cause Code ISR Deactivated Tx";
         }
         leaf gtpv2-cause-err-ind-from-rnc-enodeb-rx {
           type int32;
           description "GTPv2 Cause Code Err Ind From RNC Enodeb Rx";
         }
         leaf gtpv2-cause-err-ind-from-rnc-enodeb-tx {
           type int32;
           description "GTPv2 Cause Code Err Ind From RNC Enodeb Tx";
         }
         leaf gtpv2-cause-ctx-not-fnd-tx {
           type int32;
           description "GTPv2 Cause Code Context Not Found tx";
         }
         leaf gtpv2-cause-inv-msg-fmt-tx {
           type int32;
           description "GTPv2 Cause Code Invalid Message Format tx";
         }
         leaf gtpv2-cause-ver-not-supp-tx {
           type int32;
           description "GTPv2 Cause Code Version Not Supported tx";
         }
         leaf gtpv2-cause-inv-len-tx {
           type int32;
           description "GTPv2 Cause Code Invalid Length tx";
         }
         leaf gtpv2-cause-serv-not-supp-tx {
           type int32;
           description "GTPv2 Cause Code Service Not Supported tx";
         }
         leaf gtpv2-cause-man-ie-incorr-tx {
           type int32;
           description "GTPv2 Cause Code Mandatory IE Incorrect tx";
         }
         leaf gtpv2-cause-man-ie-miss-tx {
           type int32;
           description "GTPv2 Cause Code Mandatory IE Missing tx";
         }
         leaf gtpv2-cause-opt-ie-incorr-tx {
           type int32;
           description "GTPv2 Cause Code Optional IE Incorrect tx";
         }
         leaf gtpv2-cause-sys-fail-tx {
           type int32;
           description "GTPv2 Cause Code System Failure tx";
         }
         leaf gtpv2-cause-no-res-tx {
           type int32;
           description "GTPv2 Cause Code No Resources tx";
         }
         leaf gtpv2-cause-tft-semantic-err-tx {
           type int32;
           description "GTPv2 Cause Code TFT Semantic Error tx";
         }
         leaf gtpv2-cause-tft-syn-err-tx {
           type int32;
           description "GTPv2 Cause Code TFT Syntactic Error tx";
         }
         leaf gtpv2-cause-pkt-fltr-semantic-err-tx {
           type int32;
           description "GTPv2 Cause Code Packet Filter Semantic Error tx";
         }
         leaf gtpv2-cause-pkt-fltr-syn-err-tx {
           type int32;
           description "GTPv2 Cause Code Packet Filter Syntatctic Error tx";
         }
         leaf gtpv2-cause-miss-unkown-apn-tx {
           type int32;
           description "GTPv2 Cause Code Missing or Unknown APN tx";
         }
         leaf gtpv2-cause-unexp-repeat-ie-tx {
           type int32;
           description "GTPv2 Cause Code Unexpected Repeated IE tx";
         }
         leaf gtpv2-cause-gre-key-not-fnd-tx {
           type int32;
           description "GTPv2 Cause Code GRE Key Not Found tx";
         }
         leaf gtpv2-cause-reloc-fail-tx {
           type int32;
           description "GTPv2 Cause Code Reallocation Failure tx";
         }
         leaf gtpv2-cause-denied-in-rat-tx {
           type int32;
           description "GTPv2 Cause Code Denied In RAT tx";
         }
         leaf gtpv2-cause-pt-not-supp-tx {
           type int32;
           description "GTPv2 Cause Code PDN Type Not Supported tx";
         }
         leaf gtpv2-cause-all-dyn-addr-occ-tx {
           type int32;
           description "GTPv2 Cause Code All Dynamic Addresses Occupied tx";
         }
         leaf gtpv2-cause-no-tft-ue-ctx-exist-tx {
           type int32;
           description "GTPv2 Cause Code UE Context Without TFT Activation tx";
         }
         leaf gtpv2-cause-proto-not-supp-tx {
           type int32;
           description "GTPv2 Cause Code Protocol Not Supported tx";
         }
         leaf gtpv2-cause-ue-not-resp-tx {
           type int32;
           description "GTPv2 Cause Code UE Not Responding tx";
         }
         leaf gtpv2-cause-ue-refuses-tx {
           type int32;
           description "GTPv2 Cause Code UE Refuses tx";
         }
         leaf gtpv2-cause-serv-denied-tx {
           type int32;
           description "GTPv2 Cause Code Service Denied tx";
         }
         leaf gtpv2-cause-unable-page-ue-tx {
           type int32;
           description "GTPv2 Cause Code Unable To Page UE tx";
         }
         leaf gtpv2-cause-no-mem-tx {
           type int32;
           description "GTPv2 Cause Code No Memory tx";
         }
         leaf gtpv2-cause-user-auth-fail-tx {
           type int32;
           description "GTPv2 Cause Code User Auth Failure tx";
         }
         leaf gtpv2-cause-apn-access-denied-tx {
           type int32;
           description "GTPv2 Cause Code APN Access Denied tx";
         }
         leaf gtpv2-cause-req-rej-tx {
           type int32;
           description "GTPv2 Cause Code Request Rejected tx";
         }
         leaf gtpv2-cause-ptmsi-sig-mismatch-rx {
           type int32;
           description "GTPv2 Cause Code P-TMSI Signature Mismatch Rx";
         }
         leaf gtpv2-cause-ptmsi-sig-mismatch-tx {
           type int32;
           description "GTPv2 Cause Code P-TMSI Signature Mismatch Rx";
         }
         leaf gtpv2-cause-imsi-not-known-rx {
           type int32;
           description "GTPv2 Cause Code IMSI Not Known Rx";
         }
         leaf gtpv2-cause-imsi-not-known-tx {
           type int32;
           description "GTPv2 Cause Code IMSI Not Known Tx";
         }
         leaf gtpv2-cause-semantic-err-in-tad-rx {
           type int32;
           description "GTPv2 Cause Code Semantic Error in Tad Rx";
         }
         leaf gtpv2-cause-semantic-err-in-tad-tx {
           type int32;
           description "GTPv2 Cause Code Semantic Error in Tad Tx";
         }
         leaf gtpv2-cause-syntactic-err-in-tad-rx {
           type int32;
           description "GTPv2 Cause Code Syntactic Error in Tad Rx";
         }
         leaf gtpv2-cause-syntactic-err-in-tad-tx {
           type int32;
           description "GTPv2 Cause Code Syntactic Error in Tad Tx";
         }
         leaf gtpv2-cause-rsvd-msg-value-rcvd-rx {
           type int32;
           description "GTPv2 Cause Code Received Message Value Received Rx";
         }
         leaf gtpv2-cause-rsvd-msg-value-rcvd-tx {
           type int32;
           description "GTPv2 Cause Code Received Message Value Received Tx";
         }
         leaf gtpv2-cause-rmt-peer-not-responding-rx {
           type int32;
           description "GTPv2 Cause Code Remote Peer Not Responding Rx";
         }
         leaf gtpv2-cause-rmt-peer-not-responding-tx {
           type int32;
           description "GTPv2 Cause Code Remote Peer Not Responding Tx";
         }
         leaf gtpv2-cause-collision-with-nw-initiated-req-rx {
           type int32;
           description "GTPv2 Cause Code Collision with NW Intiated Req Rx";
         }
         leaf gtpv2-cause-collision-with-nw-initiated-req-tx {
           type int32;
           description "GTPv2 Cause Code Collision with NW Intiated Req Tx";
         }
         leaf gtpv2-cause-unable-page-ue-suspended-rx {
           type int32;
           description "GTPv2 Cause Code Imsi Suspended Rx";
         }
         leaf gtpv2-cause-unable-page-ue-suspended-tx {
           type int32;
           description "GTPv2 Cause Code Unable Page UE Suspended Tx";
         }
         leaf gtpv2-cause-cond-ie-missing-rx {
           type int32;
           description "GTPv2 Cause Code Conditional IE Missing Rx";
         }
         leaf gtpv2-cause-cond-ie-missing-tx {
           type int32;
           description "GTPv2 Cause Code Conditional IE Missing Tx";
         }
         leaf gtpv2-cause-incomp-apn-type-res-rx {
           type int32;
           description "GTPv2 Cause Code APN Restriction Type Incompatible Rx";
         }
         leaf gtpv2-cause-incomp-apn-type-res-tx {
           type int32;
           description "GTPv2 Cause Code APN Restriction Type Incompatible Tx";
         }
         leaf gtpv2-cause-invalid-total-len-rx {
           type int32;
           description "GTPv2 Cause Code Invalid Total Len Rx";
         }
         leaf gtpv2-cause-invalid-total-len-tx {
           type int32;
           description "GTPv2 Cause Code Invalid Total Len Tx";
         }
         leaf gtpv2-cause-data-forwarding-not-supp-rx {
           type int32;
           description "GTPv2 Cause Code Data Forwarding Not Supp Rx";
         }
         leaf gtpv2-cause-data-forwarding-not-supp-tx {
           type int32;
           description "GTPv2 Cause Code Data Forwarding Not Supp Tx";
         }
         leaf gtpv2-cause-invalid-reply-from-rmt-peer-rx {
           type int32;
           description "GTPv2 Cause Code Invalid Reply From Remote Peer Rx";
         }
         leaf gtpv2-cause-invalid-reply-from-rmt-peer-tx {
           type int32;
           description "GTPv2 Cause Code Invalid Reply From Remote Peer Tx";
         }
         leaf gtpv2-cause-invalid-peer-rx {
           type int32;
           description "GTPv2 Cause Code Invalid Peer Rx";
         }
         leaf gtpv2-cause-invalid-peer-tx {
           type int32;
           description "GTPv2 Cause Code Invalid Peer Tx";
         }
         leaf gtpv2-cause-temp-rej-ho-in-prog-rx {
           type int32;
           description "GTPv2 Cause Code Temporarily Reject Handover In Progress";
         }
         leaf gtpv2-cause-temp-rej-ho-in-prog-tx {
           type int32;
           description "GTPv2 Cause Code Temporarily Reject Handover In Progress";
         }
         leaf gtpv2-cause-unknown-rx {
           type int32;
           description "GTPv2 Cause Code Unknown Rx";
         }
         leaf gtpv2-cause-unknown-tx {
           type int32;
           description "GTPv2 Cause Code Unknown Tx";
         }
       }
       container gtpv2-cause-code-stats {
         leaf gtpv2-cause-req-accept-rx {
           type int32;
           description "GTPv2 Cause Code Request Accepted Rx";
         }
         leaf gtpv2-cause-req-accept-tx {
           type int32;
           description "GTPv2 Cause Code Request Accepted tx";
         }
         leaf gtpv2-cause-accept-part-rx {
           type int32;
           description "GTPv2 Cause Code Accept Partial Rx";
         }
         leaf gtpv2-cause-accept-part-tx {
           type int32;
           description "GTPv2 Cause Code Accept Partial tx";
         }
         leaf gtpv2-cause-new-pt-npref-rx {
           type int32;
           description "GTPv2 Cause Code New PDN Type Due to Network Preference Rx";
         }
         leaf gtpv2-cause-new-pt-npref-tx {
           type int32;
           description "GTPv2 Cause Code New PDN Type Due to Network Preference tx";
         }
         leaf gtpv2-cause-new-pt-si-addr-br-rx {
           type int32;
           description "GTPv2 Cause Code New PDN Type Due To Single Address Bearer Rx";
         }
         leaf gtpv2-cause-new-pt-si-addr-br-tx {
           type int32;
           description "GTPv2 Cause Code New PDN Type Due To Single Address Bearer tx";
         }
         leaf gtpv2-cause-local-detach-rx {
           type int32;
           description "GTPv2 Cause Code Local Detach Rx";
         }
         leaf gtpv2-cause-local-detach-tx {
           type int32;
           description "GTPv2 Cause Code Local Detach Tx";
         }
         leaf gtpv2-cause-complete-detach-rx {
           type int32;
           description "GTPv2 Cause Code Complete Detach Rx";
         }
         leaf gtpv2-cause-complete-detach-tx {
           type int32;
           description "GTPv2 Cause Code Complete Detach Tx";
         }
         leaf gtpv2-cause-rat-changed-3gpp-to-non-3gpp-rx {
           type int32;
           description "GTPv2 Cause Code RAT Changed 3GPP to Non 3GPP Rx";
         }
         leaf gtpv2-cause-rat-changed-3gpp-to-non-3gpp-tx {
           type int32;
           description "GTPv2 Cause Code RAT Changed 3GPP to Non 3GPP Tx";
         }
         leaf gtpv2-cause-isr-deactivated-rx {
           type int32;
           description "GTPv2 Cause Code ISR Deactivated Rx";
         }
         leaf gtpv2-cause-isr-deactivated-tx {
           type int32;
           description "GTPv2 Cause Code ISR Deactivated Tx";
         }
         leaf gtpv2-cause-err-ind-from-rnc-enodeb-rx {
           type int32;
           description "GTPv2 Cause Code Err Ind From RNC Enodeb Rx";
         }
         leaf gtpv2-cause-err-ind-from-rnc-enodeb-tx {
           type int32;
           description "GTPv2 Cause Code Err Ind From RNC Enodeb Tx";
         }
         leaf gtpv2-cause-ctx-not-fnd-rx {
           type int32;
           description "GTPv2 Cause Code Context Not Found Rx";
         }
         leaf gtpv2-cause-ctx-not-fnd-tx {
           type int32;
           description "GTPv2 Cause Code Context Not Found tx";
         }
         leaf gtpv2-cause-inv-msg-fmt-rx {
           type int32;
           description "GTPv2 Cause Code Invalid Message Format Rx";
         }
         leaf gtpv2-cause-inv-msg-fmt-tx {
           type int32;
           description "GTPv2 Cause Code Invalid Message Format tx";
         }
         leaf gtpv2-cause-ver-not-supp-rx {
           type int32;
           description "GTPv2 Cause Code Version Not Supported Rx";
         }
         leaf gtpv2-cause-ver-not-supp-tx {
           type int32;
           description "GTPv2 Cause Code Version Not Supported tx";
         }
         leaf gtpv2-cause-inv-len-rx {
           type int32;
           description "GTPv2 Cause Code Invalid Length Rx";
         }
         leaf gtpv2-cause-inv-len-tx {
           type int32;
           description "GTPv2 Cause Code Invalid Length tx";
         }
         leaf gtpv2-cause-serv-not-supp-rx {
           type int32;
           description "GTPv2 Cause Code Service Not Supported Rx";
         }
         leaf gtpv2-cause-serv-not-supp-tx {
           type int32;
           description "GTPv2 Cause Code Service Not Supported tx";
         }
         leaf gtpv2-cause-man-ie-incorr-rx {
           type int32;
           description "GTPv2 Cause Code Mandatory IE Incorrect Rx";
         }
         leaf gtpv2-cause-man-ie-incorr-tx {
           type int32;
           description "GTPv2 Cause Code Mandatory IE Incorrect tx";
         }
         leaf gtpv2-cause-man-ie-miss-rx {
           type int32;
           description "GTPv2 Cause Code Mandatory IE Missing Rx";
         }
         leaf gtpv2-cause-man-ie-miss-tx {
           type int32;
           description "GTPv2 Cause Code Mandatory IE Missing tx";
         }
         leaf gtpv2-cause-opt-ie-incorr-rx {
           type int32;
           description "GTPv2 Cause Code Optional IE Incorrect Rx";
         }
         leaf gtpv2-cause-opt-ie-incorr-tx {
           type int32;
           description "GTPv2 Cause Code Optional IE Incorrect tx";
         }
         leaf gtpv2-cause-sys-fail-rx {
           type int32;
           description "GTPv2 Cause Code System Failure Rx";
         }
         leaf gtpv2-cause-sys-fail-tx {
           type int32;
           description "GTPv2 Cause Code System Failure tx";
         }
         leaf gtpv2-cause-no-res-rx {
           type int32;
           description "GTPv2 Cause Code No Resources Rx";
         }
         leaf gtpv2-cause-no-res-tx {
           type int32;
           description "GTPv2 Cause Code No Resources tx";
         }
         leaf gtpv2-cause-tft-semantic-err-rx {
           type int32;
           description "GTPv2 Cause Code TFT Semantic Error Rx";
         }
         leaf gtpv2-cause-tft-semantic-err-tx {
           type int32;
           description "GTPv2 Cause Code TFT Semantic Error tx";
         }
         leaf gtpv2-cause-tft-syn-err-rx {
           type int32;
           description "GTPv2 Cause Code TFT Syntactic Error Rx";
         }
         leaf gtpv2-cause-tft-syn-err-tx {
           type int32;
           description "GTPv2 Cause Code TFT Syntactic Error tx";
         }
         leaf gtpv2-cause-pkt-fltr-semantic-err-rx {
           type int32;
           description "GTPv2 Cause Code Packet Filter Semantic Error Rx";
         }
         leaf gtpv2-cause-pkt-fltr-semantic-err-tx {
           type int32;
           description "GTPv2 Cause Code Packet Filter Semantic Error tx";
         }
         leaf gtpv2-cause-pkt-fltr-syn-err-rx {
           type int32;
           description "GTPv2 Cause Code Packet Filter Syntatctic Error Rx";
         }
         leaf gtpv2-cause-pkt-fltr-syn-err-tx {
           type int32;
           description "GTPv2 Cause Code Packet Filter Syntatctic Error tx";
         }
         leaf gtpv2-cause-miss-unkown-apn-rx {
           type int32;
           description "GTPv2 Cause Code Missing or Unknown APN Rx";
         }
         leaf gtpv2-cause-miss-unkown-apn-tx {
           type int32;
           description "GTPv2 Cause Code Missing or Unknown APN tx";
         }
         leaf gtpv2-cause-unexp-repeat-ie-rx {
           type int32;
           description "GTPv2 Cause Code Unexpected Repeated IE Rx";
         }
         leaf gtpv2-cause-unexp-repeat-ie-tx {
           type int32;
           description "GTPv2 Cause Code Unexpected Repeated IE tx";
         }
         leaf gtpv2-cause-gre-key-not-fnd-rx {
           type int32;
           description "GTPv2 Cause Code GRE Key Not Found Rx";
         }
         leaf gtpv2-cause-gre-key-not-fnd-tx {
           type int32;
           description "GTPv2 Cause Code GRE Key Not Found tx";
         }
         leaf gtpv2-cause-reloc-fail-rx {
           type int32;
           description "GTPv2 Cause Code Reallocation Failure Rx";
         }
         leaf gtpv2-cause-reloc-fail-tx {
           type int32;
           description "GTPv2 Cause Code Reallocation Failure tx";
         }
         leaf gtpv2-cause-denied-in-rat-rx {
           type int32;
           description "GTPv2 Cause Code Denied In RAT Rx";
         }
         leaf gtpv2-cause-denied-in-rat-tx {
           type int32;
           description "GTPv2 Cause Code Denied In RAT tx";
         }
         leaf gtpv2-cause-pt-not-supp-rx {
           type int32;
           description "GTPv2 Cause Code PDN Type Not Supported Rx";
         }
         leaf gtpv2-cause-pt-not-supp-tx {
           type int32;
           description "GTPv2 Cause Code PDN Type Not Supported tx";
         }
         leaf gtpv2-cause-all-dyn-addr-occ-rx {
           type int32;
           description "GTPv2 Cause Code All Dynamic Addresses Occupied Rx";
         }
         leaf gtpv2-cause-all-dyn-addr-occ-tx {
           type int32;
           description "GTPv2 Cause Code All Dynamic Addresses Occupied tx";
         }
         leaf gtpv2-cause-no-tft-ue-ctx-exist-rx {
           type int32;
           description "GTPv2 Cause Code UE Context Without TFT Activation Rx";
         }
         leaf gtpv2-cause-no-tft-ue-ctx-exist-tx {
           type int32;
           description "GTPv2 Cause Code UE Context Without TFT Activation tx";
         }
         leaf gtpv2-cause-proto-not-supp-rx {
           type int32;
           description "GTPv2 Cause Code Protocol Not Supported Rx";
         }
         leaf gtpv2-cause-proto-not-supp-tx {
           type int32;
           description "GTPv2 Cause Code Protocol Not Supported tx";
         }
         leaf gtpv2-cause-ue-not-resp-rx {
           type int32;
           description "GTPv2 Cause Code UE Not Responding Rx";
         }
         leaf gtpv2-cause-ue-not-resp-tx {
           type int32;
           description "GTPv2 Cause Code UE Not Responding tx";
         }
         leaf gtpv2-cause-ue-refuses-rx {
           type int32;
           description "GTPv2 Cause Code UE Refuses Rx";
         }
         leaf gtpv2-cause-ue-refuses-tx {
           type int32;
           description "GTPv2 Cause Code UE Refuses tx";
         }
         leaf gtpv2-cause-serv-denied-rx {
           type int32;
           description "GTPv2 Cause Code Service Denied Rx";
         }
         leaf gtpv2-cause-serv-denied-tx {
           type int32;
           description "GTPv2 Cause Code Service Denied tx";
         }
         leaf gtpv2-cause-unable-page-ue-rx {
           type int32;
           description "GTPv2 Cause Code Unable To Page UE Rx";
         }
         leaf gtpv2-cause-unable-page-ue-tx {
           type int32;
           description "GTPv2 Cause Code Unable To Page UE tx";
         }
         leaf gtpv2-cause-no-mem-rx {
           type int32;
           description "GTPv2 Cause Code No Memory Rx";
         }
         leaf gtpv2-cause-no-mem-tx {
           type int32;
           description "GTPv2 Cause Code No Memory tx";
         }
         leaf gtpv2-cause-user-auth-fail-rx {
           type int32;
           description "GTPv2 Cause Code User Auth Failure Rx";
         }
         leaf gtpv2-cause-user-auth-fail-tx {
           type int32;
           description "GTPv2 Cause Code User Auth Failure tx";
         }
         leaf gtpv2-cause-apn-access-denied-rx {
           type int32;
           description "GTPv2 Cause Code APN Access Denied Rx";
         }
         leaf gtpv2-cause-apn-access-denied-tx {
           type int32;
           description "GTPv2 Cause Code APN Access Denied tx";
         }
         leaf gtpv2-cause-req-rej-rx {
           type int32;
           description "GTPv2 Cause Code Request Rejected Rx";
         }
         leaf gtpv2-cause-req-rej-tx {
           type int32;
           description "GTPv2 Cause Code Request Rejected tx";
         }
         leaf gtpv2-cause-ptmsi-sig-mismatch-rx {
           type int32;
           description "GTPv2 Cause Code P-TMSI Signature Mismatch Rx";
         }
         leaf gtpv2-cause-ptmsi-sig-mismatch-tx {
           type int32;
           description "GTPv2 Cause Code P-TMSI Signature Mismatch Rx";
         }
         leaf gtpv2-cause-imsi-not-known-rx {
           type int32;
           description "GTPv2 Cause Code IMSI Not Known Rx";
         }
         leaf gtpv2-cause-imsi-not-known-tx {
           type int32;
           description "GTPv2 Cause Code IMSI Not Known Tx";
         }
         leaf gtpv2-cause-semantic-err-in-tad-rx {
           type int32;
           description "GTPv2 Cause Code Semantic Error in Tad Rx";
         }
         leaf gtpv2-cause-semantic-err-in-tad-tx {
           type int32;
           description "GTPv2 Cause Code Semantic Error in Tad Tx";
         }
         leaf gtpv2-cause-syntactic-err-in-tad-rx {
           type int32;
           description "GTPv2 Cause Code Syntactic Error in Tad Rx";
         }
         leaf gtpv2-cause-syntactic-err-in-tad-tx {
           type int32;
           description "GTPv2 Cause Code Syntactic Error in Tad Tx";
         }
         leaf gtpv2-cause-rsvd-msg-value-rcvd-rx {
           type int32;
           description "GTPv2 Cause Code Received Message Value Received Rx";
         }
         leaf gtpv2-cause-rsvd-msg-value-rcvd-tx {
           type int32;
           description "GTPv2 Cause Code Received Message Value Received Tx";
         }
         leaf gtpv2-cause-rmt-peer-not-responding-rx {
           type int32;
           description "GTPv2 Cause Code Remote Peer Not Responding Rx";
         }
         leaf gtpv2-cause-rmt-peer-not-responding-tx {
           type int32;
           description "GTPv2 Cause Code Remote Peer Not Responding Tx";
         }
         leaf gtpv2-cause-collision-with-nw-initiated-req-rx {
           type int32;
           description "GTPv2 Cause Code Collision with NW Intiated Req Rx";
         }
         leaf gtpv2-cause-collision-with-nw-initiated-req-tx {
           type int32;
           description "GTPv2 Cause Code Collision with NW Intiated Req Tx";
         }
         leaf gtpv2-cause-unable-page-ue-suspended-rx {
           type int32;
           description "GTPv2 Cause Code Imsi Suspended Rx";
         }
         leaf gtpv2-cause-unable-page-ue-suspended-tx {
           type int32;
           description "GTPv2 Cause Code Unable Page UE Suspended Tx";
         }
         leaf gtpv2-cause-cond-ie-missing-rx {
           type int32;
           description "GTPv2 Cause Code Conditional IE Missing Rx";
         }
         leaf gtpv2-cause-cond-ie-missing-tx {
           type int32;
           description "GTPv2 Cause Code Conditional IE Missing Tx";
         }
         leaf gtpv2-cause-incomp-apn-type-res-rx {
           type int32;
           description "GTPv2 Cause Code APN Restriction Type Incompatible Rx";
         }
         leaf gtpv2-cause-incomp-apn-type-res-tx {
           type int32;
           description "GTPv2 Cause Code APN Restriction Type Incompatible Tx";
         }
         leaf gtpv2-cause-invalid-total-len-rx {
           type int32;
           description "GTPv2 Cause Code Invalid Total Len Rx";
         }
         leaf gtpv2-cause-invalid-total-len-tx {
           type int32;
           description "GTPv2 Cause Code Invalid Total Len Tx";
         }
         leaf gtpv2-cause-data-forwarding-not-supp-rx {
           type int32;
           description "GTPv2 Cause Code Data Forwarding Not Supp Rx";
         }
         leaf gtpv2-cause-data-forwarding-not-supp-tx {
           type int32;
           description "GTPv2 Cause Code Data Forwarding Not Supp Tx";
         }
         leaf gtpv2-cause-invalid-reply-from-rmt-peer-rx {
           type int32;
           description "GTPv2 Cause Code Invalid Reply From Remote Peer Rx";
         }
         leaf gtpv2-cause-invalid-reply-from-rmt-peer-tx {
           type int32;
           description "GTPv2 Cause Code Invalid Reply From Remote Peer Tx";
         }
         leaf gtpv2-cause-invalid-peer-rx {
           type int32;
           description "GTPv2 Cause Code Invalid Peer Rx";
         }
         leaf gtpv2-cause-invalid-peer-tx {
           type int32;
           description "GTPv2 Cause Code Invalid Peer Tx";
         }
         leaf gtpv2-cause-temp-rej-ho-in-prog-rx {
           type int32;
           description "GTPv2 Cause Code Temporarily Reject Handover In Progress";
         }
         leaf gtpv2-cause-temp-rej-ho-in-prog-tx {
           type int32;
           description "GTPv2 Cause Code Temporarily Reject Handover In Progress";
         }
         leaf gtpv2-cause-unknown-rx {
           type int32;
           description "GTPv2 Cause Code Unknown Rx";
         }
         leaf gtpv2-cause-unknown-tx {
           type int32;
           description "GTPv2 Cause Code Unknown Tx";
         }
       }
     }
     leaf gtpv0-recv-allocs {
       type int32;
       description "Gtpv0 Recv Allocs";
     }
     leaf gtpv0-recv-frees {
       type int32;
       description "Gtpv0 Recv Frees";
     }
     leaf gtpv0-recv-alloc-fails {
       type int32;
       description "Gtpv0 Recv Alloc Fails";
     }
     leaf gtpv0-send-allocs {
       type int32;
       description "Gtpv0 Send Alloc";
     }
     leaf gtpv0-send-frees {
       type int32;
       description "Gtpv0 Send Frees";
     }
     leaf gtpv0-send-alloc-fails {
       type int32;
       description "Gtpv0 Send Alloc Fails";
     }
     leaf gtpv1-recv-allocs {
       type int32;
       description "Gtpv1 Recv Allocs";
     }
     leaf gtpv1-recv-frees {
       type int32;
       description "Gtpv1 Recv Frees";
     }
     leaf gtpv1-recv-alloc-fails {
       type int32;
       description "Gtpv1 Recv Allocs Fails";
     }
     leaf gtpv1-send-allocs {
       type int32;
       description "Gtpv1 Send Allocs";
     }
     leaf gtpv1-send-frees {
       type int32;
       description "Gtpv1 Send Frees";
     }
     leaf gtpv1-send-alloc-fails {
       type int32;
       description "Gtpv1 Send Alloc Fails";
     }
     leaf gtpv2-recv-allocs {
       type int32;
       description "Gtpv2 Recv Allocs";
     }
     leaf gtpv2-recv-frees {
       type int32;
       description "Gtpv2 Recv Frees";
     }
     leaf gtpv2-recv-alloc-fails {
       type int32;
       description "Gtpv2 Recv Alloc Fails";
     }
     leaf gtpv2-recv-br-allocs {
       type int32;
       description "Gtpv2 Recv Br Allocs";
     }
     leaf gtpv2-recv-br-frees {
       type int32;
       description "Gtpv2 Recv Br Frees";
     }
     leaf gtpv2-recv-br-alloc-fails {
       type int32;
       description "Gtpv2 Recv Br Alloc Fails";
     }
     leaf gtpv2-send-allocs {
       type int32;
       description "Gtpv2 Send Allocs";
     }
     leaf gtpv2-send-frees {
       type int32;
       description "Gtpv2 Send Frees";
     }
     leaf gtpv2-send-alloc-fails {
       type int32;
       description "Gtpv2 Send Alloc Fails";
     }
     leaf gtpv2-send-br-allocs {
       type int32;
       description "Gtpv2 Send Br Allocs";
     }
     leaf gtpv2-send-br-frees {
       type int32;
       description "Gtpv2 Send Br Frees";
     }
     leaf gtpv2-send-br-alloc-fails {
       type int32;
       description "Gtpv2 Send Br Alloc Fails";
     }
     leaf gtp-intr-evt-recv-allocs {
       type int32;
       description "Gtpv2 Int Event Recv Allocs";
     }
     leaf gtp-intr-evt-recv-frees {
       type int32;
       description "Gtpv2 Int Event Recv Frees";
     }
     leaf gtp-intr-evt-recv-alloc-fails {
       type int32;
       description "Gtpv2 Int Event Recv Alloc Fails";
     }
   }
   grouping gtpc-peer-count-block {
     leaf gw-name {
       type string;
       description "Gateway name";
     }
     leaf peer-count-s1u {
       type int32;
       description "Peer Count for Interface S1u";
     }
     leaf peer-count-s11 {
       type int32;
       description "Peer Count for Interface S11";
     }
     leaf peer-count-s12 {
       type int32;
       description "Peer Count for Interface S12";
     }
     leaf peer-count-s5 {
       type int32;
       description "Peer Count for Interface S5";
     }
     leaf peer-count-s8 {
       type int32;
       description "Peer Count for Interface S8";
     }
     leaf peer-count-s4 {
       type int32;
       description "Peer Count for Interface S4";
     }
     leaf peer-count-s11-s4 {
       type int32;
       description "Peer Count for Interface S11-S4";
     }
     leaf peer-count-gn {
       type int32;
       description "Peer Count for Interface Gn";
     }
     leaf peer-count-gp {
       type int32;
       description "Peer Count for Interface Gp";
     }
     leaf peer-count-all {
       type int32;
       description "Peer Count for All Interface";
     }
   }
   grouping gtpc-peer-statistics-block {
     leaf gw-name {
       type string;
       description "Gateway name";
     }
     leaf gtpv2-release-access-bearer-req-rx {
       type int32;
       description "Gtpv2 Release Access Bearer Req Rx";
     }
     leaf gtpv2-release-access-bearer-rsp-tx {
       type int32;
       description "Gtpv2 Release Access Bearer Resp Tx";
     }
     list gtp-global-pkt-stats {
       leaf drop-counter {
         type int32;
         description "Drop Counter";
       }
       leaf pkt-alloc-fail {
         type int32;
         description "Pkt Alloc Fail";
       }
       leaf pkt-send-fail {
         type int32;
         description "Pkt Send Fail";
       }
       leaf ip-ver-error-rx {
         type int32;
         description "Ip Ver Error Rx";
       }
       leaf ip-proto-error-rx {
         type int32;
         description "Ip Proto Error Rx";
       }
       leaf gtp-port-error-rx {
         type int32;
         description "Gtp Port Error Rx";
       }
       leaf gtp-unknown-ver-rx {
         type int32;
         description "Gtp Uknown Version Rx";
       }
       leaf pkt-len-error-rx {
         type int32;
         description "Pkt Len Error Rx";
       }
       leaf unknown-msg-rx {
         type int32;
         description "Unknown Msg Rx";
       }
     }
     list gtpv0-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv0v1-msg-stats {
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf create-pdp-req-rx {
           type int32;
           description "Create PDP Req Rx";
         }
         leaf create-pdp-req-tx {
           type int32;
           description "Create PDP Req Tx";
         }
         leaf create-pdp-rsp-rx {
           type int32;
           description "Create PDP Rsp Rx";
         }
         leaf create-pdp-rsp-tx {
           type int32;
           description "Create PDP Rsp Tx";
         }
         leaf update-pdp-req-rx {
           type int32;
           description "Update PDP Req Rx";
         }
         leaf update-pdp-req-tx {
           type int32;
           description "Update PDP Req Tx";
         }
         leaf update-pdp-rsp-rx {
           type int32;
           description "Update PDP Rsp Rx";
         }
         leaf update-pdp-rsp-tx {
           type int32;
           description "Update PDP Rsp Tx";
         }
         leaf delete-pdp-req-rx {
           type int32;
           description "Delete PDP Req Rx";
         }
         leaf delete-pdp-req-tx {
           type int32;
           description "Delete PDP Req Tx";
         }
         leaf delete-pdp-rsp-rx {
           type int32;
           description "Delete PDP Rsp Rx";
         }
         leaf delete-pdp-rsp-tx {
           type int32;
           description "Delete PDP Rsp Tx";
         }
         leaf init-pdp-req-rx {
           type int32;
           description "Initiate PDP Req Rx";
         }
         leaf init-pdp-req-tx {
           type int32;
           description "Initiate PDP Req Tx";
         }
         leaf init-pdp-rsp-rx {
           type int32;
           description "Initiate PDP Rsp Rx";
         }
         leaf init-pdp-rsp-tx {
           type int32;
           description "Initiate PDP Rsp Tx";
         }
         leaf gtp-error-ind-rx {
           type int32;
           description "Gtp Error Indication Rx";
         }
         leaf gtp-error-ind-tx {
           type int32;
           description "Gtp Error Indication Tx";
         }
       }
       container gtpv0-cause-code-stats {
         leaf cause-req-accepted-rx {
           type int32;
           description "Cause Code Request Accepted Rx";
         }
         leaf cause-req-accepted-tx {
           type int32;
           description "Cause Code Request Accepted Tx";
         }
         leaf cause-non-exist-rx {
           type int32;
           description "Cause Code Non Existant Rx";
         }
         leaf cause-non-exist-tx {
           type int32;
           description "Cause Code Non Existant Tx";
         }
         leaf cause-invalid-msg-fmt-rx {
           type int32;
           description "Cause Code Invalid Message Format Rx";
         }
         leaf cause-invalid-msg-fmt-tx {
           type int32;
           description "Cause Code Invalid Message Format Tx";
         }
         leaf cause-imsi-not-known-rx {
           type int32;
           description "Cause Code IMSI Not Known Rx";
         }
         leaf cause-imsi-not-known-tx {
           type int32;
           description "Cause Code IMSI Not Known Tx";
         }
         leaf cause-ms-gprs-detach-rx {
           type int32;
           description "Cause Code MS GPRS Detached Rx";
         }
         leaf cause-ms-gprs-detach-tx {
           type int32;
           description "Cause Code MS GPRS Detached Tx";
         }
         leaf cause-ms-not-gprs-resp-rx {
           type int32;
           description "Cause Code MS Not GPRS Response Rx";
         }
         leaf cause-ms-not-gprs-resp-tx {
           type int32;
           description "Cause Code MS Not GPRS Response Tx";
         }
         leaf cause-ms-refuses-rx {
           type int32;
           description "Cause Code MS Refuses Rx";
         }
         leaf cause-ms-refuses-tx {
           type int32;
           description "Cause Code MS Refuses Tx";
         }
         leaf cause-ver-not-supported-rx {
           type int32;
           description "Cause Code Version Not Supported Rx";
         }
         leaf cause-ver-not-supported-tx {
           type int32;
           description "Cause Code Version Not Supported Tx";
         }
         leaf cause-no-resp-rx {
           type int32;
           description "Cause Code No Response Rx";
         }
         leaf cause-no-resp-tx {
           type int32;
           description "Cause Code No Response Tx";
         }
         leaf cause-serv-not-supp-rx {
           type int32;
           description "Cause Code Service Not Supported Rx";
         }
         leaf cause-serv-not-supp-tx {
           type int32;
           description "Cause Code Service Not Supported Tx";
         }
         leaf cause-man-ie-incrt-rx {
           type int32;
           description "Cause Code Mandatory IE Incorrect Rx";
         }
         leaf cause-man-ie-incrt-tx {
           type int32;
           description "Cause Code Mandatory IE Incorrect Tx";
         }
         leaf cause-man-ie-miss-rx {
           type int32;
           description "Cause Code Mandatory IE Missing Rx";
         }
         leaf cause-man-ie-miss-tx {
           type int32;
           description "Cause Code Mandatory IE Missing Tx";
         }
         leaf cause-opt-ie-incrt-rx {
           type int32;
           description "Cause Code Optional IE Incorrect Rx";
         }
         leaf cause-opt-ie-incrt-tx {
           type int32;
           description "Cause Code Optional IE Incorrect Tx";
         }
         leaf cause-sys-fail-rx {
           type int32;
           description "Cause Code System Failure Rx";
         }
         leaf cause-sys-fail-tx {
           type int32;
           description "Cause Code System Failure Tx";
         }
         leaf cause-roam-restrict-rx {
           type int32;
           description "Cause Code Roaming Restricted Rx";
         }
         leaf cause-roam-restrict-tx {
           type int32;
           description "Cause Code Roaming Restricted Tx";
         }
         leaf cause-ptmsi-sig-mismatch-rx {
           type int32;
           description "Cause Code PTMSI Signature Mismatch Rx";
         }
         leaf cause-ptmsi-sig-mismatch-tx {
           type int32;
           description "Cause Code PTMSI Signature Mismatch Tx";
         }
         leaf cause-gprs-conn-supp-rx {
           type int32;
           description "Cause Code GPRS Connection not Supported Rx";
         }
         leaf cause-gprs-conn-supp-tx {
           type int32;
           description "Cause Code GPRS Connection not Supported Tx";
         }
         leaf cause-auth-fail-rx {
           type int32;
           description "Cause Code Auth Failure Rx";
         }
         leaf cause-auth-fail-tx {
           type int32;
           description "Cause Code Auth Failure Tx";
         }
         leaf cause-user-auth-fail-rx {
           type int32;
           description "Cause Code User Auth Failure Rx";
         }
         leaf cause-user-auth-fail-tx {
           type int32;
           description "Cause Code User Auth Failure Tx";
         }
       }
     }
     list gtpv1-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv0v1-msg-stats {
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf create-pdp-req-rx {
           type int32;
           description "Create PDP Req Rx";
         }
         leaf create-pdp-req-tx {
           type int32;
           description "Create PDP Req Tx";
         }
         leaf create-pdp-rsp-rx {
           type int32;
           description "Create PDP Rsp Rx";
         }
         leaf create-pdp-rsp-tx {
           type int32;
           description "Create PDP Rsp Tx";
         }
         leaf update-pdp-req-rx {
           type int32;
           description "Update PDP Req Rx";
         }
         leaf update-pdp-req-tx {
           type int32;
           description "Update PDP Req Tx";
         }
         leaf update-pdp-rsp-rx {
           type int32;
           description "Update PDP Rsp Rx";
         }
         leaf update-pdp-rsp-tx {
           type int32;
           description "Update PDP Rsp Tx";
         }
         leaf delete-pdp-req-rx {
           type int32;
           description "Delete PDP Req Rx";
         }
         leaf delete-pdp-req-tx {
           type int32;
           description "Delete PDP Req Tx";
         }
         leaf delete-pdp-rsp-rx {
           type int32;
           description "Delete PDP Rsp Rx";
         }
         leaf delete-pdp-rsp-tx {
           type int32;
           description "Delete PDP Rsp Tx";
         }
         leaf init-pdp-req-rx {
           type int32;
           description "Initiate PDP Req Rx";
         }
         leaf init-pdp-req-tx {
           type int32;
           description "Initiate PDP Req Tx";
         }
         leaf init-pdp-rsp-rx {
           type int32;
           description "Initiate PDP Rsp Rx";
         }
         leaf init-pdp-rsp-tx {
           type int32;
           description "Initiate PDP Rsp Tx";
         }
         leaf gtp-error-ind-rx {
           type int32;
           description "Gtp Error Indication Rx";
         }
         leaf gtp-error-ind-tx {
           type int32;
           description "Gtp Error Indication Tx";
         }
       }
       container gtpv0-cause-code-stats {
         leaf cause-req-accepted-rx {
           type int32;
           description "Cause Code Request Accepted Rx";
         }
         leaf cause-req-accepted-tx {
           type int32;
           description "Cause Code Request Accepted Tx";
         }
         leaf cause-non-exist-rx {
           type int32;
           description "Cause Code Non Existant Rx";
         }
         leaf cause-non-exist-tx {
           type int32;
           description "Cause Code Non Existant Tx";
         }
         leaf cause-invalid-msg-fmt-rx {
           type int32;
           description "Cause Code Invalid Message Format Rx";
         }
         leaf cause-invalid-msg-fmt-tx {
           type int32;
           description "Cause Code Invalid Message Format Tx";
         }
         leaf cause-imsi-not-known-rx {
           type int32;
           description "Cause Code IMSI Not Known Rx";
         }
         leaf cause-imsi-not-known-tx {
           type int32;
           description "Cause Code IMSI Not Known Tx";
         }
         leaf cause-ms-gprs-detach-rx {
           type int32;
           description "Cause Code MS GPRS Detached Rx";
         }
         leaf cause-ms-gprs-detach-tx {
           type int32;
           description "Cause Code MS GPRS Detached Tx";
         }
         leaf cause-ms-not-gprs-resp-rx {
           type int32;
           description "Cause Code MS Not GPRS Response Rx";
         }
         leaf cause-ms-not-gprs-resp-tx {
           type int32;
           description "Cause Code MS Not GPRS Response Tx";
         }
         leaf cause-ms-refuses-rx {
           type int32;
           description "Cause Code MS Refuses Rx";
         }
         leaf cause-ms-refuses-tx {
           type int32;
           description "Cause Code MS Refuses Tx";
         }
         leaf cause-ver-not-supported-rx {
           type int32;
           description "Cause Code Version Not Supported Rx";
         }
         leaf cause-ver-not-supported-tx {
           type int32;
           description "Cause Code Version Not Supported Tx";
         }
         leaf cause-no-resp-rx {
           type int32;
           description "Cause Code No Response Rx";
         }
         leaf cause-no-resp-tx {
           type int32;
           description "Cause Code No Response Tx";
         }
         leaf cause-serv-not-supp-rx {
           type int32;
           description "Cause Code Service Not Supported Rx";
         }
         leaf cause-serv-not-supp-tx {
           type int32;
           description "Cause Code Service Not Supported Tx";
         }
         leaf cause-man-ie-incrt-rx {
           type int32;
           description "Cause Code Mandatory IE Incorrect Rx";
         }
         leaf cause-man-ie-incrt-tx {
           type int32;
           description "Cause Code Mandatory IE Incorrect Tx";
         }
         leaf cause-man-ie-miss-rx {
           type int32;
           description "Cause Code Mandatory IE Missing Rx";
         }
         leaf cause-man-ie-miss-tx {
           type int32;
           description "Cause Code Mandatory IE Missing Tx";
         }
         leaf cause-opt-ie-incrt-rx {
           type int32;
           description "Cause Code Optional IE Incorrect Rx";
         }
         leaf cause-opt-ie-incrt-tx {
           type int32;
           description "Cause Code Optional IE Incorrect Tx";
         }
         leaf cause-sys-fail-rx {
           type int32;
           description "Cause Code System Failure Rx";
         }
         leaf cause-sys-fail-tx {
           type int32;
           description "Cause Code System Failure Tx";
         }
         leaf cause-roam-restrict-rx {
           type int32;
           description "Cause Code Roaming Restricted Rx";
         }
         leaf cause-roam-restrict-tx {
           type int32;
           description "Cause Code Roaming Restricted Tx";
         }
         leaf cause-ptmsi-sig-mismatch-rx {
           type int32;
           description "Cause Code PTMSI Signature Mismatch Rx";
         }
         leaf cause-ptmsi-sig-mismatch-tx {
           type int32;
           description "Cause Code PTMSI Signature Mismatch Tx";
         }
         leaf cause-gprs-conn-supp-rx {
           type int32;
           description "Cause Code GPRS Connection not Supported Rx";
         }
         leaf cause-gprs-conn-supp-tx {
           type int32;
           description "Cause Code GPRS Connection not Supported Tx";
         }
         leaf cause-auth-fail-rx {
           type int32;
           description "Cause Code Auth Failure Rx";
         }
         leaf cause-auth-fail-tx {
           type int32;
           description "Cause Code Auth Failure Tx";
         }
         leaf cause-user-auth-fail-rx {
           type int32;
           description "Cause Code User Auth Failure Rx";
         }
         leaf cause-user-auth-fail-tx {
           type int32;
           description "Cause Code User Auth Failure Tx";
         }
       }
       container gtpv1-cause-code-stats {
         leaf cause-ctx-not-found-rx {
           type int32;
           description "Cause Code Context Not Found Rx";
         }
         leaf cause-ctx-not-found-tx {
           type int32;
           description "Cause Code Context Not Found tx";
         }
         leaf cause-dyn-pdp-addr-rx {
           type int32;
           description "Cause Code Dynamic PDP Address Rx";
         }
         leaf cause-dyn-pdp-addr-tx {
           type int32;
           description "Cause Code Dynamic PDP Address tx";
         }
         leaf cause-no-mem-rx {
           type int32;
           description "Cause Code No Memory Rx";
         }
         leaf cause-no-mem-tx {
           type int32;
           description "Cause Code No Memory tx";
         }
         leaf cause-reloc-fail-rx {
           type int32;
           description "Cause Code Relocation Failed Rx";
         }
         leaf cause-reloc-fail-tx {
           type int32;
           description "Cause Code Relocation Failed tx";
         }
         leaf cause-unk-man-exthdr-rx {
           type int32;
           description "Cause Code Unknown Extension Header Rx";
         }
         leaf cause-unk-man-exthdr-tx {
           type int32;
           description "Cause Code Unknown Extension Header tx";
         }
         leaf cause-semantic-tft-err1-rx {
           type int32;
           description "Cause Code Symantic TFT Error 1 Rx";
         }
         leaf cause-semantic-tft-err1-tx {
           type int32;
           description "Cause Code Symantic TFT Error 1 tx";
         }
         leaf cause-syn-tft-err2-rx {
           type int32;
           description "Cause Code Syntactic TFT Error 2 Rx";
         }
         leaf cause-syn-tft-err2-tx {
           type int32;
           description "Cause Code Syntactic TFT Error 2 tx";
         }
         leaf cause-semantic-pkt-fltr-err1-rx {
           type int32;
           description "Cause Code Semantic Packet Filter Error 1 Rx";
         }
         leaf cause-semantic-pkt-fltr-err1-tx {
           type int32;
           description "Cause Code Semantic Packet Filter Error 1 tx";
         }
         leaf cause-syn-pkt-fltr-err2-rx {
           type int32;
           description "Cause Code Syntactic Packet Filter Error 2 Rx";
         }
         leaf cause-syn-pkt-fltr-err2-tx {
           type int32;
           description "Cause Code Syntactic Packet Filter Error 2 tx";
         }
         leaf cause-miss-unk-apn-rx {
           type int32;
           description "Cause Code Missing Unknown APN Rx";
         }
         leaf cause-miss-unk-apn-tx {
           type int32;
           description "Cause Code Missing Unknown APN tx";
         }
         leaf cause-unk-pdp-addr-rx {
           type int32;
           description "Cause Code Unknown PDP Address Rx";
         }
         leaf cause-unk-pdp-addr-tx {
           type int32;
           description "Cause Code Unknown PDP Address tx";
         }
         leaf cause-no-tft-ctx-exist-rx {
           type int32;
           description "Cause Code No TFT Context Exists Rx";
         }
         leaf cause-no-tft-ctx-exist-tx {
           type int32;
           description "Cause Code No TFT Context Exists tx";
         }
       }
       container gtp-v2v1-stats {
         leaf gtpv1-end-mark-rx {
           type int32;
           description "Gtpv1 End Marker Rx";
         }
         leaf gtpv1-end-mark-tx {
           type int32;
           description "Gtpv1 End Marker Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf gtp-error-ind-rx {
           type int32;
           description "Gtp Error Indication Rx";
         }
         leaf gtp-error-ind-tx {
           type int32;
           description "Gtp Error Indication Tx";
         }
       }
     }
     container gtpv2-stats {
       container gtp-ver-global-stats {
         leaf prot-err {
           type int32;
           description "Prot Err";
         }
         leaf unsupported-msg {
           type int32;
           description "Unsupported Msg";
         }
         leaf t3-resp-tmr-exp {
           type int32;
           description "T3 Resp Tmr Exp";
         }
       }
       container gtpv2-msg-stats {
         leaf gtpv2-cause-req-accept-rx {
           type int32;
           description "GTPv2 Cause Code Request Accepted Rx";
         }
         leaf gtpv2-cause-accept-part-rx {
           type int32;
           description "GTPv2 Cause Code Accept Partial Rx";
         }
         leaf gtpv2-cause-new-pt-npref-rx {
           type int32;
           description "GTPv2 Cause Code New PDN Type Due to Network Preference Rx";
         }
         leaf gtpv2-cause-new-pt-si-addr-br-rx {
           type int32;
           description "GTPv2 Cause Code New PDN Type Due To Single Address Bearer Rx";
         }
         leaf gtpv2-cause-ctx-not-fnd-rx {
           type int32;
           description "GTPv2 Cause Code Context Not Found Rx";
         }
         leaf gtpv2-cause-inv-msg-fmt-rx {
           type int32;
           description "GTPv2 Cause Code Invalid Message Format Rx";
         }
         leaf gtpv2-cause-ver-not-supp-rx {
           type int32;
           description "GTPv2 Cause Code Version Not Supported Rx";
         }
         leaf gtpv2-cause-inv-len-rx {
           type int32;
           description "GTPv2 Cause Code Invalid Length Rx";
         }
         leaf gtpv2-cause-serv-not-supp-rx {
           type int32;
           description "GTPv2 Cause Code Service Not Supported Rx";
         }
         leaf gtpv2-cause-man-ie-incorr-rx {
           type int32;
           description "GTPv2 Cause Code Mandatory IE Incorrect Rx";
         }
         leaf gtpv2-cause-man-ie-miss-rx {
           type int32;
           description "GTPv2 Cause Code Mandatory IE Missing Rx";
         }
         leaf gtpv2-cause-opt-ie-incorr-rx {
           type int32;
           description "GTPv2 Cause Code Optional IE Incorrect Rx";
         }
         leaf gtpv2-cause-sys-fail-rx {
           type int32;
           description "GTPv2 Cause Code System Failure Rx";
         }
         leaf gtpv2-cause-no-res-rx {
           type int32;
           description "GTPv2 Cause Code No Resources Rx";
         }
         leaf gtpv2-cause-tft-semantic-err-rx {
           type int32;
           description "GTPv2 Cause Code TFT Semantic Error Rx";
         }
         leaf gtpv2-cause-tft-syn-err-rx {
           type int32;
           description "GTPv2 Cause Code TFT Syntactic Error Rx";
         }
         leaf gtpv2-cause-pkt-fltr-semantic-err-rx {
           type int32;
           description "GTPv2 Cause Code Packet Filter Semantic Error Rx";
         }
         leaf gtpv2-cause-pkt-fltr-syn-err-rx {
           type int32;
           description "GTPv2 Cause Code Packet Filter Syntatctic Error Rx";
         }
         leaf gtpv2-cause-miss-unkown-apn-rx {
           type int32;
           description "GTPv2 Cause Code Missing or Unknown APN Rx";
         }
         leaf gtpv2-cause-unexp-repeat-ie-rx {
           type int32;
           description "GTPv2 Cause Code Unexpected Repeated IE Rx";
         }
         leaf gtpv2-cause-gre-key-not-fnd-rx {
           type int32;
           description "GTPv2 Cause Code GRE Key Not Found Rx";
         }
         leaf gtpv2-cause-reloc-fail-rx {
           type int32;
           description "GTPv2 Cause Code Reallocation Failure Rx";
         }
         leaf gtpv2-cause-denied-in-rat-rx {
           type int32;
           description "GTPv2 Cause Code Denied In RAT Rx";
         }
         leaf gtpv2-cause-pt-not-supp-rx {
           type int32;
           description "GTPv2 Cause Code PDN Type Not Supported Rx";
         }
         leaf gtpv2-cause-all-dyn-addr-occ-rx {
           type int32;
           description "GTPv2 Cause Code All Dynamic Addresses Occupied Rx";
         }
         leaf gtpv2-cause-no-tft-ue-ctx-exist-rx {
           type int32;
           description "GTPv2 Cause Code UE Context Without TFT Activation Rx";
         }
         leaf gtpv2-cause-proto-not-supp-rx {
           type int32;
           description "GTPv2 Cause Code Protocol Not Supported Rx";
         }
         leaf gtpv2-cause-ue-not-resp-rx {
           type int32;
           description "GTPv2 Cause Code UE Not Responding Rx";
         }
         leaf gtpv2-cause-ue-refuses-rx {
           type int32;
           description "GTPv2 Cause Code UE Refuses Rx";
         }
         leaf gtpv2-cause-serv-denied-rx {
           type int32;
           description "GTPv2 Cause Code Service Denied Rx";
         }
         leaf gtpv2-cause-unable-page-ue-rx {
           type int32;
           description "GTPv2 Cause Code Unable To Page UE Rx";
         }
         leaf gtpv2-cause-no-mem-rx {
           type int32;
           description "GTPv2 Cause Code No Memory Rx";
         }
         leaf gtpv2-cause-user-auth-fail-rx {
           type int32;
           description "GTPv2 Cause Code User Auth Failure Rx";
         }
         leaf gtpv2-cause-apn-access-denied-rx {
           type int32;
           description "GTPv2 Cause Code APN Access Denied Rx";
         }
         leaf gtpv2-cause-req-rej-rx {
           type int32;
           description "GTPv2 Cause Code Request Rejected Rx";
         }
         leaf num-msg-rx {
           type uint64;
           description "Num Msg Rx";
         }
         leaf num-msg-tx {
           type uint64;
           description "Num Msg Tx";
         }
         leaf num-bytes-rx {
           type uint64;
           description "Num Bytes Rx";
         }
         leaf num-bytes-tx {
           type uint64;
           description "Num Bytes Tx";
         }
         leaf msg-redirect-rx {
           type int32;
           description "Msg Redirect Rx";
         }
         leaf msg-redirect-tx {
           type int32;
           description "Msg Redirect Tx";
         }
         leaf s11-piggyback-rx {
           type int32;
           description "S11 piggyback Rx";
         }
         leaf s11-piggyback-tx {
           type int32;
           description "S11 piggyback Tx";
         }
         leaf s4-piggyback-rx {
           type int32;
           description "S4 piggyback Rx";
         }
         leaf s4-piggyback-tx {
           type int32;
           description "S4 piggyback Tx";
         }
         leaf s5-piggyback-rx {
           type int32;
           description "S5 piggyback Rx";
         }
         leaf s5-piggyback-tx {
           type int32;
           description "S5 piggyback Tx";
         }
         leaf echo-req-rx {
           type int32;
           description "Echo Req Rx";
         }
         leaf echo-req-tx {
           type int32;
           description "Echo Req Tx";
         }
         leaf echo-rsp-rx {
           type int32;
           description "Echo Rsp Tx";
         }
         leaf echo-rsp-tx {
           type int32;
           description "Echo Rsp Tx";
         }
         leaf version-not-support-rx {
           type int32;
           description "Version Not Supported Rx";
         }
         leaf version-not-support-tx {
           type int32;
           description "Version Not Supported Tx";
         }
         leaf gtpv2-create-sess-req-rx {
           type int32;
           description "Gtpv2 Create Session Req Rx";
         }
         leaf gtpv2-create-sess-req-tx {
           type int32;
           description "Gtpv2 Create Session Req Tx";
         }
         leaf gtpv2-create-sess-rsp-rx {
           type int32;
           description "Gtpv2 Create Session Rsp Rx";
         }
         leaf gtpv2-create-sess-rsp-tx {
           type int32;
           description "Gtpv2 Create Session Rsp Tx";
         }
         leaf gtpv2-modify-bearer-req-rx {
           type int32;
           description "Gtpv2 Modify Bearer Req Rx";
         }
         leaf gtpv2-modify-bearer-req-tx {
           type int32;
           description "Gtpv2 Modify Bearer Req Tx";
         }
         leaf gtpv2-modify-bearer-rsp-rx {
           type int32;
           description "Gtpv2 Modify Bearer Rsp Rx";
         }
         leaf gtpv2-modify-bearer-rsp-tx {
           type int32;
           description "Gtpv2 Modify Bearer Rsp Tx";
         }
         leaf gtpv2-delete-sess-req-rx {
           type int32;
           description "Gtpv2 Delete Session Req Rx";
         }
         leaf gtpv2-delete-sess-req-tx {
           type int32;
           description "Gtpv2 Delete Session Req Tx";
         }
         leaf gtpv2-delete-sess-rsp-rx {
           type int32;
           description "Gtpv2 Delete Session Rsp Rx";
         }
         leaf gtpv2-delete-sess-rsp-tx {
           type int32;
           description "Gtpv2 Delete Session Rsp Tx";
         }
         leaf gtpv2-create-bearer-req-rx {
           type int32;
           description "Gtpv2 Create Bearer Req Rx";
         }
         leaf gtpv2-create-bearer-req-tx {
           type int32;
           description "Gtpv2 Create Bearer Req Tx";
         }
         leaf gtpv2-create-bearer-rsp-rx {
           type int32;
           description "Gtpv2 Create Bearer Rsp Rx";
         }
         leaf gtpv2-create-bearer-rsp-tx {
           type int32;
           description "Gtpv2 Create Bearer Rsp Tx";
         }
         leaf gtpv2-update-bearer-req-rx {
           type int32;
           description "Gtpv2 Update Bearer Req Rx";
         }
         leaf gtpv2-update-bearer-req-tx {
           type int32;
           description "Gtpv2 Update Bearer Req Tx";
         }
         leaf gtpv2-update-bearer-rsp-rx {
           type int32;
           description "Gtpv2 Update Bearer Rsp Rx";
         }
         leaf gtpv2-update-bearer-rsp-tx {
           type int32;
           description "Gtpv2 Update Bearer Rsp Tx";
         }
         leaf gtpv2-delete-bearer-req-rx {
           type int32;
           description "Gtpv2 Delete Bearer Req Rx";
         }
         leaf gtpv2-delete-bearer-req-tx {
           type int32;
           description "Gtpv2 Delete Bearer Req Tx";
         }
         leaf gtpv2-delete-bearer-rsp-rx {
           type int32;
           description "Gtpv2 Delete Bearer Rsp Rx";
         }
         leaf gtpv2-delete-bearer-rsp-tx {
           type int32;
           description "Gtpv2 Delete Bearer Rsp Tx";
         }
         leaf gtpv2-delete-pdn-conn-set-req-rx {
           type int32;
           description "Gtpv2 Delete PDN connection set req rx";
         }
         leaf gtpv2-delete-pdn-conn-set-req-tx {
           type int32;
           description "Gtpv2 Delete PDN connection set req tx";
         }
         leaf gtpv2-delete-pdn-conn-set-rsp-rx {
           type int32;
           description "Gtpv2 Delete PDN connection set rsp rx";
         }
         leaf gtpv2-delete-pdn-conn-set-rsp-tx {
           type int32;
           description "Gtpv2 Delete PDN connection set rsp tx";
         }
         leaf gtpv2-update-pdn-conn-set-req-rx {
           type int32;
           description "Gtpv2 Update PDN connection set req rx";
         }
         leaf gtpv2-update-pdn-conn-set-req-tx {
           type int32;
           description "Gtpv2 Update PDN connection set req tx";
         }
         leaf gtpv2-update-pdn-conn-set-rsp-rx {
           type int32;
           description "Gtpv2 Update PDN connection set rsp rx";
         }
         leaf gtpv2-update-pdn-conn-set-rsp-tx {
           type int32;
           description "Gtpv2 Update PDN connection set rsp tx";
         }
         leaf gtpv2-modify-bearer-cmd-rx {
           type int32;
           description "Gtpv2 Modify bearer command rx";
         }
         leaf gtpv2-modify-bearer-cmd-tx {
           type int32;
           description "Gtpv2 Modify bearer command tx";
         }
         leaf gtpv2-modify-bearer-fail-ind-rx {
           type int32;
           description "Gtpv2 Modify bearer failure indication rx";
         }
         leaf gtpv2-modify-bearer-fail-ind-tx {
           type int32;
           description "Gtpv2 Modify bearer failure indication tx";
         }
         leaf gtpv2-delete-bearer-cmd-rx {
           type int32;
           description "Gtpv2 Delete bearer command rx";
         }
         leaf gtpv2-delete-bearer-cmd-tx {
           type int32;
           description "Gtpv2 Delete bearer command tx";
         }
         leaf gtpv2-delete-bearer-fail-ind-rx {
           type int32;
           description "Gtpv2 Delete bearer failure indication rx";
         }
         leaf gtpv2-delete-bearer-fail-ind-tx {
           type int32;
           description "Gtpv2 Delete bearer failure indication tx";
         }
         leaf gtpv2-bearer-resource-cmd-rx {
           type int32;
           description "Gtpv2 Bearer resource command rx";
         }
         leaf gtpv2-bearer-resource-cmd-tx {
           type int32;
           description "Gtpv2 Bearer resource command tx";
         }
         leaf gtpv2-bearer-resource-fail-ind-rx {
           type int32;
           description "Gtpv2 Bearer resource failure indication rx";
         }
         leaf gtpv2-bearer-resource-fail-ind-tx {
           type int32;
           description "Gtpv2 Bearer resource failure indication tx";
         }
         leaf gtpv2-chg-notif-req-rx {
           type int32;
           description "Gtpv2 Change notification req rx";
         }
         leaf gtpv2-chg-notif-req-tx {
           type int32;
           description "Gtpv2 Change notification req tx";
         }
         leaf gtpv2-chg-notif-rsp-rx {
           type int32;
           description "Gtpv2 Change notification rsp rx";
         }
         leaf gtpv2-chg-notif-rsp-tx {
           type int32;
           description "Gtpv2 Change notification rsp tx";
         }
         leaf gtpv2-release-access-bearer-req-rx {
           type int32;
           description "Gtpv2 Release Access Bearer Req Rx";
         }
         leaf gtpv2-release-access-bearer-req-tx {
           type int32;
           description "Gtpv2 Release Access Bearer Req Tx";
         }
         leaf gtpv2-release-access-bearer-rsp-rx {
           type int32;
           description "Gtpv2 Release Access Bearer Resp Rx";
         }
         leaf gtpv2-release-access-bearer-rsp-tx {
           type int32;
           description "Gtpv2 Release Access Bearer Resp Tx";
         }
         leaf gtpv2-suspend-notification-rx {
           type int32;
           description "Gtpv2 suspend notification Rx";
         }
         leaf gtpv2-suspend-notification-tx {
           type int32;
           description "Gtpv2 suspend notification Tx";
         }
         leaf gtpv2-suspend-acknowledge-rx {
           type int32;
           description "Gtpv2 suspend acknowledge Rx";
         }
         leaf gtpv2-suspend-acknowledge-tx {
           type int32;
           description "Gtpv2 suspend acknowledge Tx";
         }
         leaf gtpv2-resume-notification-rx {
           type int32;
           description "Gtpv2 resume notification Rx";
         }
         leaf gtpv2-resume-notification-tx {
           type int32;
           description "Gtpv2 resume notification Tx";
         }
         leaf gtpv2-resume-acknowledge-rx {
           type int32;
           description "Gtpv2 resume acknowledge Rx";
         }
         leaf gtpv2-resume-acknowledge-tx {
           type int32;
           description "Gtpv2 resume acknowledge Tx";
         }
         leaf gtpv2-create-indirect-data-forward-tunnel-req-rx {
           type int32;
           description "Gtpv2 Create Indirect Data Forward Tunnel Req Rx";
         }
         leaf gtpv2-create-indirect-data-forward-tunnel-req-tx {
           type int32;
           description "Gtpv2 Create Indirect Data Forward Tunnel Req Tx";
         }
         leaf gtpv2-create-indirect-data-forward-tunnel-resp-rx {
           type int32;
           description "Gtpv2 Create Indirect Data Forward Tunnel Resp Rx";
         }
         leaf gtpv2-create-indirect-data-forward-tunnel-resp-tx {
           type int32;
           description "Gtpv2 Create Indirect Data Forward Tunnel Resp Tx";
         }
         leaf gtpv2-delete-indirect-data-forward-tunnel-req-rx {
           type int32;
           description "Gtpv2 Delete Indirect Data Forward Tunnel Req Rx";
         }
         leaf gtpv2-delete-indirect-data-forward-tunnel-req-tx {
           type int32;
           description "Gtpv2 Delete Indirect Data Forward Tunnel Req Tx";
         }
         leaf gtpv2-delete-indirect-data-forward-tunnel-resp-rx {
           type int32;
           description "Gtpv2 Delete Indirect Data Forward Tunnel Resp Rx";
         }
         leaf gtpv2-delete-indirect-data-forward-tunnel-resp-tx {
           type int32;
           description "Gtpv2 Delete Indirect Data Forward Tunnel Resp Tx";
         }
         leaf gtpv2-downlink-data-notif-rx {
           type int32;
           description "Gtpv2 Downlink data notification rx";
         }
         leaf gtpv2-downlink-data-notif-tx {
           type int32;
           description "Gtpv2 Downlink data notification tx";
         }
         leaf gtpv2-downlink-data-notif-ack-rx {
           type int32;
           description "Gtpv2 Downlink data notification ack rx";
         }
         leaf gtpv2-downlink-data-notif-ack-tx {
           type int32;
           description "Gtpv2 Downlink data notification ack tx";
         }
         leaf gtpv2-downlink-data-notif-fail-rx {
           type int32;
           description "Gtpv2 Downlink data notification fail rx";
         }
         leaf gtpv2-downlink-data-notif-fail-tx {
           type int32;
           description "Gtpv2 Downlink data notification fail tx";
         }
         leaf gtpv2-stop-paging-ind-rx {
           type int32;
           description "Gtpv2 Stop Paging Indication rx";
         }
         leaf gtpv2-stop-paging-ind-tx {
           type int32;
           description "Gtpv2 Stop Paging Indication tx";
         }
         leaf gtpv2-cause-req-accept-tx {
           type int32;
           description "GTPv2 Cause Code Request Accepted tx";
         }
         leaf gtpv2-cause-accept-part-tx {
           type int32;
           description "GTPv2 Cause Code Accept Partial tx";
         }
         leaf gtpv2-cause-new-pt-npref-tx {
           type int32;
           description "GTPv2 Cause Code New PDN Type Due to Network Preference tx";
         }
         leaf gtpv2-cause-new-pt-si-addr-br-tx {
           type int32;
           description "GTPv2 Cause Code New PDN Type Due To Single Address Bearer tx";
         }
         leaf gtpv2-cause-local-detach-rx {
           type int32;
           description "GTPv2 Cause Code Local Detach Rx";
         }
         leaf gtpv2-cause-local-detach-tx {
           type int32;
           description "GTPv2 Cause Code Local Detach Tx";
         }
         leaf gtpv2-cause-complete-detach-rx {
           type int32;
           description "GTPv2 Cause Code Complete Detach Rx";
         }
         leaf gtpv2-cause-complete-detach-tx {
           type int32;
           description "GTPv2 Cause Code Complete Detach Tx";
         }
         leaf gtpv2-cause-rat-changed-3gpp-to-non-3gpp-rx {
           type int32;
           description "GTPv2 Cause Code RAT Changed 3GPP to Non 3GPP Rx";
         }
         leaf gtpv2-cause-rat-changed-3gpp-to-non-3gpp-tx {
           type int32;
           description "GTPv2 Cause Code RAT Changed 3GPP to Non 3GPP Tx";
         }
         leaf gtpv2-cause-isr-deactivated-rx {
           type int32;
           description "GTPv2 Cause Code ISR Deactivated Rx";
         }
         leaf gtpv2-cause-isr-deactivated-tx {
           type int32;
           description "GTPv2 Cause Code ISR Deactivated Tx";
         }
         leaf gtpv2-cause-err-ind-from-rnc-enodeb-rx {
           type int32;
           description "GTPv2 Cause Code Err Ind From RNC Enodeb Rx";
         }
         leaf gtpv2-cause-err-ind-from-rnc-enodeb-tx {
           type int32;
           description "GTPv2 Cause Code Err Ind From RNC Enodeb Tx";
         }
         leaf gtpv2-cause-ctx-not-fnd-tx {
           type int32;
           description "GTPv2 Cause Code Context Not Found tx";
         }
         leaf gtpv2-cause-inv-msg-fmt-tx {
           type int32;
           description "GTPv2 Cause Code Invalid Message Format tx";
         }
         leaf gtpv2-cause-ver-not-supp-tx {
           type int32;
           description "GTPv2 Cause Code Version Not Supported tx";
         }
         leaf gtpv2-cause-inv-len-tx {
           type int32;
           description "GTPv2 Cause Code Invalid Length tx";
         }
         leaf gtpv2-cause-serv-not-supp-tx {
           type int32;
           description "GTPv2 Cause Code Service Not Supported tx";
         }
         leaf gtpv2-cause-man-ie-incorr-tx {
           type int32;
           description "GTPv2 Cause Code Mandatory IE Incorrect tx";
         }
         leaf gtpv2-cause-man-ie-miss-tx {
           type int32;
           description "GTPv2 Cause Code Mandatory IE Missing tx";
         }
         leaf gtpv2-cause-opt-ie-incorr-tx {
           type int32;
           description "GTPv2 Cause Code Optional IE Incorrect tx";
         }
         leaf gtpv2-cause-sys-fail-tx {
           type int32;
           description "GTPv2 Cause Code System Failure tx";
         }
         leaf gtpv2-cause-no-res-tx {
           type int32;
           description "GTPv2 Cause Code No Resources tx";
         }
         leaf gtpv2-cause-tft-semantic-err-tx {
           type int32;
           description "GTPv2 Cause Code TFT Semantic Error tx";
         }
         leaf gtpv2-cause-tft-syn-err-tx {
           type int32;
           description "GTPv2 Cause Code TFT Syntactic Error tx";
         }
         leaf gtpv2-cause-pkt-fltr-semantic-err-tx {
           type int32;
           description "GTPv2 Cause Code Packet Filter Semantic Error tx";
         }
         leaf gtpv2-cause-pkt-fltr-syn-err-tx {
           type int32;
           description "GTPv2 Cause Code Packet Filter Syntatctic Error tx";
         }
         leaf gtpv2-cause-miss-unkown-apn-tx {
           type int32;
           description "GTPv2 Cause Code Missing or Unknown APN tx";
         }
         leaf gtpv2-cause-unexp-repeat-ie-tx {
           type int32;
           description "GTPv2 Cause Code Unexpected Repeated IE tx";
         }
         leaf gtpv2-cause-gre-key-not-fnd-tx {
           type int32;
           description "GTPv2 Cause Code GRE Key Not Found tx";
         }
         leaf gtpv2-cause-reloc-fail-tx {
           type int32;
           description "GTPv2 Cause Code Reallocation Failure tx";
         }
         leaf gtpv2-cause-denied-in-rat-tx {
           type int32;
           description "GTPv2 Cause Code Denied In RAT tx";
         }
         leaf gtpv2-cause-pt-not-supp-tx {
           type int32;
           description "GTPv2 Cause Code PDN Type Not Supported tx";
         }
         leaf gtpv2-cause-all-dyn-addr-occ-tx {
           type int32;
           description "GTPv2 Cause Code All Dynamic Addresses Occupied tx";
         }
         leaf gtpv2-cause-no-tft-ue-ctx-exist-tx {
           type int32;
           description "GTPv2 Cause Code UE Context Without TFT Activation tx";
         }
         leaf gtpv2-cause-proto-not-supp-tx {
           type int32;
           description "GTPv2 Cause Code Protocol Not Supported tx";
         }
         leaf gtpv2-cause-ue-not-resp-tx {
           type int32;
           description "GTPv2 Cause Code UE Not Responding tx";
         }
         leaf gtpv2-cause-ue-refuses-tx {
           type int32;
           description "GTPv2 Cause Code UE Refuses tx";
         }
         leaf gtpv2-cause-serv-denied-tx {
           type int32;
           description "GTPv2 Cause Code Service Denied tx";
         }
         leaf gtpv2-cause-unable-page-ue-tx {
           type int32;
           description "GTPv2 Cause Code Unable To Page UE tx";
         }
         leaf gtpv2-cause-no-mem-tx {
           type int32;
           description "GTPv2 Cause Code No Memory tx";
         }
         leaf gtpv2-cause-user-auth-fail-tx {
           type int32;
           description "GTPv2 Cause Code User Auth Failure tx";
         }
         leaf gtpv2-cause-apn-access-denied-tx {
           type int32;
           description "GTPv2 Cause Code APN Access Denied tx";
         }
         leaf gtpv2-cause-req-rej-tx {
           type int32;
           description "GTPv2 Cause Code Request Rejected tx";
         }
         leaf gtpv2-cause-ptmsi-sig-mismatch-rx {
           type int32;
           description "GTPv2 Cause Code P-TMSI Signature Mismatch Rx";
         }
         leaf gtpv2-cause-ptmsi-sig-mismatch-tx {
           type int32;
           description "GTPv2 Cause Code P-TMSI Signature Mismatch Rx";
         }
         leaf gtpv2-cause-imsi-not-known-rx {
           type int32;
           description "GTPv2 Cause Code IMSI Not Known Rx";
         }
         leaf gtpv2-cause-imsi-not-known-tx {
           type int32;
           description "GTPv2 Cause Code IMSI Not Known Tx";
         }
         leaf gtpv2-cause-semantic-err-in-tad-rx {
           type int32;
           description "GTPv2 Cause Code Semantic Error in Tad Rx";
         }
         leaf gtpv2-cause-semantic-err-in-tad-tx {
           type int32;
           description "GTPv2 Cause Code Semantic Error in Tad Tx";
         }
         leaf gtpv2-cause-syntactic-err-in-tad-rx {
           type int32;
           description "GTPv2 Cause Code Syntactic Error in Tad Rx";
         }
         leaf gtpv2-cause-syntactic-err-in-tad-tx {
           type int32;
           description "GTPv2 Cause Code Syntactic Error in Tad Tx";
         }
         leaf gtpv2-cause-rsvd-msg-value-rcvd-rx {
           type int32;
           description "GTPv2 Cause Code Received Message Value Received Rx";
         }
         leaf gtpv2-cause-rsvd-msg-value-rcvd-tx {
           type int32;
           description "GTPv2 Cause Code Received Message Value Received Tx";
         }
         leaf gtpv2-cause-rmt-peer-not-responding-rx {
           type int32;
           description "GTPv2 Cause Code Remote Peer Not Responding Rx";
         }
         leaf gtpv2-cause-rmt-peer-not-responding-tx {
           type int32;
           description "GTPv2 Cause Code Remote Peer Not Responding Tx";
         }
         leaf gtpv2-cause-collision-with-nw-initiated-req-rx {
           type int32;
           description "GTPv2 Cause Code Collision with NW Intiated Req Rx";
         }
         leaf gtpv2-cause-collision-with-nw-initiated-req-tx {
           type int32;
           description "GTPv2 Cause Code Collision with NW Intiated Req Tx";
         }
         leaf gtpv2-cause-unable-page-ue-suspended-rx {
           type int32;
           description "GTPv2 Cause Code Imsi Suspended Rx";
         }
         leaf gtpv2-cause-unable-page-ue-suspended-tx {
           type int32;
           description "GTPv2 Cause Code Unable Page UE Suspended Tx";
         }
         leaf gtpv2-cause-cond-ie-missing-rx {
           type int32;
           description "GTPv2 Cause Code Conditional IE Missing Rx";
         }
         leaf gtpv2-cause-cond-ie-missing-tx {
           type int32;
           description "GTPv2 Cause Code Conditional IE Missing Tx";
         }
         leaf gtpv2-cause-incomp-apn-type-res-rx {
           type int32;
           description "GTPv2 Cause Code APN Restriction Type Incompatible Rx";
         }
         leaf gtpv2-cause-incomp-apn-type-res-tx {
           type int32;
           description "GTPv2 Cause Code APN Restriction Type Incompatible Tx";
         }
         leaf gtpv2-cause-invalid-total-len-rx {
           type int32;
           description "GTPv2 Cause Code Invalid Total Len Rx";
         }
         leaf gtpv2-cause-invalid-total-len-tx {
           type int32;
           description "GTPv2 Cause Code Invalid Total Len Tx";
         }
         leaf gtpv2-cause-data-forwarding-not-supp-rx {
           type int32;
           description "GTPv2 Cause Code Data Forwarding Not Supp Rx";
         }
         leaf gtpv2-cause-data-forwarding-not-supp-tx {
           type int32;
           description "GTPv2 Cause Code Data Forwarding Not Supp Tx";
         }
         leaf gtpv2-cause-invalid-reply-from-rmt-peer-rx {
           type int32;
           description "GTPv2 Cause Code Invalid Reply From Remote Peer Rx";
         }
         leaf gtpv2-cause-invalid-reply-from-rmt-peer-tx {
           type int32;
           description "GTPv2 Cause Code Invalid Reply From Remote Peer Tx";
         }
         leaf gtpv2-cause-invalid-peer-rx {
           type int32;
           description "GTPv2 Cause Code Invalid Peer Rx";
         }
         leaf gtpv2-cause-invalid-peer-tx {
           type int32;
           description "GTPv2 Cause Code Invalid Peer Tx";
         }
         leaf gtpv2-cause-temp-rej-ho-in-prog-rx {
           type int32;
           description "GTPv2 Cause Code Temporarily Reject Handover In Progress";
         }
         leaf gtpv2-cause-temp-rej-ho-in-prog-tx {
           type int32;
           description "GTPv2 Cause Code Temporarily Reject Handover In Progress";
         }
         leaf gtpv2-cause-unknown-rx {
           type int32;
           description "GTPv2 Cause Code Unknown Rx";
         }
         leaf gtpv2-cause-unknown-tx {
           type int32;
           description "GTPv2 Cause Code Unknown Tx";
         }
       }
       container gtpv2-cause-code-stats {
         leaf gtpv2-cause-req-accept-rx {
           type int32;
           description "GTPv2 Cause Code Request Accepted Rx";
         }
         leaf gtpv2-cause-req-accept-tx {
           type int32;
           description "GTPv2 Cause Code Request Accepted tx";
         }
         leaf gtpv2-cause-accept-part-rx {
           type int32;
           description "GTPv2 Cause Code Accept Partial Rx";
         }
         leaf gtpv2-cause-accept-part-tx {
           type int32;
           description "GTPv2 Cause Code Accept Partial tx";
         }
         leaf gtpv2-cause-new-pt-npref-rx {
           type int32;
           description "GTPv2 Cause Code New PDN Type Due to Network Preference Rx";
         }
         leaf gtpv2-cause-new-pt-npref-tx {
           type int32;
           description "GTPv2 Cause Code New PDN Type Due to Network Preference tx";
         }
         leaf gtpv2-cause-new-pt-si-addr-br-rx {
           type int32;
           description "GTPv2 Cause Code New PDN Type Due To Single Address Bearer Rx";
         }
         leaf gtpv2-cause-new-pt-si-addr-br-tx {
           type int32;
           description "GTPv2 Cause Code New PDN Type Due To Single Address Bearer tx";
         }
         leaf gtpv2-cause-local-detach-rx {
           type int32;
           description "GTPv2 Cause Code Local Detach Rx";
         }
         leaf gtpv2-cause-local-detach-tx {
           type int32;
           description "GTPv2 Cause Code Local Detach Tx";
         }
         leaf gtpv2-cause-complete-detach-rx {
           type int32;
           description "GTPv2 Cause Code Complete Detach Rx";
         }
         leaf gtpv2-cause-complete-detach-tx {
           type int32;
           description "GTPv2 Cause Code Complete Detach Tx";
         }
         leaf gtpv2-cause-rat-changed-3gpp-to-non-3gpp-rx {
           type int32;
           description "GTPv2 Cause Code RAT Changed 3GPP to Non 3GPP Rx";
         }
         leaf gtpv2-cause-rat-changed-3gpp-to-non-3gpp-tx {
           type int32;
           description "GTPv2 Cause Code RAT Changed 3GPP to Non 3GPP Tx";
         }
         leaf gtpv2-cause-isr-deactivated-rx {
           type int32;
           description "GTPv2 Cause Code ISR Deactivated Rx";
         }
         leaf gtpv2-cause-isr-deactivated-tx {
           type int32;
           description "GTPv2 Cause Code ISR Deactivated Tx";
         }
         leaf gtpv2-cause-err-ind-from-rnc-enodeb-rx {
           type int32;
           description "GTPv2 Cause Code Err Ind From RNC Enodeb Rx";
         }
         leaf gtpv2-cause-err-ind-from-rnc-enodeb-tx {
           type int32;
           description "GTPv2 Cause Code Err Ind From RNC Enodeb Tx";
         }
         leaf gtpv2-cause-ctx-not-fnd-rx {
           type int32;
           description "GTPv2 Cause Code Context Not Found Rx";
         }
         leaf gtpv2-cause-ctx-not-fnd-tx {
           type int32;
           description "GTPv2 Cause Code Context Not Found tx";
         }
         leaf gtpv2-cause-inv-msg-fmt-rx {
           type int32;
           description "GTPv2 Cause Code Invalid Message Format Rx";
         }
         leaf gtpv2-cause-inv-msg-fmt-tx {
           type int32;
           description "GTPv2 Cause Code Invalid Message Format tx";
         }
         leaf gtpv2-cause-ver-not-supp-rx {
           type int32;
           description "GTPv2 Cause Code Version Not Supported Rx";
         }
         leaf gtpv2-cause-ver-not-supp-tx {
           type int32;
           description "GTPv2 Cause Code Version Not Supported tx";
         }
         leaf gtpv2-cause-inv-len-rx {
           type int32;
           description "GTPv2 Cause Code Invalid Length Rx";
         }
         leaf gtpv2-cause-inv-len-tx {
           type int32;
           description "GTPv2 Cause Code Invalid Length tx";
         }
         leaf gtpv2-cause-serv-not-supp-rx {
           type int32;
           description "GTPv2 Cause Code Service Not Supported Rx";
         }
         leaf gtpv2-cause-serv-not-supp-tx {
           type int32;
           description "GTPv2 Cause Code Service Not Supported tx";
         }
         leaf gtpv2-cause-man-ie-incorr-rx {
           type int32;
           description "GTPv2 Cause Code Mandatory IE Incorrect Rx";
         }
         leaf gtpv2-cause-man-ie-incorr-tx {
           type int32;
           description "GTPv2 Cause Code Mandatory IE Incorrect tx";
         }
         leaf gtpv2-cause-man-ie-miss-rx {
           type int32;
           description "GTPv2 Cause Code Mandatory IE Missing Rx";
         }
         leaf gtpv2-cause-man-ie-miss-tx {
           type int32;
           description "GTPv2 Cause Code Mandatory IE Missing tx";
         }
         leaf gtpv2-cause-opt-ie-incorr-rx {
           type int32;
           description "GTPv2 Cause Code Optional IE Incorrect Rx";
         }
         leaf gtpv2-cause-opt-ie-incorr-tx {
           type int32;
           description "GTPv2 Cause Code Optional IE Incorrect tx";
         }
         leaf gtpv2-cause-sys-fail-rx {
           type int32;
           description "GTPv2 Cause Code System Failure Rx";
         }
         leaf gtpv2-cause-sys-fail-tx {
           type int32;
           description "GTPv2 Cause Code System Failure tx";
         }
         leaf gtpv2-cause-no-res-rx {
           type int32;
           description "GTPv2 Cause Code No Resources Rx";
         }
         leaf gtpv2-cause-no-res-tx {
           type int32;
           description "GTPv2 Cause Code No Resources tx";
         }
         leaf gtpv2-cause-tft-semantic-err-rx {
           type int32;
           description "GTPv2 Cause Code TFT Semantic Error Rx";
         }
         leaf gtpv2-cause-tft-semantic-err-tx {
           type int32;
           description "GTPv2 Cause Code TFT Semantic Error tx";
         }
         leaf gtpv2-cause-tft-syn-err-rx {
           type int32;
           description "GTPv2 Cause Code TFT Syntactic Error Rx";
         }
         leaf gtpv2-cause-tft-syn-err-tx {
           type int32;
           description "GTPv2 Cause Code TFT Syntactic Error tx";
         }
         leaf gtpv2-cause-pkt-fltr-semantic-err-rx {
           type int32;
           description "GTPv2 Cause Code Packet Filter Semantic Error Rx";
         }
         leaf gtpv2-cause-pkt-fltr-semantic-err-tx {
           type int32;
           description "GTPv2 Cause Code Packet Filter Semantic Error tx";
         }
         leaf gtpv2-cause-pkt-fltr-syn-err-rx {
           type int32;
           description "GTPv2 Cause Code Packet Filter Syntatctic Error Rx";
         }
         leaf gtpv2-cause-pkt-fltr-syn-err-tx {
           type int32;
           description "GTPv2 Cause Code Packet Filter Syntatctic Error tx";
         }
         leaf gtpv2-cause-miss-unkown-apn-rx {
           type int32;
           description "GTPv2 Cause Code Missing or Unknown APN Rx";
         }
         leaf gtpv2-cause-miss-unkown-apn-tx {
           type int32;
           description "GTPv2 Cause Code Missing or Unknown APN tx";
         }
         leaf gtpv2-cause-unexp-repeat-ie-rx {
           type int32;
           description "GTPv2 Cause Code Unexpected Repeated IE Rx";
         }
         leaf gtpv2-cause-unexp-repeat-ie-tx {
           type int32;
           description "GTPv2 Cause Code Unexpected Repeated IE tx";
         }
         leaf gtpv2-cause-gre-key-not-fnd-rx {
           type int32;
           description "GTPv2 Cause Code GRE Key Not Found Rx";
         }
         leaf gtpv2-cause-gre-key-not-fnd-tx {
           type int32;
           description "GTPv2 Cause Code GRE Key Not Found tx";
         }
         leaf gtpv2-cause-reloc-fail-rx {
           type int32;
           description "GTPv2 Cause Code Reallocation Failure Rx";
         }
         leaf gtpv2-cause-reloc-fail-tx {
           type int32;
           description "GTPv2 Cause Code Reallocation Failure tx";
         }
         leaf gtpv2-cause-denied-in-rat-rx {
           type int32;
           description "GTPv2 Cause Code Denied In RAT Rx";
         }
         leaf gtpv2-cause-denied-in-rat-tx {
           type int32;
           description "GTPv2 Cause Code Denied In RAT tx";
         }
         leaf gtpv2-cause-pt-not-supp-rx {
           type int32;
           description "GTPv2 Cause Code PDN Type Not Supported Rx";
         }
         leaf gtpv2-cause-pt-not-supp-tx {
           type int32;
           description "GTPv2 Cause Code PDN Type Not Supported tx";
         }
         leaf gtpv2-cause-all-dyn-addr-occ-rx {
           type int32;
           description "GTPv2 Cause Code All Dynamic Addresses Occupied Rx";
         }
         leaf gtpv2-cause-all-dyn-addr-occ-tx {
           type int32;
           description "GTPv2 Cause Code All Dynamic Addresses Occupied tx";
         }
         leaf gtpv2-cause-no-tft-ue-ctx-exist-rx {
           type int32;
           description "GTPv2 Cause Code UE Context Without TFT Activation Rx";
         }
         leaf gtpv2-cause-no-tft-ue-ctx-exist-tx {
           type int32;
           description "GTPv2 Cause Code UE Context Without TFT Activation tx";
         }
         leaf gtpv2-cause-proto-not-supp-rx {
           type int32;
           description "GTPv2 Cause Code Protocol Not Supported Rx";
         }
         leaf gtpv2-cause-proto-not-supp-tx {
           type int32;
           description "GTPv2 Cause Code Protocol Not Supported tx";
         }
         leaf gtpv2-cause-ue-not-resp-rx {
           type int32;
           description "GTPv2 Cause Code UE Not Responding Rx";
         }
         leaf gtpv2-cause-ue-not-resp-tx {
           type int32;
           description "GTPv2 Cause Code UE Not Responding tx";
         }
         leaf gtpv2-cause-ue-refuses-rx {
           type int32;
           description "GTPv2 Cause Code UE Refuses Rx";
         }
         leaf gtpv2-cause-ue-refuses-tx {
           type int32;
           description "GTPv2 Cause Code UE Refuses tx";
         }
         leaf gtpv2-cause-serv-denied-rx {
           type int32;
           description "GTPv2 Cause Code Service Denied Rx";
         }
         leaf gtpv2-cause-serv-denied-tx {
           type int32;
           description "GTPv2 Cause Code Service Denied tx";
         }
         leaf gtpv2-cause-unable-page-ue-rx {
           type int32;
           description "GTPv2 Cause Code Unable To Page UE Rx";
         }
         leaf gtpv2-cause-unable-page-ue-tx {
           type int32;
           description "GTPv2 Cause Code Unable To Page UE tx";
         }
         leaf gtpv2-cause-no-mem-rx {
           type int32;
           description "GTPv2 Cause Code No Memory Rx";
         }
         leaf gtpv2-cause-no-mem-tx {
           type int32;
           description "GTPv2 Cause Code No Memory tx";
         }
         leaf gtpv2-cause-user-auth-fail-rx {
           type int32;
           description "GTPv2 Cause Code User Auth Failure Rx";
         }
         leaf gtpv2-cause-user-auth-fail-tx {
           type int32;
           description "GTPv2 Cause Code User Auth Failure tx";
         }
         leaf gtpv2-cause-apn-access-denied-rx {
           type int32;
           description "GTPv2 Cause Code APN Access Denied Rx";
         }
         leaf gtpv2-cause-apn-access-denied-tx {
           type int32;
           description "GTPv2 Cause Code APN Access Denied tx";
         }
         leaf gtpv2-cause-req-rej-rx {
           type int32;
           description "GTPv2 Cause Code Request Rejected Rx";
         }
         leaf gtpv2-cause-req-rej-tx {
           type int32;
           description "GTPv2 Cause Code Request Rejected tx";
         }
         leaf gtpv2-cause-ptmsi-sig-mismatch-rx {
           type int32;
           description "GTPv2 Cause Code P-TMSI Signature Mismatch Rx";
         }
         leaf gtpv2-cause-ptmsi-sig-mismatch-tx {
           type int32;
           description "GTPv2 Cause Code P-TMSI Signature Mismatch Rx";
         }
         leaf gtpv2-cause-imsi-not-known-rx {
           type int32;
           description "GTPv2 Cause Code IMSI Not Known Rx";
         }
         leaf gtpv2-cause-imsi-not-known-tx {
           type int32;
           description "GTPv2 Cause Code IMSI Not Known Tx";
         }
         leaf gtpv2-cause-semantic-err-in-tad-rx {
           type int32;
           description "GTPv2 Cause Code Semantic Error in Tad Rx";
         }
         leaf gtpv2-cause-semantic-err-in-tad-tx {
           type int32;
           description "GTPv2 Cause Code Semantic Error in Tad Tx";
         }
         leaf gtpv2-cause-syntactic-err-in-tad-rx {
           type int32;
           description "GTPv2 Cause Code Syntactic Error in Tad Rx";
         }
         leaf gtpv2-cause-syntactic-err-in-tad-tx {
           type int32;
           description "GTPv2 Cause Code Syntactic Error in Tad Tx";
         }
         leaf gtpv2-cause-rsvd-msg-value-rcvd-rx {
           type int32;
           description "GTPv2 Cause Code Received Message Value Received Rx";
         }
         leaf gtpv2-cause-rsvd-msg-value-rcvd-tx {
           type int32;
           description "GTPv2 Cause Code Received Message Value Received Tx";
         }
         leaf gtpv2-cause-rmt-peer-not-responding-rx {
           type int32;
           description "GTPv2 Cause Code Remote Peer Not Responding Rx";
         }
         leaf gtpv2-cause-rmt-peer-not-responding-tx {
           type int32;
           description "GTPv2 Cause Code Remote Peer Not Responding Tx";
         }
         leaf gtpv2-cause-collision-with-nw-initiated-req-rx {
           type int32;
           description "GTPv2 Cause Code Collision with NW Intiated Req Rx";
         }
         leaf gtpv2-cause-collision-with-nw-initiated-req-tx {
           type int32;
           description "GTPv2 Cause Code Collision with NW Intiated Req Tx";
         }
         leaf gtpv2-cause-unable-page-ue-suspended-rx {
           type int32;
           description "GTPv2 Cause Code Imsi Suspended Rx";
         }
         leaf gtpv2-cause-unable-page-ue-suspended-tx {
           type int32;
           description "GTPv2 Cause Code Unable Page UE Suspended Tx";
         }
         leaf gtpv2-cause-cond-ie-missing-rx {
           type int32;
           description "GTPv2 Cause Code Conditional IE Missing Rx";
         }
         leaf gtpv2-cause-cond-ie-missing-tx {
           type int32;
           description "GTPv2 Cause Code Conditional IE Missing Tx";
         }
         leaf gtpv2-cause-incomp-apn-type-res-rx {
           type int32;
           description "GTPv2 Cause Code APN Restriction Type Incompatible Rx";
         }
         leaf gtpv2-cause-incomp-apn-type-res-tx {
           type int32;
           description "GTPv2 Cause Code APN Restriction Type Incompatible Tx";
         }
         leaf gtpv2-cause-invalid-total-len-rx {
           type int32;
           description "GTPv2 Cause Code Invalid Total Len Rx";
         }
         leaf gtpv2-cause-invalid-total-len-tx {
           type int32;
           description "GTPv2 Cause Code Invalid Total Len Tx";
         }
         leaf gtpv2-cause-data-forwarding-not-supp-rx {
           type int32;
           description "GTPv2 Cause Code Data Forwarding Not Supp Rx";
         }
         leaf gtpv2-cause-data-forwarding-not-supp-tx {
           type int32;
           description "GTPv2 Cause Code Data Forwarding Not Supp Tx";
         }
         leaf gtpv2-cause-invalid-reply-from-rmt-peer-rx {
           type int32;
           description "GTPv2 Cause Code Invalid Reply From Remote Peer Rx";
         }
         leaf gtpv2-cause-invalid-reply-from-rmt-peer-tx {
           type int32;
           description "GTPv2 Cause Code Invalid Reply From Remote Peer Tx";
         }
         leaf gtpv2-cause-invalid-peer-rx {
           type int32;
           description "GTPv2 Cause Code Invalid Peer Rx";
         }
         leaf gtpv2-cause-invalid-peer-tx {
           type int32;
           description "GTPv2 Cause Code Invalid Peer Tx";
         }
         leaf gtpv2-cause-temp-rej-ho-in-prog-rx {
           type int32;
           description "GTPv2 Cause Code Temporarily Reject Handover In Progress";
         }
         leaf gtpv2-cause-temp-rej-ho-in-prog-tx {
           type int32;
           description "GTPv2 Cause Code Temporarily Reject Handover In Progress";
         }
         leaf gtpv2-cause-unknown-rx {
           type int32;
           description "GTPv2 Cause Code Unknown Rx";
         }
         leaf gtpv2-cause-unknown-tx {
           type int32;
           description "GTPv2 Cause Code Unknown Tx";
         }
       }
     }
     leaf error-msg {
       type string;
       description "Error message";
     }
   }
   grouping mobile-gateway-service-mode-block {
     leaf gateway-name {
       type string;
       description "Mobile Gateway Name";
     }
     leaf mm-service-mode {
       type string;
       description "Service Mode Maintenance status for a profile";
     }
     container mm-service-mode-description {
       leaf mm-service-mode {
         type string;
         description "Service Mode Maintenance status for a profile";
       }
       leaf mm-service-mode-pending-mm-ack {
         type string;
       }
       leaf mm-service-mode-pending-ready-ack {
         type string;
       }
       list mobiled-session-description {
         leaf mobiled-client {
           type string;
           description "Mobiled Client - Could be RE or one of the SPICs";
         }
         leaf mobiled-peer-list {
           type string;
           description "Mobiled Peer List - Apps separated by commas";
         }
       }
       list mobiled-session-description2 {
         leaf mobiled-client {
           type string;
           description "Mobiled Client - Could be RE or one of the SPICs";
         }
         leaf mobiled-peer-list {
           type string;
           description "Mobiled Peer List - Apps separated by commas";
         }
       }
     }
   }
   grouping gateway-system-interface-service-mode-block {
     leaf gw-interface-name {
       type string;
       description "Interface Name";
     }
     leaf gateway-name {
       type string;
       description "Mobile Gateway Name";
     }
     leaf mm-service-mode {
       type string;
       description "Service Mode Maintenance status for a profile";
     }
     container mm-service-mode-description {
       leaf mm-service-mode {
         type string;
         description "Service Mode Maintenance status for a profile";
       }
       leaf mm-service-mode-pending-mm-ack {
         type string;
       }
       leaf mm-service-mode-pending-ready-ack {
         type string;
       }
       list mobiled-session-description {
         leaf mobiled-client {
           type string;
           description "Mobiled Client - Could be RE or one of the SPICs";
         }
         leaf mobiled-peer-list {
           type string;
           description "Mobiled Peer List - Apps separated by commas";
         }
       }
       list mobiled-session-description2 {
         leaf mobiled-client {
           type string;
           description "Mobiled Client - Could be RE or one of the SPICs";
         }
         leaf mobiled-peer-list {
           type string;
           description "Mobiled Peer List - Apps separated by commas";
         }
       }
     }
   }
   grouping mobile-gateways-ip-reassembly-statistics-block {
     container ipreassm-gw-hdr {
       leaf ipreassm-gw-name {
         type string;
         description "Gateway name";
       }
     }
     list ip-reassm-stats {
       leaf first-fragments {
         type uint64;
         description "Number of first fragments";
       }
       leaf non-first-fragments {
         type uint64;
         description "Number of non-first fragments";
       }
       leaf total-fragments {
         type uint64;
         description "Total number of fragments";
       }
       leaf reassembled-pkts {
         type uint64;
         description "Total number of re-assembled packets";
       }
       leaf merged-pkts {
         type uint64;
         description "Total number of merged packets";
       }
       leaf reassm-pending-pkts {
         type uint64;
         description "Total number of packets pending reassembly";
       }
       leaf timedout-pkts {
         type uint64;
         description "Total number of timed out fragmented packets";
       }
       leaf timedout-frags {
         type uint64;
         description "Total number of timed out fragments";
       }
       leaf reassm-pkt-drop-exceed-max-len {
         type uint64;
         description "Total number of packets dropped because of exceeding maximum length after re-assembly";
       }
       leaf invalid-len-frag {
         type uint64;
         description "Total number of invalid length fragments received";
       }
       leaf overlap-rx-frag {
         type uint64;
         description "Total number of overlapping fragments received";
       }
       leaf dup-rx-frag {
         type uint64;
         description "Total number of duplicate fragments received";
       }
       leaf frag-drop-no-buf {
         type uint64;
         description "Total number of fragments dropped because of no buffers";
       }
       leaf frag-drop-pkt-lim-exceed {
         type uint64;
         description "Total number of fragments dropped because of exceeding packet limit";
       }
       leaf total-fragments-dropped {
         type uint64;
         description "Total number of fragments dropped";
       }
       leaf ipreassm-fpc-slot {
         type int32;
         description "FPC slot";
       }
       leaf ipreassm-pic-slot {
         type int32;
         description "PIC slot";
       }
     }
   }
   grouping cac-statistics-block {
     container mcos-mobile-gateways-gateway-name {
       leaf mcos-gateway-name {
         type string;
       }
     }
     container cac-gw-level-statistics {
       leaf bearer-load-rejects-lthr {
         type int32;
         description "Bearer Load Rejects (L-THR) ";
       }
       leaf bearer_load_rejects_hthr {
         type int32;
         description "Bearer Load Rejects (H-THR) ";
       }
       leaf bearer-load-admits-in-h-thr {
         type int32;
         description "Bearer Load Admits in H-THR ";
       }
       leaf memory-load-rejects-lthr {
         type int32;
         description "Memory Load Rejects (L-THR) ";
       }
       leaf memory-load-rejects-hthr {
         type int32;
         description "Memory Load Rejects (H-THR) ";
       }
       leaf memory-load-admit-and-preempt {
         type int32;
         description "Memory Load Admit & Preempt ";
       }
       leaf cpu-load-rejects-lthr {
         type int32;
         description "CPU Load Rejects (L-THR) ";
       }
       leaf cpu-load-rejects-hthr {
         type int32;
         description "CPU Load Rejects (H-THR) ";
       }
       leaf memory-high-rejects {
         type int32;
         description "Memory High Rejects ";
       }
       leaf cpu-high-rejects {
         type int32;
         description "CPU High Rejects ";
       }
       leaf bearer-reservation-rejects {
         type int32;
         description "Bearer Reservation Rejects ";
       }
       leaf takedowns-due-to-preemption {
         type int32;
         description "Takedowns due to Preemption ";
       }
       leaf cac-preemption-job-trigger {
         type int32;
         description "Preemption Job triggers";
       }
       leaf gateway-bearer-count {
         type int32;
         description "Gateway bearer count ";
       }
       leaf cac-invalid-def-br-spad {
         type int32;
         description "Invalid Default Bearer spad";
       }
       leaf bearer-load-admints-in-h-thr {
         type int32;
         description "Bearer Load Admits in H-THR ";
       }
       leaf memory-load-admits-hthr {
         type int32;
         description "Memory Load Admits (H-THR) ";
       }
       leaf bearer-load-redirects-lthr {
         type int32;
         description "Bearer Load Redirects (L-THR)";
       }
       leaf memory-load-redirects-lthr {
         type int32;
         description "Memory Load Redirects (L-THR)";
       }
       leaf cpu-load-redirects-lthr {
         type int32;
         description "CPU Load Redirects (L-THR) ";
       }
       leaf bearer-load-redirects-hthr {
         type int32;
         description "Bearer Load Redirects (H-THR)";
       }
       leaf memory-load-redirects-hthr {
         type int32;
         description "Memory Load Redirects (H-THR)";
       }
       leaf cpu-load-redirects-hthr {
         type int32;
         description "CPU Load Redirects (H-THR) ";
       }
       leaf mcos-redirect-stats-for-spic {
         type string;
         description "PFE Id";
       }
       leaf mcos-redirect-stats-counter {
         type int32;
         description "Statistics Counter value for the PFE";
       }
       list mcos-redirect-stats-breakup {
         list mcos-redirect-stats-aggr {
           leaf mcos-redirect-stats-aggr-type {
             type string;
             description "Redirect statistics aggregated from PFEs";
           }
           leaf mcos-redirect-stats-aggr-counter {
             type int32;
             description "Redirect statistics aggregated from PFEs";
           }
           leaf mcos-redirect-stats-for-spic {
             type string;
             description "PFE Id";
           }
           leaf mcos-redirect-stats-counter {
             type int32;
             description "Statistics Counter value for the PFE";
           }
         }
         leaf mcos-stats-threshold-type {
           type string;
           description "High / Low Threshold";
         }
       }
       leaf apfe-total-def-dmem-resource-unavailable {
         type int32;
         description "APFE dmem resource Unavailable while trying to create default bearer ";
       }
       leaf apfe-total-def-bearer-resource-unavailable {
         type int32;
         description "APFE bearer resource Unavailable while trying to create default bearer ";
       }
       leaf apfe-def-gbr-bw-resource-unavailable {
         type int32;
         description "APFE GBR Bandwidth resource Unavailable while trying to create default bearer ";
       }
       leaf apfe-def-bearer-resource-unavailable {
         type int32;
         description "APFE def bearer resource Unavailable ";
       }
       leaf apfe-dedi-dmem-resource-unavailable {
         type int32;
         description "APFE dmem resource Unavailable while trying to create dedicated bearer ";
       }
       leaf apfe-dedi-bearer-resource-unavailable {
         type int32;
         description "APFE bearer resource Unavailable while trying to create dedicated bearer ";
       }
       leaf apfe-dedi-gbr-bw-resource-unavailable {
         type int32;
         description "APFE GBR Bandwidth resource Unavailable while trying to create dedicated bearer ";
       }
       leaf bw-policy-rejects {
         type int32;
         description "BW Policy Rejects ";
       }
       leaf cos-policy-rejects {
         type int32;
         description "COS Policy Rejects ";
       }
       leaf apfe-sdf-resource-unavailable {
         type int32;
         description "APFE SDF resource Unavailable while trying to create/modify bearer";
       }
       leaf nbm-ipv4-prefixes-unavailable {
         type int32;
         description "NBM IPv4 Prefixes Unavailable ";
       }
       leaf nbm_ipv6_prefixes_unavailable {
         type int32;
         description "NBM IPv6 Prefixes Unavailable ";
       }
       leaf cac-rsv-fail-reject-indt {
         type int32;
         description "Indirect tunnel reject ";
       }
       leaf cac-apfe-rsv-fail-reject-indt {
         type int32;
         description "Indirect tunnel APFE resource unavailable ";
       }
       leaf memory-high-redirects {
         type int32;
         description "Memory High Redirects ";
       }
       leaf cpu-high-redirects {
         type int32;
         description "CPU High Redirects ";
       }
       leaf bearer-reservation-redirects {
         type int32;
         description "Bearer Reservation Redirects ";
       }
     }
     container cac-apn-level-statistics {
       leaf bearer-load-rejects-lthr {
         type int32;
         description "Bearer Load Rejects (L-THR) ";
       }
       leaf bearer_load_rejects_hthr {
         type int32;
         description "Bearer Load Rejects (H-THR) ";
       }
       leaf bearer-load-admits-in-h-thr {
         type int32;
         description "Bearer Load Admits in H-THR ";
       }
       leaf memory-load-rejects-lthr {
         type int32;
         description "Memory Load Rejects (L-THR) ";
       }
       leaf memory-load-rejects-hthr {
         type int32;
         description "Memory Load Rejects (H-THR) ";
       }
       leaf memory-load-admit-and-preempt {
         type int32;
         description "Memory Load Admit & Preempt ";
       }
       leaf cpu-load-rejects-lthr {
         type int32;
         description "CPU Load Rejects (L-THR) ";
       }
       leaf cpu-load-rejects-hthr {
         type int32;
         description "CPU Load Rejects (H-THR) ";
       }
       leaf bw-policy-rejects {
         type int32;
         description "BW Policy Rejects ";
       }
       leaf cos-policy-rejects {
         type int32;
         description "COS Policy Rejects ";
       }
       leaf bearer-reservation-rejects {
         type int32;
         description "Bearer Reservation Rejects ";
       }
       leaf bearer-load-admints-in-h-thr {
         type int32;
         description "Bearer Load Admits in H-THR ";
       }
       leaf memory-load-admits-hthr {
         type int32;
         description "Memory Load Admits (H-THR) ";
       }
       leaf bearer-load-redirects-lthr {
         type int32;
         description "Bearer Load Redirects (L-THR)";
       }
       leaf memory-load-redirects-lthr {
         type int32;
         description "Memory Load Redirects (L-THR)";
       }
       leaf cpu-load-redirects-lthr {
         type int32;
         description "CPU Load Redirects (L-THR) ";
       }
       leaf bearer-load-redirects-hthr {
         type int32;
         description "Bearer Load Redirects (H-THR)";
       }
       leaf memory-load-redirects-hthr {
         type int32;
         description "Memory Load Redirects (H-THR)";
       }
       leaf cpu-load-redirects-hthr {
         type int32;
         description "CPU Load Redirects (H-THR) ";
       }
       leaf mcos-redirect-stats-for-spic {
         type string;
         description "PFE Id";
       }
       leaf mcos-redirect-stats-counter {
         type int32;
         description "Statistics Counter value for the PFE";
       }
       list mcos-redirect-stats-breakup {
         leaf mcos-stats-threshold-type {
           type string;
           description "High / Low Threshold";
         }
         list mcos-redirect-stats-aggr {
           leaf mcos-redirect-stats-aggr-type {
             type string;
             description "Redirect statistics aggregated from PFEs";
           }
           leaf mcos-redirect-stats-aggr-counter {
             type int32;
             description "Redirect statistics aggregated from PFEs";
           }
           leaf mcos-redirect-stats-for-spic {
             type string;
             description "PFE Id";
           }
           leaf mcos-redirect-stats-counter {
             type int32;
             description "Statistics Counter value for the PFE";
           }
         }
       }
       leaf bearer-reservation-redirects {
         type int32;
         description "Bearer Reservation Redirects ";
       }
     }
   }
   grouping mobile-gateway-aaa-diam-ne-statistics-block {
     list aaa-diam-ne-stats {
       leaf aaa-diam-ne-name {
         type string;
         description "Diameter NE name";
       }
       leaf aaa-diam-ne-pkts-in {
         type uint64;
         description "Number of incoming packets";
       }
       leaf aaa-diam-ne-pkts-out {
         type uint64;
         description "Number of outgoing packets";
       }
       leaf aaa-diam-ne-request-timeout {
         type uint64;
         description "Number of request timeouts";
       }
       leaf aaa-diam-ne-ccr-out {
         type uint64;
         description "Number of outgoing credit control request";
       }
       leaf aaa-diam-ne-cca-in {
         type uint64;
         description "Number of incoming credit control answer";
       }
       leaf aaa-mobile-gateway-name {
         type string;
         description "Gateway Name";
       }
       leaf aaa-fpc-pic {
         type string;
         description "FPC/PIC slot information";
       }
     }
   }
   grouping mobile-gateway-aaa-diam-ne-status-block {
     list aaa-diam-ne-status {
       leaf aaa-diam-ne-name {
         type string;
         description "Diameter NE name";
       }
       list aaa-diam-ne-peer-status {
         leaf aaa-diam-peer-name {
           type string;
           description "Diameter Peer name";
         }
         list aaa-diam-ne-fpc-pic-peer-status {
           leaf aaa-fpc-pic {
             type string;
             description "FPC/PIC slot information";
           }
           leaf aaa-diam-peer-state {
             type string;
             description "Current state";
           }
           leaf aaa-diam-peer-watchdog-state {
             type string;
             description "Watchdog State";
           }
         }
       }
     }
   }
   grouping mobile-gateway-aaa-diam-peer-statistics-block {
     leaf aaa-diam-peer-name {
       type string;
       description "Diameter Peer name";
     }
     list aaa-diam-peer-spic-stats {
       leaf aaa-fpc-pic {
         type string;
         description "FPC/PIC slot information";
       }
       container aaa-diam-peer-error-stats {
         leaf aaa-diam-peer-request-timeout {
           type uint64;
           description "Number of request timeouts";
         }
         leaf aaa-diam-peer-tot-retx {
           type uint64;
           description "Number of Retransmissions";
         }
         leaf aaa-diam-peer-redirect-events {
           type uint64;
           description "Number of redirect events";
         }
         leaf aaa-diam-peer-conn-failures {
           type uint64;
           description "Number of Connection failures";
         }
         leaf aaa-diam-peer-dup-requests {
           type uint64;
           description "Number of Duplicate requests";
         }
         leaf aaa-diam-peer-malformed-msgs {
           type uint64;
           description "Number of Malformed Request";
         }
         leaf aaa-diam-peer-drop-responses {
           type uint64;
           description "Number of Dropped Responses";
         }
         leaf aaa-diam-peer-drop-requests {
           type uint64;
           description "Number of Dropped Requests";
         }
         leaf aaa-diam-peer-last-disc-cause {
           type uint64;
           description "Last Disconnect Cause";
         }
         leaf aaa-diam-peer-transport-fail {
           type uint64;
           description "Number of Transport Failures";
         }
         leaf aaa-diam-peer-unknown-type {
           type uint64;
           description "Number of Unknown Type Errors";
         }
         leaf aaa-diam-peer-unknown-application {
           type uint64;
           description "Number of Unknown Application Errors";
         }
         leaf aaa-diam-peer-high-watermark-hit {
           type uint64;
           description "Number of times high-watermark is hit";
         }
         leaf aaa-diam-peer-low-watermark-hit {
           type uint64;
           description "Number of times low-watermark is hit";
         }
         leaf aaa-diam-peer-dev-watchdog-failures {
           type uint64;
           description "Number of Device Watchdog Failures";
         }
         leaf aaa-diam-peer-cap-xchng-failures {
           type uint64;
           description "Number of Capabelity Exchange failures";
         }
       }
       container aaa-diam-peer-msg-stats {
         leaf aaa-diam-peer-total-msgs-trans {
           type uint64;
           description "Number of Messages Transmitted";
         }
         leaf aaa-diam-peer-total-msgs-rcvd {
           type uint64;
           description "Number of Messages Received";
         }
         leaf aaa-diam-peer-cc-req-out {
           type uint64;
           description "Number of Outgoing Credit Control Request";
         }
         leaf aaa-diam-peer-cc-req-in {
           type uint64;
           description "Number of incoming  Credit Control Request";
         }
         leaf aaa-diam-peer-cc-ans-out {
           type uint64;
           description "Number of Outgoing Credit Control Ansers";
         }
         leaf aaa-diam-peer-cc-ans-in {
           type uint64;
           description "Number of Incoming Credit Control Answer";
         }
         leaf aaa-diam-peer-re-auth-req-out {
           type uint64;
           description "Number of outgoing Re-Auth Request";
         }
         leaf aaa-diam-peer-re-auth-req-in {
           type uint64;
           description "Number of incoming Re-Auth Request";
         }
         leaf aaa-diam-peer-re-auth-ans-out {
           type uint64;
           description "Number of outgoing Re-Auth Answer";
         }
         leaf aaa-diam-peer-re-auth-ans-in {
           type uint64;
           description "Number of incoming Re-Auth Answer";
         }
         leaf aaa-diam-peer-abrt-sess-req-out {
           type uint64;
           description "Number of outgoing Abort Session Request";
         }
         leaf aaa-diam-peer-abrt-sess-req-in {
           type uint64;
           description "Number of incoming Abort Session Request";
         }
         leaf aaa-diam-peer-abrt-sess-ans-out {
           type uint64;
           description "Number of outgoing Abort Session Answer";
         }
         leaf aaa-diam-peer-abrt-sess-ans-in {
           type uint64;
           description "Number of incoming Abort Session Answer";
         }
         leaf aaa-diam-peer-cap-xchng-req-out {
           type uint64;
           description "Number of outgoing Capability Exchange Request";
         }
         leaf aaa-diam-peer-cap-xchng-req-in {
           type uint64;
           description "Number of incoming Capability Exchange Request";
         }
         leaf aaa-diam-peer-cap-xchng-ans-out {
           type uint64;
           description "Number of outgoing Capability Exchange Answer";
         }
         leaf aaa-diam-peer-cap-xchng-ans-in {
           type uint64;
           description "Number of incoming Capability Exchange Answer";
         }
         leaf aaa-diam-peer-dev-watchdog-req-out {
           type uint64;
           description "Number of outgoing Device Watchdog Request";
         }
         leaf aaa-diam-peer-dev-watchdog-req-in {
           type uint64;
           description "Number of incoming Device Watchdog Request";
         }
         leaf aaa-diam-peer-dev-watchdog-ans-out {
           type uint64;
           description "Number of outgoing Device Watchdog Answer";
         }
         leaf aaa-diam-peer-dev-watchdog-ans-in {
           type uint64;
           description "Number of incoming Device Watchdog Answer";
         }
         leaf aaa-diam-peer-discnt-peer-req-out {
           type uint64;
           description "Number of outgoing Disconnect Peer Request";
         }
         leaf aaa-diam-peer-discnt-peer-req-in {
           type uint64;
           description "Number of incoming Disconnect Peer Request";
         }
         leaf aaa-diam-peer-discnt-peer-ans-out {
           type uint64;
           description "Number of outgoing Disconnect Peer Answer";
         }
         leaf aaa-diam-peer-discnt-peer-ans-in {
           type uint64;
           description "Number of incoming Disconnect Peer Answer";
         }
       }
       container aaa-diam-peer-fail-stats {
         leaf aaa-diam-peer-perm-fail-out {
           type uint64;
           description "Number of Permanent Failures Transmitted";
         }
         leaf aaa-diam-peer-perm-fail-in {
           type uint64;
           description "Number of Permanent Failures Received";
         }
         leaf aaa-diam-peer-protocol-err-out {
           type uint64;
           description "Number of Protocol Errors Transmitted";
         }
         leaf aaa-diam-peer-protocol-err-in {
           type uint64;
           description "Number of Protocol Errors received ";
         }
         leaf aaa-diam-peer-transient-fail-out {
           type uint64;
           description "Number of Transient Failures Transmitted";
         }
         leaf aaa-diam-peer-transient-fail-in {
           type uint64;
           description "Number of Transient Failures Received";
         }
       }
     }
   }
   grouping mobile-gateway-aaa-diam-peer-status-block {
     list aaa-diam-peer-status {
       leaf aaa-mobile-gateway-name {
         type string;
         description "Gateway Name";
       }
       leaf aaa-diam-peer-name {
         type string;
         description "Diameter Peer name";
       }
       leaf aaa-fpc-pic {
         type string;
         description "FPC/PIC slot information";
       }
       leaf aaa-diam-peer-state {
         type string;
         description "Current state";
       }
       leaf aaa-diam-peer-state-duration {
         type string;
         description "Duration of the diameter peer in the current state";
       }
       leaf aaa-diam-peer-watchdog-state {
         type string;
         description "Watchdog State";
       }
       leaf aaa-diam-peer-origin-host {
         type string;
         description "Diameter Origin Host";
       }
       leaf aaa-diam-peer-origin-realm {
         type string;
         description "Diamter Origin Realm";
       }
       leaf aaa-diam-peer-address {
         type string;
         description "Diameter peer address";
       }
       leaf aaa-diam-peer-port {
         type uint64;
         description "Diameter peer port";
       }
       leaf aaa-diam-source-address {
         type string;
         description "Local Ip addressed used to connect to peer ";
       }
       leaf aaa-diam-source-port {
         type uint64;
         description "Local port number used to connect to peer";
       }
     }
   }
   grouping mobile-gateway-status-block {
     container mobile-gateway-status-brief {
       leaf active-subscriber-count {
         type uint32;
         description "Number of active subscribers";
       }
       leaf active-svc-subscriber-count {
         type uint32;
         description "Number of active subscribers with services";
       }
       leaf active-session-count {
         type uint32;
         description "Number of active sessions";
       }
       leaf active-svc-session-count {
         type uint64;
         description "Number of active sessions with services";
       }
       leaf active-bearer-count {
         type uint32;
         description "Number of active bearers";
       }
       leaf active-prepaid-bearers {
         type uint32;
         description "Number of active prepaid bearers";
       }
       leaf active-postpaid-bearers {
         type uint32;
         description "Number of active postpaid bearers";
       }
       leaf active-gbr-bearers {
         type uint32;
         description "Number of active GBR bearers";
       }
       leaf active-non-gbr-bearers {
         type uint32;
         description "Number of active Non-GBR bearers";
       }
       leaf cpu-load {
         type uint32;
         description "Current CPU load";
       }
       leaf memory-load {
         type uint32;
         description "Current Memory load";
       }
       leaf pdn-type-ipv4-session-count {
         type uint32;
         description "Ipv4 session count";
       }
       leaf pdn-type-ipv6-session-count {
         type uint32;
         description "Ipv6 session count";
       }
       leaf pdn-type-ipv46-session-count {
         type uint32;
         description "Ipv46 session count";
       }
       leaf roaming-status-type-home-session-count {
         type uint32;
         description "Roaming status home session count";
       }
       leaf roaming-status-type-roamer-session-count {
         type uint32;
         description "Roaming status roamer session count";
       }
       leaf roaming-status-type-visitor-session-count {
         type uint32;
         description "Roaming status visitor session count";
       }
       leaf idle-subscriber-count {
         type uint32;
         description "Number of idle subscribers";
       }
       leaf idle-session-count {
         type uint32;
         description "Number of idle sessions";
       }
       leaf idle-bearer-count {
         type uint32;
         description "Number of idle bearers";
       }
       leaf susp-subscriber-count {
         type uint32;
         description "Number of suspended subscribers";
       }
       leaf susp-session-count {
         type uint32;
         description "Number of suspended sessions";
       }
       leaf susp-bearer-count {
         type uint32;
         description "Number of suspended bearers";
       }
       leaf indt-tunn-count {
         type uint32;
         description "Number of indirect tunnels";
       }
       leaf dt-tunn-count {
         type uint32;
         description "Number of direct tunnels";
       }
     }
     container mobile-gateway-status-detail {
       leaf fpc-slot {
         type int32;
         description "FPC slot";
       }
       leaf pic-slot {
         type int32;
         description "PIC slot";
       }
       leaf pic-role {
         type string;
         description "PIC Role Information Standalone/Primary/Secondary";
       }
       leaf pic-type {
         type string;
         description "Client type";
       }
       leaf active-subscriber-count {
         type uint32;
         description "Number of active subscribers";
       }
       leaf active-svc-subscriber-count {
         type uint32;
         description "Number of active subscribers with services";
       }
       leaf active-session-count {
         type uint32;
         description "Number of active sessions";
       }
       leaf active-svc-session-count {
         type uint64;
         description "Number of active sessions with services";
       }
       leaf active-bearer-count {
         type uint32;
         description "Number of active bearers";
       }
       leaf active-prepaid-bearers {
         type uint32;
         description "Number of active prepaid bearers";
       }
       leaf active-postpaid-bearers {
         type uint32;
         description "Number of active postpaid bearers";
       }
       leaf active-gbr-bearers {
         type uint32;
         description "Number of active GBR bearers";
       }
       leaf active-non-gbr-bearers {
         type uint32;
         description "Number of active Non-GBR bearers";
       }
       leaf cpu-load {
         type uint32;
         description "Current CPU load";
       }
       leaf memory-load {
         type uint32;
         description "Current Memory load";
       }
       leaf pdn-type-ipv4-session-count {
         type uint32;
         description "Ipv4 session count";
       }
       leaf pdn-type-ipv6-session-count {
         type uint32;
         description "Ipv6 session count";
       }
       leaf pdn-type-ipv46-session-count {
         type uint32;
         description "Ipv46 session count";
       }
       leaf roaming-status-type-home-session-count {
         type uint32;
         description "Roaming status home session count";
       }
       leaf roaming-status-type-roamer-session-count {
         type uint32;
         description "Roaming status roamer session count";
       }
       leaf roaming-status-type-visitor-session-count {
         type uint32;
         description "Roaming status visitor session count";
       }
       leaf idle-subscriber-count {
         type uint32;
         description "Number of idle subscribers";
       }
       leaf idle-session-count {
         type uint32;
         description "Number of idle sessions";
       }
       leaf idle-bearer-count {
         type uint32;
         description "Number of idle bearers";
       }
       leaf susp-subscriber-count {
         type uint32;
         description "Number of suspended subscribers";
       }
       leaf susp-session-count {
         type uint32;
         description "Number of suspended sessions";
       }
       leaf susp-bearer-count {
         type uint32;
         description "Number of suspended bearers";
       }
       leaf indt-tunn-count {
         type uint32;
         description "Number of indirect tunnels";
       }
       leaf dt-tunn-count {
         type uint32;
         description "Number of direct tunnels";
       }
     }
     container mobile-gateway-status-extensive {
       leaf fpc-slot {
         type int32;
         description "FPC slot";
       }
       leaf pic-slot {
         type int32;
         description "PIC slot";
       }
       leaf pic-role {
         type string;
         description "PIC Role Information Standalone/Primary/Secondary";
       }
       leaf pic-type {
         type string;
         description "Client type";
       }
       leaf active-subscriber-count {
         type uint32;
         description "Number of active subscribers";
       }
       leaf active-svc-subscriber-count {
         type uint32;
         description "Number of active subscribers with services";
       }
       leaf active-session-count {
         type uint32;
         description "Number of active sessions";
       }
       leaf active-svc-session-count {
         type uint64;
         description "Number of active sessions with services";
       }
       leaf active-bearer-count {
         type uint32;
         description "Number of active bearers";
       }
       leaf active-prepaid-bearers {
         type uint32;
         description "Number of active prepaid bearers";
       }
       leaf active-postpaid-bearers {
         type uint32;
         description "Number of active postpaid bearers";
       }
       leaf active-gbr-bearers {
         type uint32;
         description "Number of active GBR bearers";
       }
       leaf active-non-gbr-bearers {
         type uint32;
         description "Number of active Non-GBR bearers";
       }
       leaf cpu-load {
         type uint32;
         description "Current CPU load";
       }
       leaf memory-load {
         type uint32;
         description "Current Memory load";
       }
       leaf pdn-type-ipv4-session-count {
         type uint32;
         description "Ipv4 session count";
       }
       leaf pdn-type-ipv6-session-count {
         type uint32;
         description "Ipv6 session count";
       }
       leaf pdn-type-ipv46-session-count {
         type uint32;
         description "Ipv46 session count";
       }
       leaf roaming-status-type-home-session-count {
         type uint32;
         description "Roaming status home session count";
       }
       leaf roaming-status-type-roamer-session-count {
         type uint32;
         description "Roaming status roamer session count";
       }
       leaf roaming-status-type-visitor-session-count {
         type uint32;
         description "Roaming status visitor session count";
       }
       list service-session-connection {
         leaf svcs-sess-fpc-slot {
           type int32;
           description "FPC slot";
         }
         leaf svcs-sess-pic-slot {
           type int32;
           description "PIC slot";
         }
       }
     }
     container mobile-gateway-gtp-peer-apfe-distribution {
       leaf fpc-slot {
         type int32;
         description "FPC slot";
       }
       leaf pic-slot {
         type int32;
         description "PIC slot";
       }
       leaf active-bearer-count {
         type uint32;
         description "Number of active bearers";
       }
     }
     container mobile-gateway-qci-status-brief-info {
       leaf qci-index {
         type uint32;
         description "QCI index for qos parameters";
       }
       leaf qci-type-bearer-count {
         type uint32;
         description "QCI type bearer count";
       }
       leaf qci-type-prepaid-bearer-count {
         type uint32;
         description "QCI type prepaid bearer count";
       }
       leaf qci-type-postpaid-bearer-count {
         type uint32;
         description "QCI type postpaid bearer count";
       }
     }
     container mobile-gateway-qci-status-detail-info {
       leaf fpc-slot {
         type int32;
         description "FPC slot";
       }
       leaf pic-slot {
         type int32;
         description "PIC slot";
       }
       leaf qci-index {
         type uint32;
         description "QCI index for qos parameters";
       }
       leaf qci-type-bearer-count {
         type uint32;
         description "QCI type bearer count";
       }
       leaf qci-type-prepaid-bearer-count {
         type uint32;
         description "QCI type prepaid bearer count";
       }
       leaf qci-type-postpaid-bearer-count {
         type uint32;
         description "QCI type postpaid bearer count";
       }
     }
     container mobile-gateway-priority-level-status-brief-info {
       leaf priority-level-index {
         type uint32;
         description "Priority level index for qos parameters";
       }
       leaf priority-level-type-bearer-count {
         type uint32;
         description "Priority level type bearer count";
       }
       leaf priority-level-type-prepaid-bearer-count {
         type uint32;
         description "Priority level type prepaid bearer count";
       }
       leaf priority-level-type-postpaid-bearer-count {
         type uint32;
         description "Priority level type postpaid bearer count";
       }
     }
     container mobile-gateway-priority-level-status-detail-info {
       leaf fpc-slot {
         type int32;
         description "FPC slot";
       }
       leaf pic-slot {
         type int32;
         description "PIC slot";
       }
       leaf priority-level-index {
         type uint32;
         description "Priority level index for qos parameters";
       }
       leaf priority-level-type-bearer-count {
         type uint32;
         description "Priority level type bearer count";
       }
       leaf priority-level-type-prepaid-bearer-count {
         type uint32;
         description "Priority level type prepaid bearer count";
       }
       leaf priority-level-type-postpaid-bearer-count {
         type uint32;
         description "Priority level type postpaid bearer count";
       }
     }
     container mobile-gateway-traffic-class-status-brief-info {
       leaf traffic-class-string {
         type string;
         description "Traffic class string";
       }
       leaf traffic-class-type-bearer-count {
         type uint32;
         description "Traffic class type bearer count";
       }
       leaf traffic-class-type-prepaid-bearer-count {
         type uint32;
         description "Traffic class type prepaid bearer count";
       }
       leaf traffic-class-type-postpaid-bearer-count {
         type uint32;
         description "Traffic class type postpaid bearer count";
       }
     }
     container mobile-gateway-traffic-class-status-detail-info {
       leaf fpc-slot {
         type int32;
         description "FPC slot";
       }
       leaf pic-slot {
         type int32;
         description "PIC slot";
       }
       leaf traffic-class-string {
         type string;
         description "Traffic class string";
       }
       leaf traffic-class-type-bearer-count {
         type uint32;
         description "Traffic class type bearer count";
       }
       leaf traffic-class-type-prepaid-bearer-count {
         type uint32;
         description "Traffic class type prepaid bearer count";
       }
       leaf traffic-class-type-postpaid-bearer-count {
         type uint32;
         description "Traffic class type postpaid bearer count";
       }
     }
     container mobile-gateway-arp-status-brief-info {
       leaf arp-index {
         type uint32;
         description "ARP index for qos parameters";
       }
       leaf arp-type-bearer-count {
         type uint32;
         description "ARP type bearer count";
       }
       leaf arp-type-prepaid-bearer-count {
         type uint32;
         description "ARP type prepaid bearer count";
       }
       leaf arp-type-postpaid-bearer-count {
         type uint32;
         description "ARP type postpaid bearer count";
       }
     }
     container mobile-gateway-arp-status-detail-info {
       leaf fpc-slot {
         type int32;
         description "FPC slot";
       }
       leaf pic-slot {
         type int32;
         description "PIC slot";
       }
       leaf arp-index {
         type uint32;
         description "ARP index for qos parameters";
       }
       leaf arp-type-bearer-count {
         type uint32;
         description "ARP type bearer count";
       }
       leaf arp-type-prepaid-bearer-count {
         type uint32;
         description "ARP type prepaid bearer count";
       }
       leaf arp-type-postpaid-bearer-count {
         type uint32;
         description "ARP type postpaid bearer count";
       }
     }
     container mobile-gateway-rat-type-status-brief-info {
       leaf rat-type-string {
         type string;
         description "RAT type string";
       }
       leaf rat-type-active-subscriber-count {
         type uint32;
         description "RAT type active subscriber count";
       }
       leaf rat-type-active-session-count {
         type uint32;
         description "RAT type active session count";
       }
       leaf rat-type-active-bearer-count {
         type uint32;
         description "RAT type active bearer count";
       }
       leaf rat-type-idle-subscriber-count {
         type uint32;
         description "RAT type idle subscriber count";
       }
       leaf rat-type-idle-session-count {
         type uint32;
         description "RAT type idle session count";
       }
       leaf rat-type-idle-bearer-count {
         type uint32;
         description "RAT type idle bearer count";
       }
       leaf rat-type-suspended-subscriber-count {
         type uint32;
         description "RAT type suspended subscriber count";
       }
       leaf rat-type-suspended-session-count {
         type uint32;
         description "RAT type suspended session count";
       }
       leaf rat-type-suspended-bearer-count {
         type uint32;
         description "RAT type suspended bearer count";
       }
     }
     container mobile-gateway-rat-type-status-detail-info {
       leaf fpc-slot {
         type int32;
         description "FPC slot";
       }
       leaf pic-slot {
         type int32;
         description "PIC slot";
       }
       leaf rat-type-string {
         type string;
         description "RAT type string";
       }
       leaf rat-type-active-subscriber-count {
         type uint32;
         description "RAT type active subscriber count";
       }
       leaf rat-type-active-session-count {
         type uint32;
         description "RAT type active session count";
       }
       leaf rat-type-active-bearer-count {
         type uint32;
         description "RAT type active bearer count";
       }
       leaf rat-type-idle-subscriber-count {
         type uint32;
         description "RAT type idle subscriber count";
       }
       leaf rat-type-idle-session-count {
         type uint32;
         description "RAT type idle session count";
       }
       leaf rat-type-idle-bearer-count {
         type uint32;
         description "RAT type idle bearer count";
       }
       leaf rat-type-suspended-subscriber-count {
         type uint32;
         description "RAT type suspended subscriber count";
       }
       leaf rat-type-suspended-session-count {
         type uint32;
         description "RAT type suspended session count";
       }
       leaf rat-type-suspended-bearer-count {
         type uint32;
         description "RAT type suspended bearer count";
       }
     }
     container mobile-gateway-preemption-list-status-brief {
       leaf priority-1-gbr-count {
         type uint32;
         description "Preemption List count for Priority Level 1 and Bearer type GBR";
       }
       leaf priority-1-ngbr-count {
         type uint32;
         description "Preemption List count for Priority Level 1 and Bearer type NON-GBR";
       }
       leaf priority-2-gbr-count {
         type uint32;
         description "Preemption List count for Priority Level 2 and Bearer type GBR";
       }
       leaf priority-2-ngbr-count {
         type uint32;
         description "Preemption List count for Priority Level 2 and Bearer type NON-GBR";
       }
       leaf priority-3-gbr-count {
         type uint32;
         description "Preemption List count for Priority Level 3 and Bearer type GBR";
       }
       leaf priority-3-ngbr-count {
         type uint32;
         description "Preemption List count for Priority Level 3 and Bearer type NON-GBR";
       }
       leaf priority-4-gbr-count {
         type uint32;
         description "Preemption List count for Priority Level 4 and Bearer type GBR";
       }
       leaf priority-4-ngbr-count {
         type uint32;
         description "Preemption List count for Priority Level 4 and Bearer type NON-GBR";
       }
       leaf priority-5-gbr-count {
         type uint32;
         description "Preemption List count for Priority Level 5 and Bearer type GBR";
       }
       leaf priority-5-ngbr-count {
         type uint32;
         description "Preemption List count for Priority Level 5 and Bearer type NON-GBR";
       }
       leaf priority-6-gbr-count {
         type uint32;
         description "Preemption List count for Priority Level 6 and Bearer type GBR";
       }
       leaf priority-6-ngbr-count {
         type uint32;
         description "Preemption List count for Priority Level 6 and Bearer type NON-GBR";
       }
       leaf priority-7-gbr-count {
         type uint32;
         description "Preemption List count for Priority Level 7 and Bearer type GBR";
       }
       leaf priority-7-ngbr-count {
         type uint32;
         description "Preemption List count for Priority Level 7 and Bearer type NON-GBR";
       }
       leaf priority-8-gbr-count {
         type uint32;
         description "Preemption List count for Priority Level 8 and Bearer type GBR";
       }
       leaf priority-8-ngbr-count {
         type uint32;
         description "Preemption List count for Priority Level 8 and Bearer type NON-GBR";
       }
       leaf priority-9-gbr-count {
         type uint32;
         description "Preemption List count for Priority Level 9 and Bearer type GBR";
       }
       leaf priority-9-ngbr-count {
         type uint32;
         description "Preemption List count for Priority Level 9 and Bearer type NON-GBR";
       }
       leaf priority-10-gbr-count {
         type uint32;
         description "Preemption List count for Priority Level 10 and Bearer type GBR";
       }
       leaf priority-10-ngbr-count {
         type uint32;
         description "Preemption List count for Priority Level 10 and Bearer type NON-GBR";
       }
       leaf priority-11-gbr-count {
         type uint32;
         description "Preemption List count for Priority Level 11 and Bearer type GBR";
       }
       leaf priority-11-ngbr-count {
         type uint32;
         description "Preemption List count for Priority Level 11 and Bearer type NON-GBR";
       }
       leaf priority-12-gbr-count {
         type uint32;
         description "Preemption List count for Priority Level 12 and Bearer type GBR";
       }
       leaf priority-12-ngbr-count {
         type uint32;
         description "Preemption List count for Priority Level 12 and Bearer type NON-GBR";
       }
       leaf priority-13-gbr-count {
         type uint32;
         description "Preemption List count for Priority Level 13 and Bearer type GBR";
       }
       leaf priority-13-ngbr-count {
         type uint32;
         description "Preemption List count for Priority Level 13 and Bearer type NON-GBR";
       }
       leaf priority-14-gbr-count {
         type uint32;
         description "Preemption List count for Priority Level 14 and Bearer type GBR";
       }
       leaf priority-14-ngbr-count {
         type uint32;
         description "Preemption List count for Priority Level 14 and Bearer type NON-GBR";
       }
       leaf priority-15-gbr-count {
         type uint32;
         description "Preemption List count for Priority Level 15 and Bearer type GBR";
       }
       leaf priority-15-ngbr-count {
         type uint32;
         description "Preemption List count for Priority Level 15 and Bearer type NON-GBR";
       }
     }
     container mobile-gateway-preemption-list-status-detail {
       leaf fpc-slot {
         type int32;
         description "FPC slot";
       }
       leaf pic-slot {
         type int32;
         description "PIC slot";
       }
       leaf priority-1-gbr-count {
         type uint32;
         description "Preemption List count for Priority Level 1 and Bearer type GBR";
       }
       leaf priority-1-ngbr-count {
         type uint32;
         description "Preemption List count for Priority Level 1 and Bearer type NON-GBR";
       }
       leaf priority-2-gbr-count {
         type uint32;
         description "Preemption List count for Priority Level 2 and Bearer type GBR";
       }
       leaf priority-2-ngbr-count {
         type uint32;
         description "Preemption List count for Priority Level 2 and Bearer type NON-GBR";
       }
       leaf priority-3-gbr-count {
         type uint32;
         description "Preemption List count for Priority Level 3 and Bearer type GBR";
       }
       leaf priority-3-ngbr-count {
         type uint32;
         description "Preemption List count for Priority Level 3 and Bearer type NON-GBR";
       }
       leaf priority-4-gbr-count {
         type uint32;
         description "Preemption List count for Priority Level 4 and Bearer type GBR";
       }
       leaf priority-4-ngbr-count {
         type uint32;
         description "Preemption List count for Priority Level 4 and Bearer type NON-GBR";
       }
       leaf priority-5-gbr-count {
         type uint32;
         description "Preemption List count for Priority Level 5 and Bearer type GBR";
       }
       leaf priority-5-ngbr-count {
         type uint32;
         description "Preemption List count for Priority Level 5 and Bearer type NON-GBR";
       }
       leaf priority-6-gbr-count {
         type uint32;
         description "Preemption List count for Priority Level 6 and Bearer type GBR";
       }
       leaf priority-6-ngbr-count {
         type uint32;
         description "Preemption List count for Priority Level 6 and Bearer type NON-GBR";
       }
       leaf priority-7-gbr-count {
         type uint32;
         description "Preemption List count for Priority Level 7 and Bearer type GBR";
       }
       leaf priority-7-ngbr-count {
         type uint32;
         description "Preemption List count for Priority Level 7 and Bearer type NON-GBR";
       }
       leaf priority-8-gbr-count {
         type uint32;
         description "Preemption List count for Priority Level 8 and Bearer type GBR";
       }
       leaf priority-8-ngbr-count {
         type uint32;
         description "Preemption List count for Priority Level 8 and Bearer type NON-GBR";
       }
       leaf priority-9-gbr-count {
         type uint32;
         description "Preemption List count for Priority Level 9 and Bearer type GBR";
       }
       leaf priority-9-ngbr-count {
         type uint32;
         description "Preemption List count for Priority Level 9 and Bearer type NON-GBR";
       }
       leaf priority-10-gbr-count {
         type uint32;
         description "Preemption List count for Priority Level 10 and Bearer type GBR";
       }
       leaf priority-10-ngbr-count {
         type uint32;
         description "Preemption List count for Priority Level 10 and Bearer type NON-GBR";
       }
       leaf priority-11-gbr-count {
         type uint32;
         description "Preemption List count for Priority Level 11 and Bearer type GBR";
       }
       leaf priority-11-ngbr-count {
         type uint32;
         description "Preemption List count for Priority Level 11 and Bearer type NON-GBR";
       }
       leaf priority-12-gbr-count {
         type uint32;
         description "Preemption List count for Priority Level 12 and Bearer type GBR";
       }
       leaf priority-12-ngbr-count {
         type uint32;
         description "Preemption List count for Priority Level 12 and Bearer type NON-GBR";
       }
       leaf priority-13-gbr-count {
         type uint32;
         description "Preemption List count for Priority Level 13 and Bearer type GBR";
       }
       leaf priority-13-ngbr-count {
         type uint32;
         description "Preemption List count for Priority Level 13 and Bearer type NON-GBR";
       }
       leaf priority-14-gbr-count {
         type uint32;
         description "Preemption List count for Priority Level 14 and Bearer type GBR";
       }
       leaf priority-14-ngbr-count {
         type uint32;
         description "Preemption List count for Priority Level 14 and Bearer type NON-GBR";
       }
       leaf priority-15-gbr-count {
         type uint32;
         description "Preemption List count for Priority Level 15 and Bearer type GBR";
       }
       leaf priority-15-ngbr-count {
         type uint32;
         description "Preemption List count for Priority Level 15 and Bearer type NON-GBR";
       }
     }
     container mobile-gateway-status-state-brief {
       leaf session-established {
         type uint32;
         description "Established Sessions";
       }
       leaf session-deleting {
         type uint32;
         description "Sessions in deleting state";
       }
       leaf session-updating-bearer {
         type uint32;
         description "Sessions in updating bearers state";
       }
       leaf session-authorizing {
         type uint32;
         description "Sessions waiting for initial authorization";
       }
       leaf session-acquiring-address {
         type uint32;
         description "Sessions in acquire address state";
       }
       leaf sgw-session-init {
         type uint32;
         description "Sessions in initial state";
       }
       leaf sgw-session-wait-def-bearer-setup {
         type uint32;
         description "Sessions in default bearer setup wait state";
       }
       leaf sgw-session-sync-wait {
         type uint32;
         description "Sessions waiting for session sync to backup SP";
       }
       leaf sgw-session-established {
         type uint32;
         description "Sessions in established state";
       }
       leaf sgw-session-cleanup {
         type uint32;
         description "Sessions in clean up state";
       }
       leaf sgw-session-idle {
         type uint32;
         description "Sessions in idle mode";
       }
       leaf sgw-session-suspended {
         type uint32;
         description "Sessions in suspended state";
       }
       leaf sgw-session-pfe-wait {
         type uint32;
         description "Sessions in PFE wait state";
       }
       leaf sgw-session-pgw-wait {
         type uint32;
         description "Sessions in PGW wait state";
       }
       leaf sgw-session-ho-mme-wait {
         type uint32;
         description "Sessions in handover MME wait state";
       }
     }
     container mobile-gateway-status-state-detail {
       leaf fpc-slot {
         type int32;
         description "FPC slot";
       }
       leaf pic-slot {
         type int32;
         description "PIC slot";
       }
       leaf pic-role {
         type string;
         description "PIC Role Information Standalone/Primary/Secondary";
       }
       leaf session-established {
         type uint32;
         description "Established Sessions";
       }
       leaf session-deleting {
         type uint32;
         description "Sessions in deleting state";
       }
       leaf session-updating-bearer {
         type uint32;
         description "Sessions in updating bearers state";
       }
       leaf session-authorizing {
         type uint32;
         description "Sessions waiting for initial authorization";
       }
       leaf session-acquiring-address {
         type uint32;
         description "Sessions in acquire address state";
       }
       leaf sgw-session-init {
         type uint32;
         description "Sessions in initial state";
       }
       leaf sgw-session-wait-def-bearer-setup {
         type uint32;
         description "Sessions in default bearer setup wait state";
       }
       leaf sgw-session-sync-wait {
         type uint32;
         description "Sessions waiting for session sync to backup SP";
       }
       leaf sgw-session-established {
         type uint32;
         description "Sessions in established state";
       }
       leaf sgw-session-cleanup {
         type uint32;
         description "Sessions in clean up state";
       }
       leaf sgw-session-idle {
         type uint32;
         description "Sessions in idle mode";
       }
       leaf sgw-session-suspended {
         type uint32;
         description "Sessions in suspended state";
       }
       leaf sgw-session-pfe-wait {
         type uint32;
         description "Sessions in PFE wait state";
       }
       leaf sgw-session-pgw-wait {
         type uint32;
         description "Sessions in PGW wait state";
       }
       leaf sgw-session-ho-mme-wait {
         type uint32;
         description "Sessions in handover MME wait state";
       }
     }
   }
   grouping mobile-gateway-call-rate-statistics-block {
     container mobile-gateway-call-rate-stats {
       leaf record-number {
         type uint32;
         description "Call-rate statistics history number";
       }
       leaf call-rate-interval {
         type uint32;
         description "Call-rate statistics interval";
       }
       leaf activation-count {
         type uint32;
         description "Activation count in the given period";
       }
       leaf deactivation-count {
         type uint32;
         description "Deactivation count in the given period";
       }
       leaf rx-data-packets {
         type uint64;
         description "Data packets received in the given period";
       }
       leaf tx-data-packets {
         type uint64;
         description "Data packets transmitted in the given period";
       }
       leaf rx-data-bytes {
         type uint64;
         description "Data bytes received in the given period";
       }
       leaf tx-data-bytes {
         type uint64;
         description "Data bytes transmitted in the given period";
       }
       leaf call-rate-time {
         type string;
         description "Time at which the call-rate statistics were retrieved";
       }
     }
   }
   grouping mobile-gateways-apn-service-mode-block {
     leaf apn-name {
       type string;
       description "Access Point Name";
     }
     leaf gateway-name {
       type string;
       description "Mobile Gateway Name";
     }
     leaf mm-service-mode {
       type string;
       description "Service Mode Maintenance status for a profile";
     }
     container mm-service-mode-description {
       leaf mm-service-mode {
         type string;
         description "Service Mode Maintenance status for a profile";
       }
       leaf mm-service-mode-pending-mm-ack {
         type string;
       }
       leaf mm-service-mode-pending-ready-ack {
         type string;
       }
       list mobiled-session-description {
         leaf mobiled-client {
           type string;
           description "Mobiled Client - Could be RE or one of the SPICs";
         }
         leaf mobiled-peer-list {
           type string;
           description "Mobiled Peer List - Apps separated by commas";
         }
       }
       list mobiled-session-description2 {
         leaf mobiled-client {
           type string;
           description "Mobiled Client - Could be RE or one of the SPICs";
         }
         leaf mobiled-peer-list {
           type string;
           description "Mobiled Peer List - Apps separated by commas";
         }
       }
     }
   }
   grouping ggsn-pgw-address-assign-service-mode-block {
     leaf mm-routing-instance {
       type string;
       description "Routing Instance";
     }
     leaf mm-pool-name {
       type string;
       description "Name of the address pool";
     }
     leaf mm-service-mode {
       type string;
       description "Service Mode Maintenance status for a profile";
     }
     container mm-service-mode-description {
       leaf mm-service-mode {
         type string;
         description "Service Mode Maintenance status for a profile";
       }
       leaf mm-service-mode-pending-mm-ack {
         type string;
       }
       leaf mm-service-mode-pending-ready-ack {
         type string;
       }
       list mobiled-session-description {
         leaf mobiled-client {
           type string;
           description "Mobiled Client - Could be RE or one of the SPICs";
         }
         leaf mobiled-peer-list {
           type string;
           description "Mobiled Peer List - Apps separated by commas";
         }
       }
       list mobiled-session-description2 {
         leaf mobiled-client {
           type string;
           description "Mobiled Client - Could be RE or one of the SPICs";
         }
         leaf mobiled-peer-list {
           type string;
           description "Mobiled Peer List - Apps separated by commas";
         }
       }
     }
   }
   grouping mobile-gateway-sm-ippool-pool-information-block {
     list sm-ippool-pool-statistics {
       leaf sm-ippool-pool-name {
         type string;
         description "Pool name";
       }
       leaf sm-ippool-total-addresses {
         type uint64;
         description "Total number of addresses";
       }
       leaf sm-ippool-used-addresses {
         type uint32;
         description "Number of addresses in use";
       }
       leaf sm-ippool-skipped {
         type uint64;
         description "Total number of addresses skipped from allocation";
       }
       leaf sm-ippool-utilization {
         type int32;
         description "Percentage of addresses in use";
       }
       leaf sm-ippool-aging-period-count {
         type int32;
         description "Total number of addresses in aging period";
       }
       leaf sm-ippool-ri {
         type string;
         description "Routing instance";
       }
       leaf sm-ippool-mobile-gateway-name {
         type string;
         description "Gateway Name";
       }
       leaf sm-ippool-empty {
         type empty;
       }
       leaf sm-ippool-fpc-pic {
         type string;
         description "FPC/PIC slot information";
       }
       leaf sm-ippool-comment {
         type string;
         description "Comment";
       }
       leaf mm-service-mode {
         type string;
         description "Service Mode Maintenance status for a profile";
       }
       leaf sm-ippool-address-chunks {
         type int32;
         description "Number of address chunks";
       }
       leaf sm-ippool-total-address-chunk-size {
         type int32;
         description "Total number of addresses in all the address chunks";
       }
       leaf sm-ippool-alloc-failures {
         type int32;
         description "Total number of address allocation failures";
       }
     }
   }
   grouping mobile-gateway-sm-ippool-group-information-block {
     list sm-ippool-group-statistics {
       leaf sm-ippool-group-name {
         type string;
         description "Group name";
       }
       leaf sm-ippool-total-addresses {
         type uint64;
         description "Total number of addresses";
       }
       leaf sm-ippool-used-addresses {
         type uint32;
         description "Number of addresses in use";
       }
       leaf sm-ippool-utilization {
         type int32;
         description "Percentage of addresses in use";
       }
       leaf sm-ippool-ri {
         type string;
         description "Routing instance";
       }
       leaf sm-ippool-mobile-gateway-name {
         type string;
         description "Gateway Name";
       }
       leaf sm-ippool-empty {
         type empty;
       }
       leaf sm-ippool-fpc-pic {
         type string;
         description "FPC/PIC slot information";
       }
       leaf sm-ippool-comment {
         type string;
         description "Comment";
       }
     }
   }
   grouping mobile-gateway-sm-ippool-statistics-block {
     list sm-ippool-statistics {
       leaf sm-ippool-empty {
         type empty;
       }
       leaf sm-ippool-mobile-gateway-name {
         type string;
         description "Gateway Name";
       }
       leaf sm-ippool-allocs {
         type int32;
         description "Total number of address allocations";
       }
       leaf sm-ippool-alloc-failures {
         type int32;
         description "Total number of address allocation failures";
       }
       leaf sm-ippool-releases {
         type int32;
         description "Total number of address releases";
       }
       leaf sm-ippool-release-failures {
         type int32;
         description "Total number of address release failures";
       }
       leaf sm-ippool-lock-failures {
         type int32;
         description "Lock failures";
       }
       leaf sm-ippool-fpc-pic {
         type string;
         description "FPC/PIC slot information";
       }
       leaf sm-ippool-comment {
         type string;
         description "Comment";
       }
     }
   }
   grouping rmpsd-show-rmm-client-command-block {
     list rmpsd-client-stats {
       leaf rmpsd-client {
         type string;
         description "Resource-Manager Client slot information";
       }
       leaf rmpsd-client-state {
         type string;
         description "Resource-Manager Client State information";
       }
       leaf rmpsd-client-role {
         type string;
         description "Resource-Manager Client Role information";
       }
     }
   }
   grouping tdf-gateway-aaa-statistics-block {
     list tdf-gateway-aaa-radius-statistics {
       leaf aaa-gateway-name {
         type string;
         description "Gateway name";
       }
       leaf aaa-fpc-pic {
         type string;
         description "FPC/PIC slot information";
       }
       leaf aaa-radius-received {
         type uint64;
         description "Radius message received";
       }
       leaf aaa-radius-sent {
         type uint64;
         description "Radius message sent";
       }
       leaf aaa-radius-forwarded-in {
         type uint64;
         description "Radius message forwarded in";
       }
       leaf aaa-radius-forwarded-out {
         type uint64;
         description "Radius message forwarded out";
       }
       leaf aaa-radius-snooped {
         type uint64;
         description "Radius message forwarded out";
       }
       leaf aaa-radius-access-request-received {
         type uint64;
         description "Radius access request message received";
       }
       leaf aaa-radius-access-request-sent {
         type uint64;
         description "Radius access request message sent";
       }
       leaf aaa-radius-access-request-forwarded-in {
         type uint64;
         description "Radius access request message forwarded-in";
       }
       leaf aaa-radius-access-request-forwarded-out {
         type uint64;
         description "Radius access request message forwarded-out";
       }
       leaf aaa-radius-access-request-snooped {
         type uint64;
         description "Radius access request message snooped";
       }
       leaf aaa-radius-access-response-received {
         type uint64;
         description "Radius access response message received";
       }
       leaf aaa-radius-access-response-sent {
         type uint64;
         description "Radius access response message sent";
       }
       leaf aaa-radius-access-response-forwarded-in {
         type uint64;
         description "Radius access response message forwarded-in";
       }
       leaf aaa-radius-access-response-forwarded-out {
         type uint64;
         description "Radius access response message forwarded-out";
       }
       leaf aaa-radius-access-response-snooped {
         type uint64;
         description "Radius access response message snooped";
       }
       leaf aaa-radius-access-accept-received {
         type uint64;
         description "Radius access accept message received";
       }
       leaf aaa-radius-access-accept-sent {
         type uint64;
         description "Radius access accept message sent";
       }
       leaf aaa-radius-access-accept-forwarded-in {
         type uint64;
         description "Radius access accept message forwarded-in";
       }
       leaf aaa-radius-access-accept-forwarded-out {
         type uint64;
         description "Radius access accept message forwarded-out";
       }
       leaf aaa-radius-access-accept-snooped {
         type uint64;
         description "Radius access accept message snooped";
       }
       leaf aaa-radius-access-reject-received {
         type uint64;
         description "Radius access reject message received";
       }
       leaf aaa-radius-access-reject-sent {
         type uint64;
         description "Radius access reject message sent";
       }
       leaf aaa-radius-access-reject-forwarded-in {
         type uint64;
         description "Radius access reject message forwarded-in";
       }
       leaf aaa-radius-access-reject-forwarded-out {
         type uint64;
         description "Radius access reject message forwarded-out";
       }
       leaf aaa-radius-access-reject-snooped {
         type uint64;
         description "Radius access reject message snooped";
       }
       leaf aaa-radius-acct-request-received {
         type uint64;
         description "Radius accounting request message received";
       }
       leaf aaa-radius-acct-request-sent {
         type uint64;
         description "Radius accounting request message sent";
       }
       leaf aaa-radius-acct-request-forwarded-in {
         type uint64;
         description "Radius accounting request message forwarded-in";
       }
       leaf aaa-radius-acct-request-forwarded-out {
         type uint64;
         description "Radius accounting request message forwarded-out";
       }
       leaf aaa-radius-acct-request-snooped {
         type uint64;
         description "Radius accounting request message snooped";
       }
       leaf aaa-radius-acct-start-request-received {
         type uint64;
         description "Radius accounting start request message received";
       }
       leaf aaa-radius-acct-start-request-sent {
         type uint64;
         description "Radius accounting start request message sent";
       }
       leaf aaa-radius-acct-start-request-forwarded-in {
         type uint64;
         description "Radius accounting start request message forwarded-in";
       }
       leaf aaa-radius-acct-start-request-forwarded-out {
         type uint64;
         description "Radius accounting start request message forwarded-out";
       }
       leaf aaa-radius-acct-start-request-snooped {
         type uint64;
         description "Radius accounting start request message snooped";
       }
       leaf aaa-radius-acct-interim-request-received {
         type uint64;
         description "Radius accounting interim request message received";
       }
       leaf aaa-radius-acct-interim-request-sent {
         type uint64;
         description "Radius accounting interim request message sent";
       }
       leaf aaa-radius-acct-interim-request-forwarded-in {
         type uint64;
         description "Radius accounting interim request message forwarded-in";
       }
       leaf aaa-radius-acct-interim-request-forwarded-out {
         type uint64;
         description "Radius accounting interim request message forwarded-out";
       }
       leaf aaa-radius-acct-interim-request-snooped {
         type uint64;
         description "Radius accounting interim request message snooped";
       }
       leaf aaa-radius-acct-stop-request-received {
         type uint64;
         description "Radius accounting stop request message received";
       }
       leaf aaa-radius-acct-stop-request-sent {
         type uint64;
         description "Radius accounting stop request message sent";
       }
       leaf aaa-radius-acct-stop-request-forwarded-in {
         type uint64;
         description "Radius accounting stop request message forwarded-in";
       }
       leaf aaa-radius-acct-stop-request-forwarded-out {
         type uint64;
         description "Radius accounting stop request message forwarded-out";
       }
       leaf aaa-radius-acct-stop-request-snooped {
         type uint64;
         description "Radius accounting stop request message snooped";
       }
       leaf aaa-radius-acct-on-request-received {
         type uint64;
         description "Radius accounting on request message received";
       }
       leaf aaa-radius-acct-on-request-sent {
         type uint64;
         description "Radius accounting on request message sent";
       }
       leaf aaa-radius-acct-on-request-forwarded-in {
         type uint64;
         description "Radius accounting on request message forwarded-in";
       }
       leaf aaa-radius-acct-on-request-forwarded-out {
         type uint64;
         description "Radius accounting on request message forwarded-out";
       }
       leaf aaa-radius-acct-on-request-snooped {
         type uint64;
         description "Radius accounting on request message snooped";
       }
       leaf aaa-radius-acct-off-request-received {
         type uint64;
         description "Radius accounting off request message received";
       }
       leaf aaa-radius-acct-off-request-sent {
         type uint64;
         description "Radius accounting off request message sent";
       }
       leaf aaa-radius-acct-off-request-forwarded-in {
         type uint64;
         description "Radius accounting off request message forwarded-in";
       }
       leaf aaa-radius-acct-off-request-forwarded-out {
         type uint64;
         description "Radius accounting off request message forwarded-out";
       }
       leaf aaa-radius-acct-off-request-snooped {
         type uint64;
         description "Radius accounting off request message snooped";
       }
       leaf aaa-radius-acct-response-received {
         type uint64;
         description "Radius accounting response message received";
       }
       leaf aaa-radius-acct-response-sent {
         type uint64;
         description "Radius accounting response message sent";
       }
       leaf aaa-radius-acct-response-forwarded-in {
         type uint64;
         description "Radius accounting response message forwarded-in";
       }
       leaf aaa-radius-acct-response-forwarded-out {
         type uint64;
         description "Radius accounting response message forwarded-out";
       }
       leaf aaa-radius-acct-response-snooped {
         type uint64;
         description "Radius accounting response message snooped";
       }
       leaf aaa-radius-acct-start-response-received {
         type uint64;
         description "Radius accounting start response message received";
       }
       leaf aaa-radius-acct-start-response-sent {
         type uint64;
         description "Radius accounting start response message sent";
       }
       leaf aaa-radius-acct-start-response-forwarded-in {
         type uint64;
         description "Radius accounting start response message forwarded-in";
       }
       leaf aaa-radius-acct-start-response-forwarded-out {
         type uint64;
         description "Radius accounting start response message forwarded-out";
       }
       leaf aaa-radius-acct-start-response-snooped {
         type uint64;
         description "Radius accounting start response message snooped";
       }
       leaf aaa-radius-acct-interim-response-received {
         type uint64;
         description "Radius accounting interim response message received";
       }
       leaf aaa-radius-acct-interim-response-sent {
         type uint64;
         description "Radius accounting interim response message sent";
       }
       leaf aaa-radius-acct-interim-response-forwarded-in {
         type uint64;
         description "Radius accounting interim response message forwarded-in";
       }
       leaf aaa-radius-acct-interim-response-forwarded-out {
         type uint64;
         description "Radius accounting interim response message forwarded-out";
       }
       leaf aaa-radius-acct-interim-response-snooped {
         type uint64;
         description "Radius accounting interim response message snooped";
       }
       leaf aaa-radius-acct-stop-response-received {
         type uint64;
         description "Radius accounting stop response message received";
       }
       leaf aaa-radius-acct-stop-response-sent {
         type uint64;
         description "Radius accounting stop response message sent";
       }
       leaf aaa-radius-acct-stop-response-forwarded-in {
         type uint64;
         description "Radius accounting stop response message forwarded-in";
       }
       leaf aaa-radius-acct-stop-response-forwarded-out {
         type uint64;
         description "Radius accounting stop response message forwarded-out";
       }
       leaf aaa-radius-acct-stop-response-snooped {
         type uint64;
         description "Radius accounting stop response message snooped";
       }
       leaf aaa-radius-acct-on-response-received {
         type uint64;
         description "Radius accounting on response message received";
       }
       leaf aaa-radius-acct-on-response-sent {
         type uint64;
         description "Radius accounting on response message sent";
       }
       leaf aaa-radius-acct-on-response-forwarded-in {
         type uint64;
         description "Radius accounting on response message forwarded-in";
       }
       leaf aaa-radius-acct-on-response-forwarded-out {
         type uint64;
         description "Radius accounting on response message forwarded-out";
       }
       leaf aaa-radius-acct-on-response-snooped {
         type uint64;
         description "Radius accounting on response message snooped";
       }
       leaf aaa-radius-acct-off-response-received {
         type uint64;
         description "Radius accounting off response message received";
       }
       leaf aaa-radius-acct-off-response-sent {
         type uint64;
         description "Radius accounting off response message sent";
       }
       leaf aaa-radius-acct-off-response-forwarded-in {
         type uint64;
         description "Radius accounting off response message forwarded-in";
       }
       leaf aaa-radius-acct-off-response-forwarded-out {
         type uint64;
         description "Radius accounting off response message forwarded-out";
       }
       leaf aaa-radius-acct-off-response-snooped {
         type uint64;
         description "Radius accounting off response message snooped";
       }
       leaf aaa-radius-change-of-auth-request-received {
         type uint64;
         description "Radius change of authorization request message received";
       }
       leaf aaa-radius-change-of-auth-request-sent {
         type uint64;
         description "Radius change of authorization request message sent";
       }
       leaf aaa-radius-change-of-auth-request-forwarded-in {
         type uint64;
         description "Radius change of authorization request message forwarded-in";
       }
       leaf aaa-radius-change-of-auth-request-forwarded-out {
         type uint64;
         description "Radius change of authorization request message forwarded-out";
       }
       leaf aaa-radius-change-of-auth-request-snooped {
         type uint64;
         description "Radius change of authorization request message snooped";
       }
       leaf aaa-radius-change-of-auth-response-received {
         type uint64;
         description "Radius change of authorization response message received";
       }
       leaf aaa-radius-change-of-auth-response-sent {
         type uint64;
         description "Radius change of authorization response message sent";
       }
       leaf aaa-radius-change-of-auth-response-forwarded-in {
         type uint64;
         description "Radius change of authorization response message forwarded-in";
       }
       leaf aaa-radius-change-of-auth-response-forwarded-out {
         type uint64;
         description "Radius change of authorization response message forwarded-out";
       }
       leaf aaa-radius-change-of-auth-response-snooped {
         type uint64;
         description "Radius change of authorization response message snooped";
       }
       leaf aaa-radius-change-of-auth-ack-received {
         type uint64;
         description "Radius change of authorization ack message received";
       }
       leaf aaa-radius-change-of-auth-ack-sent {
         type uint64;
         description "Radius change of authorization ack message sent";
       }
       leaf aaa-radius-change-of-auth-ack-forwarded-in {
         type uint64;
         description "Radius change of authorization ack message forwarded-in";
       }
       leaf aaa-radius-change-of-auth-ack-forwarded-out {
         type uint64;
         description "Radius change of authorization ack message forwarded-out";
       }
       leaf aaa-radius-change-of-auth-ack-snooped {
         type uint64;
         description "Radius change of authorization ack message snooped";
       }
       leaf aaa-radius-change-of-auth-nak-received {
         type uint64;
         description "Radius change of authorization nak message received";
       }
       leaf aaa-radius-change-of-auth-nak-sent {
         type uint64;
         description "Radius change of authorization nak message sent";
       }
       leaf aaa-radius-change-of-auth-nak-forwarded-in {
         type uint64;
         description "Radius change of authorization nak message forwarded-in";
       }
       leaf aaa-radius-change-of-auth-nak-forwarded-out {
         type uint64;
         description "Radius change of authorization nak message forwarded-out";
       }
       leaf aaa-radius-change-of-auth-nak-snooped {
         type uint64;
         description "Radius change of authorization nak message snooped";
       }
       leaf aaa-radius-disconnect-message-request-received {
         type uint64;
         description "Radius disconnect message request message received";
       }
       leaf aaa-radius-disconnect-message-request-sent {
         type uint64;
         description "Radius disconnect message request message sent";
       }
       leaf aaa-radius-disconnect-message-request-forwarded-in {
         type uint64;
         description "Radius disconnect message request message forwarded-in";
       }
       leaf aaa-radius-disconnect-message-request-forwarded-out {
         type uint64;
         description "Radius disconnect message request message forwarded-out";
       }
       leaf aaa-radius-disconnect-message-request-snooped {
         type uint64;
         description "Radius disconnect message request message snooped";
       }
       leaf aaa-radius-disconnect-message-response-received {
         type uint64;
         description "Radius disconnect message response message received";
       }
       leaf aaa-radius-disconnect-message-response-sent {
         type uint64;
         description "Radius disconnect message response message sent";
       }
       leaf aaa-radius-disconnect-message-response-forwarded-in {
         type uint64;
         description "Radius disconnect message response message forwarded-in";
       }
       leaf aaa-radius-disconnect-message-response-forwarded-out {
         type uint64;
         description "Radius disconnect message response message forwarded-out";
       }
       leaf aaa-radius-disconnect-message-response-snooped {
         type uint64;
         description "Radius disconnect message response message snooped";
       }
       leaf aaa-radius-disconnect-message-ack-received {
         type uint64;
         description "Radius disconnect message ack message received";
       }
       leaf aaa-radius-disconnect-message-ack-sent {
         type uint64;
         description "Radius disconnect message ack message sent";
       }
       leaf aaa-radius-disconnect-message-ack-forwarded-in {
         type uint64;
         description "Radius disconnect message ack message forwarded-in";
       }
       leaf aaa-radius-disconnect-message-ack-forwarded-out {
         type uint64;
         description "Radius disconnect message ack message forwarded-out";
       }
       leaf aaa-radius-disconnect-message-ack-snooped {
         type uint64;
         description "Radius disconnect message ack message snooped";
       }
       leaf aaa-radius-disconnect-message-nak-received {
         type uint64;
         description "Radius disconnect message nak message received";
       }
       leaf aaa-radius-disconnect-message-nak-sent {
         type uint64;
         description "Radius disconnect message nak message sent";
       }
       leaf aaa-radius-disconnect-message-nak-forwarded-in {
         type uint64;
         description "Radius disconnect message nak message forwarded-in";
       }
       leaf aaa-radius-disconnect-message-nak-forwarded-out {
         type uint64;
         description "Radius disconnect message nak message forwarded-out";
       }
       leaf aaa-radius-disconnect-message-nak-snooped {
         type uint64;
         description "Radius disconnect message nak message snooped";
       }
       leaf aaa-radius-duplicate-packet {
         type uint64;
         description "Radius duplicate packets";
       }
       leaf aaa-radius-request-processing-error {
         type uint64;
         description "Radius requests processing errors";
       }
       leaf aaa-radius-response-processing-error {
         type uint64;
         description "Radius responses processing errors";
       }
       leaf aaa-radius-request-transmit-errors {
         type uint64;
         description "Radius requests transmit errors";
       }
       leaf aaa-radius-response-transmit-errors {
         type uint64;
         description "Radius responses transmit errors";
       }
       leaf aaa-radius-request-enqueue-errors {
         type uint64;
         description "Radius request enqueue errors";
       }
       leaf aaa-radius-response-enqueue-errors {
         type uint64;
         description "Radius response enqueue errors";
       }
       leaf aaa-radius-request-timeouts {
         type uint64;
         description "Radius request timeouts";
       }
       leaf aaa-radius-request-retransmissions {
         type uint64;
         description "Radius request retransmissions";
       }
       leaf aaa-radius-request-missing-tdf-domain {
         type uint64;
         description "Radius requests missing tdf domain";
       }
       leaf aaa-radius-request-missing-pcef-profile {
         type uint64;
         description "Radius request missing pcef profile";
       }
       leaf aaa-radius-request-dropped {
         type uint64;
         description "Radius requests dropped";
       }
       leaf aaa-radius-response-dropped {
         type uint64;
         description "Radius responses dropped";
       }
       leaf aaa-radius-dyn-request-processing-err {
         type uint64;
         description "Server initiated request processing errors";
       }
       leaf aaa-radius-dyn-request-dropped {
         type uint64;
         description "Server initiated requests dropped";
       }
       leaf aaa-radius-dyn-request-duplicate {
         type uint64;
         description "Duplicate server initiated requests received";
       }
       leaf aaa-radius-cached-reply-sent {
         type uint64;
         description "Radius cached reply sent";
       }
     }
   }
   grouping radius-client-statistics-block {
     list aaa-radius-client-acct-stats {
       leaf aaa-radius-client-name {
         type string;
         description "RADIUS client name";
       }
       leaf aaa-gateway-name {
         type string;
         description "Gateway name";
       }
       leaf aaa-fpc-pic {
         type string;
         description "FPC/PIC slot information";
       }
       leaf aaa-radius-client-acct-req {
         type uint64;
         description "Radius client accounting requests";
       }
       leaf aaa-radius-client-acct-start-req {
         type uint64;
         description "Radius client accounting start requests";
       }
       leaf aaa-radius-client-acct-stop-req {
         type uint64;
         description "Radius client accounting stop requests";
       }
       leaf aaa-radius-client-acct-interim-req {
         type uint64;
         description "Radius client accounting interim requests";
       }
       leaf aaa-radius-client-acct-on-req {
         type uint64;
         description "Radius client accounting on requests";
       }
       leaf aaa-radius-client-acct-off-req {
         type uint64;
         description "Radius client accounting off requests";
       }
       leaf aaa-radius-client-acct-resp {
         type uint64;
         description "Radius client accounting response";
       }
       leaf aaa-radius-client-acct-start-resp {
         type uint64;
         description "Radius client accounting start response";
       }
       leaf aaa-radius-client-acct-stop-resp {
         type uint64;
         description "Radius client accounting stop response";
       }
       leaf aaa-radius-client-acct-interim-resp {
         type uint64;
         description "Radius client accounting interim response";
       }
       leaf aaa-radius-client-acct-on-resp {
         type uint64;
         description "Radius client accounting on response";
       }
       leaf aaa-radius-client-acct-off-resp {
         type uint64;
         description "Radius client accounting off response";
       }
       leaf aaa-radius-client-duplicate-req {
         type uint64;
         description "Radius client duplicate request";
       }
       leaf aaa-radius-client-malformed-req {
         type uint64;
         description "Radius client malformed request";
       }
       leaf aaa-radius-req-bad-authenticator {
         type uint64;
         description "Radius requests with bad authenticator";
       }
       leaf aaa-radius-req-unknown {
         type uint64;
         description "Radius unknown request type";
       }
       leaf aaa-radius-dropped-req {
         type uint64;
         description "Radius request dropped";
       }
       leaf aaa-radius-client-last-cleared {
         type string;
         description "Time since the counters were last cleared";
       }
     }
   }
   grouping radius-snoop-segment-statistics-block {
     list aaa-radius-snoop-segment-stats {
       leaf aaa-radius-snoop-segment-name {
         type string;
         description "RADIUS snoop-segement";
       }
       leaf aaa-gateway-name {
         type string;
         description "Gateway name";
       }
       leaf aaa-fpc-pic {
         type string;
         description "FPC/PIC slot information";
       }
       leaf aaa-radius-client-acct-req {
         type uint64;
         description "Radius client accounting requests";
       }
       leaf aaa-radius-client-acct-start-req {
         type uint64;
         description "Radius client accounting start requests";
       }
       leaf aaa-radius-client-acct-stop-req {
         type uint64;
         description "Radius client accounting stop requests";
       }
       leaf aaa-radius-client-acct-interim-req {
         type uint64;
         description "Radius client accounting interim requests";
       }
       leaf aaa-radius-client-acct-on-req {
         type uint64;
         description "Radius client accounting on requests";
       }
       leaf aaa-radius-client-acct-off-req {
         type uint64;
         description "Radius client accounting off requests";
       }
       leaf aaa-radius-client-duplicate-req {
         type uint64;
         description "Radius client duplicate request";
       }
       leaf aaa-radius-client-malformed-req {
         type uint64;
         description "Radius client malformed request";
       }
       leaf aaa-radius-req-bad-authenticator {
         type uint64;
         description "Radius requests with bad authenticator";
       }
       leaf aaa-radius-req-unknown {
         type uint64;
         description "Radius unknown request type";
       }
       leaf aaa-radius-dropped-req {
         type uint64;
         description "Radius request dropped";
       }
       leaf aaa-radius-client-last-cleared {
         type string;
         description "Time since the counters were last cleared";
       }
     }
   }
   grouping tdf-gateway-status-block {
     container tdf-gateway-status-brief {
       leaf active-subscriber-count {
         type uint32;
         description "Number of active subscribers";
       }
       leaf active-ip-subscriber-count {
         type uint32;
         description "Number of active IP subscribers";
       }
       leaf active-ifl-subscriber-count {
         type uint32;
         description "Number of active IFL subscribers";
       }
       leaf active-svc-subscriber-count {
         type uint32;
         description "Number of active subscribers with services";
       }
       leaf active-ip-svc-subscriber-count {
         type uint32;
         description "Number of IP active subscribers with services";
       }
       leaf active-ifl-svc-subscriber-count {
         type uint32;
         description "Number of active IFL subscribers with services";
       }
       leaf del-pending-svc-subscriber-count {
         type uint32;
         description "Number of delete pending subscribers with services";
       }
       leaf del-pending-ip-svc-subscriber-count {
         type uint32;
         description "Number of delete pending IP subscribers with services";
       }
       leaf del-pending-ifl-svc-subscriber-count {
         type uint32;
         description "Number of delete pending IFL subscribers with services";
       }
       leaf active-svc-session-count {
         type uint64;
         description "Number of active sessions with services";
       }
       leaf cpu-load {
         type uint32;
         description "Current CPU load";
       }
       leaf memory-load {
         type uint32;
         description "Current Memory load";
       }
     }
     container tdf-gateway-status-detail {
       leaf fpc-slot {
         type int32;
         description "FPC slot";
       }
       leaf pic-slot {
         type int32;
         description "PIC slot";
       }
       leaf pic-role {
         type string;
         description "PIC Role Information Standalone/Primary/Secondary";
       }
       leaf pic-type {
         type string;
         description "Client type";
       }
       leaf active-subscriber-count {
         type uint32;
         description "Number of active subscribers";
       }
       leaf active-ip-subscriber-count {
         type uint32;
         description "Number of active IP subscribers";
       }
       leaf active-ifl-subscriber-count {
         type uint32;
         description "Number of active IFL subscribers";
       }
       leaf active-svc-subscriber-count {
         type uint32;
         description "Number of active subscribers with services";
       }
       leaf active-ip-svc-subscriber-count {
         type uint32;
         description "Number of IP active subscribers with services";
       }
       leaf active-ifl-svc-subscriber-count {
         type uint32;
         description "Number of active IFL subscribers with services";
       }
       leaf del-pending-svc-subscriber-count {
         type uint32;
         description "Number of delete pending subscribers with services";
       }
       leaf del-pending-ip-svc-subscriber-count {
         type uint32;
         description "Number of delete pending IP subscribers with services";
       }
       leaf del-pending-ifl-svc-subscriber-count {
         type uint32;
         description "Number of delete pending IFL subscribers with services";
       }
       leaf active-svc-session-count {
         type uint64;
         description "Number of active sessions with services";
       }
       leaf cpu-load {
         type uint32;
         description "Current CPU load";
       }
       leaf memory-load {
         type uint32;
         description "Current Memory load";
       }
     }
     container tdf-gateway-status-state {
       leaf session-established {
         type uint32;
         description "Established Sessions";
       }
       leaf session-deleting {
         type uint32;
         description "Sessions in deleting state";
       }
     }
   }
   grouping tdf-call-rate-statistics-root-block {
     leaf gateway-name {
       type string;
       description "Mobile Gateway Name";
     }
     leaf domain-name {
       type string;
       description "Domain Name";
     }
     list tdf-call-rate-statistics {
       leaf record-number {
         type uint32;
         description "Call-rate statistics history number";
       }
       leaf call-rate-time {
         type string;
         description "Time at which the call-rate statistics were retrieved";
       }
       leaf activation-count {
         type uint32;
         description "Activation count in the given period";
       }
       leaf deactivation-count {
         type uint32;
         description "Deactivation count in the given period";
       }
       leaf activation-processing-time {
         type string;
         description "Session Activation processing time";
       }
       leaf session-duration {
         type string;
         description "Session duration";
       }
     }
     container tdf-call-rate-statistics-standard-deviation {
       leaf activation-count-standard-deviation {
         type string;
         description "Activation standard deviation";
       }
       leaf deactivation-count-standard-deviation {
         type string;
         description "Deactivation standard deviation";
       }
       leaf activation-processing-time-standard-deviation {
         type string;
         description "Activation processing time standard deviation";
       }
       leaf session-duration-standard-deviation {
         type string;
         description "Session duration standard deviation";
       }
     }
   }
   grouping mobile-gateways-domain-service-mode-block {
     leaf domain-name {
       type string;
       description "Domain Name";
     }
     leaf gateway-name {
       type string;
       description "Mobile Gateway Name";
     }
     leaf mm-service-mode {
       type string;
       description "Service Mode Maintenance status for a profile";
     }
     container mm-service-mode-description {
       leaf mm-service-mode {
         type string;
         description "Service Mode Maintenance status for a profile";
       }
       leaf mm-service-mode-pending-mm-ack {
         type string;
       }
       leaf mm-service-mode-pending-ready-ack {
         type string;
       }
       list mobiled-session-description {
         leaf mobiled-client {
           type string;
           description "Mobiled Client - Could be RE or one of the SPICs";
         }
         leaf mobiled-peer-list {
           type string;
           description "Mobiled Peer List - Apps separated by commas";
         }
       }
       list mobiled-session-description2 {
         leaf mobiled-client {
           type string;
           description "Mobiled Client - Could be RE or one of the SPICs";
         }
         leaf mobiled-peer-list {
           type string;
           description "Mobiled Peer List - Apps separated by commas";
         }
       }
     }
   }
   grouping mobile-gateway-charging-trigger-profile-block {
     leaf mobile-gateway-name {
       type string;
       description "Gateway Name";
     }
     list charging-trigger-profile {
       leaf cg-tg-name {
         type string;
         description "Trigger profile name";
       }
       leaf cg-tg-id {
         type int32;
         description "Trigger profile ID";
       }
       leaf cg-tg-time-limit {
         type string;
         description "Trigger profile time limit enable/disable";
       }
       leaf cg-tg-volume-limit {
         type string;
         description "Trigger profile volume limit enable/disable";
       }
       leaf cg-tg-volume-limit-direction {
         type string;
         description "Trigger profile volume limit direction";
       }
       leaf cg-tg-plmn-change {
         type string;
         description "Trigger profile PLMN change enable/disable";
       }
       leaf cg-tg-qos-change {
         type string;
         description "Trigger profile QoS change enable/disable";
       }
       leaf cg-tg-rat-change {
         type string;
         description "Trigger profile RAT change enable/disable";
       }
       leaf cg-tg-sgsn-sgw-change {
         type string;
         description "Trigger profile SGSN/SGW change enable/disable";
       }
       leaf cg-tg-sgsn-mme-change {
         type string;
         description "Trigger profile SGSN/MME change enable/disable";
       }
       leaf cg-tg-user-loc-change {
         type string;
         description "Trigger profile user location change enable/disable";
       }
       leaf cg-tg-ms-time-zone-change {
         type string;
         description "Trigger profile MS time zone change enable/disable";
       }
     }
   }
   grouping mobile-gateways-sgw-idle-mode-buffering-statistics-block {
     container mfwd-gw-hdr {
       leaf mfwd-gw-name {
         type string;
         description "Gateway name";
       }
     }
     container mfwd-stats-hdr {
       leaf mfwd-stats-type {
         type string;
         description "Type of statistics";
       }
       leaf mfwd-fpc-slot {
         type int32;
         description "FPC slot";
       }
       leaf mfwd-pic-slot {
         type int32;
         description "PIC slot";
       }
     }
     list mfwd-idle-mode-stats {
       leaf mfwd-protocol {
         type string;
         description "Protocol";
       }
       leaf mfwd-dir {
         type string;
         description "Direction of flow";
       }
       leaf mfwd-pkt-rcvd {
         type uint64;
         description "Number of packets received from PFE(s)";
       }
       leaf mfwd-invalid-pkts {
         type uint64;
         description "Number of invalid packets received from PFE(s)";
       }
       leaf mfwd-flows-created {
         type uint64;
         description "Number of flows created";
       }
       leaf mfwd-flows-agedout {
         type uint64;
         description "Number of flows aged out";
       }
       leaf mfwd-active-flows {
         type uint64;
         description "Number of currently active flows";
       }
       leaf mfwd-active-flows-buffered {
         type uint64;
         description "Number of currently active flows being buffered";
       }
       leaf mfwd-fpc-slot {
         type int32;
         description "FPC slot";
       }
       leaf mfwd-pic-slot {
         type int32;
         description "PIC slot";
       }
     }
     container mfwd-buffering-stats {
       leaf mfwd-active-flows-buffered {
         type uint64;
         description "Number of currently active flows being buffered";
       }
       container mfwd-buffering-pkt-stats {
         leaf mfwd-total-pkts-rcvd {
           type uint64;
           description "Total number of packets received from PFE(s)";
         }
         leaf mfwd-total-invalid-pkts {
           type uint64;
           description "Total number of invalid packets received from PFE(s)";
         }
         leaf mfwd-current-pkts-buffered {
           type uint64;
           description "Current number of packets buffered";
         }
         leaf mfwd-current-bytes-buffered {
           type uint64;
           description "Current size (in bytes) of packets buffered";
         }
         leaf mfwd-total-pkts-reinjected {
           type uint64;
           description "Total number of packets reinjected";
         }
         leaf mfwd-total-bytes-reinjected {
           type uint64;
           description "Total size (in bytes) of packets reinjected to PFE(s)";
         }
         leaf mfwd-total-pkts-exceeded-limit {
           type uint64;
           description "Total number of packets exceeding buffering limit";
         }
         leaf mfwd-total-bytes-exceeded-limit {
           type uint64;
           description "Total size (in bytes) of packets exceeding buffering limit";
         }
         leaf mfwd-total-buffered-pkts-dropped {
           type uint64;
           description "Total number of buffered packets dropped";
         }
         leaf mfwd-total-buffered-bytes-dropped {
           type uint64;
           description "Total size (in bytes) of buffered packets dropped";
         }
       }
       container mfwd-buffering-limit-stats {
         leaf mfwd-ded-buffer-exceeded {
           type uint64;
           description "Number of times dedicated buffer limit is exceeded";
         }
         leaf mfwd-shr-buffer-exceeded {
           type uint64;
           description "Number of times shared buffer limit is exceeded";
         }
         leaf mfwd-ded-memory-exceeded {
           type uint64;
           description "Number of times dedicated memory limit is exceeded";
         }
         leaf mfwd-shr-memory-exceeded {
           type uint64;
           description "Number of times shared memory limit is exceeded";
         }
       }
       container mfwd-buffering-memory-stats {
         leaf mfwd-total-memory-used {
           type uint64;
           description "Total memory used for buffering (in bytes)";
         }
         leaf mfwd-total-memory-free {
           type uint64;
           description "Total memory free for buffering (in bytes)";
         }
         leaf mfwd-ded-memory-used {
           type uint64;
           description "Amount of dedicated memory used (in %)";
         }
         leaf mfwd-shr-memory-used {
           type uint64;
           description "Amount of shared memory used (in %)";
         }
       }
     }
   }
   grouping mobile-gateway-information-block {
     leaf gw-num-gateways {
       type uint32;
       description "Number of configured gateways";
     }
   }
 }
