/*
 * Copyright (c) 2023 Juniper Networks, Inc.
 * All rights reserved.
 */
 module junos-rpc-tcp-forwarding {
   namespace "http://yang.juniper.net/junos/rpc/tcp-forwarding";

   prefix tcp-forwarding;

   import junos-common-types {
     prefix jt;
     revision-date 2023-01-01;
   }

   organization "Juniper Networks, Inc.";

   contact "yang-support@juniper.net";

   description "Junos RPC YANG module for tcp-forwarding command(s)";

   revision 2023-01-01 {
     description "Junos: 23.1R1.8";
   }

   rpc get-tcpfwd-status {
     description "Show status information";
     output {
       container tcpfwd-status {
         uses tcpfwd-status-block;
       }
     }
   }
   rpc get-tcpfwd-status-listener {
     description "Show listener status information";
     input {
       leaf port-number {
         description "TCP listening port";
         type union {
           type string {
             pattern "<.*>|$.*";
           }
           type uint16 {
             range "8000 .. 8063";
           }
         }
         mandatory true;
       }
       leaf listening-address {
         description "TCP listening address";
         type string;
         mandatory true;
       }
       leaf routing-instance {
         description "Routing instance";
         type string;
       }
     }
     output {
       container tcpfwd-status {
         uses tcpfwd-status-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping tcpfwd-status-block {
     leaf routing-instance {
       type string;
       description "Routing instance";
     }
     leaf listening-address {
       type string;
       description "Listening address";
     }
     leaf listening-port {
       type uint32;
       description "Listening port";
     }
     leaf listening-status {
       type string;
       description "Listening status";
     }
     leaf listening-received-bytes {
       type uint64;
       description "Number of bytes received on the listening connection";
     }
     leaf listening-transmitted-bytes {
       type uint64;
       description "Number of bytes transmitted on the listening connection";
     }
     leaf forwarding-routing-instance {
       type string;
       description "Forwarding routing instance";
     }
     leaf forwarding-address {
       type string;
       description "Forwarding address";
     }
     leaf forwarding-port {
       type uint32;
       description "Forwarding port";
     }
     leaf forwarding-received-bytes {
       type uint64;
       description "Number of bytes received on the forwarding connection";
     }
     leaf forwarding-transmitted-bytes {
       type uint64;
       description "Number of bytes transmitted on the forwarding connection";
     }
     leaf source-prefix {
       type string;
       description "Source prefix";
     }
     leaf source-address {
       type string;
       description "Source address";
     }
     leaf source-port {
       type uint32;
       description "Source port";
     }
     container tcpfwd-allowed-sources {
       description "TCP forwarding allowed source prefixes";
       leaf source-prefix {
         type string;
         description "Source prefix";
       }
     }
     container tcpfwd-connections {
       description "TCP connections status";
       leaf max-connections {
         type uint32;
         description "Max connections";
       }
       leaf active-connections {
         type uint32;
         description "Active connections";
       }
       leaf source-address {
         type string;
         description "Source address";
       }
       leaf source-port {
         type uint32;
         description "Source port";
       }
       leaf listening-status {
         type string;
         description "Listening status";
       }
       leaf listening-received-bytes {
         type uint64;
         description "Number of bytes received on the listening connection";
       }
       leaf listening-transmitted-bytes {
         type uint64;
         description "Number of bytes transmitted on the listening connection";
       }
       leaf forwarding-status {
         type string;
         description "Forwarding status";
       }
       leaf forwarding-received-bytes {
         type uint64;
         description "Number of bytes received on the forwarding connection";
       }
       leaf forwarding-transmitted-bytes {
         type uint64;
         description "Number of bytes transmitted on the forwarding connection";
       }
     }
   }
 }
