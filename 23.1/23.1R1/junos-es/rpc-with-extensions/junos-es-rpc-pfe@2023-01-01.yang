/*
 * Copyright (c) 2023 Juniper Networks, Inc.
 * All rights reserved.
 */
 module junos-es-rpc-pfe {
   namespace "http://yang.juniper.net/junos-es/rpc/pfe";

   prefix pfe;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for pfe command(s)";

   revision 2023-01-01 {
     description "Junos: 23.1R1.8";
   }

   rpc get-pfe-data {
     description "Show Packet Forwarding Engine data";
     junos:command "show pfe data";
     input {
       leaf command {
         description "Command line to show";
         junos:cli-feature "nokeyword";
         type string {
           length "1 .. 80";
         }
         mandatory true;
       }
       leaf target {
         description "Component on which command is showed";
         type string;
       }
     }
     output {
       choice output_c {
         case output-tag {
           leaf output {
             type string;
           }
         }
         case multichassis-tag {
           anyxml multi-routing-engine-results;
         }
       }
     }
   }
   rpc get-pfe-information {
     description "Show list of Packet Forwarding Engine components";
     junos:command "show pfe terse";
     input {
       uses command-forwarding;
     }
     output {
       container pfe-information {
         uses pfe-information-block;
       }
     }
   }
   rpc get-pfe-statistics {
     description "Show Packet Forwarding Engine traffic statistics";
     junos:command "show pfe statistics traffic";
     output {
       container pfe-statistics {
         uses pfe-statistics-block;
       }
     }
   }
   rpc get-pfe-stats-error {
     description "Show error statistics";
     junos:command "show pfe statistics error";
     output {
       container pfe-stats-error {
         uses pfe-stats-error-block;
       }
     }
   }
   rpc get-vxlan-information {
     description "Show VxLAN Egress L3 information";
     junos:command "show pfe vxlan";
     output {
       choice output_c {
         case output-tag {
           leaf output {
             type string;
           }
         }
         case multichassis-tag {
           anyxml multi-routing-engine-results;
         }
       }
     }
   }
   rpc get-vxlan-next-hop-usage-information {
     description "Show utilization of the Egress L3 Next-hop table";
     junos:command "show pfe vxlan nh-usage";
     output {
       choice output_c {
         case output-tag {
           leaf output {
             type string;
           }
         }
         case multichassis-tag {
           anyxml multi-routing-engine-results;
         }
       }
     }
   }
   rpc get-vxlan-interface-usage-information {
     description "Show utilization of the Egress L3 Interface number table";
     junos:command "show pfe vxlan intf-usage";
     output {
       choice output_c {
         case output-tag {
           leaf output {
             type string;
           }
         }
         case multichassis-tag {
           anyxml multi-routing-engine-results;
         }
       }
     }
   }
   rpc get-vxlan-vport-usage-information {
     description "Show utilization of the source vport table";
     junos:command "show pfe vxlan vport-usage";
     output {
       choice output_c {
         case output-tag {
           leaf output {
             type string;
           }
         }
         case multichassis-tag {
           anyxml multi-routing-engine-results;
         }
       }
     }
   }
   rpc get-pfe-tcam-usage-all-tcam-stages {
     description "Show packet forwarding engine tcam usage at all tcam stages";
     junos:command "show pfe tcam usage all-tcam-stages";
     output {
       choice output_c {
         case output-tag {
           leaf output {
             type string;
           }
         }
         case multichassis-tag {
           anyxml multi-routing-engine-results;
         }
       }
     }
   }
   rpc get-pfe-tcam-usage-all-tcam-stages-detail {
     description "Show packet forwarding engine tcam usage at all tcam stages in detail";
     junos:command "show pfe tcam usage all-tcam-stages detail";
     output {
       choice output_c {
         case output-tag {
           leaf output {
             type string;
           }
         }
         case multichassis-tag {
           anyxml multi-routing-engine-results;
         }
       }
     }
   }
   rpc get-pfe-tcam-usage-egress-tcam-stage {
     description "Show tcam usage for egress tcam-stage";
     junos:command "show pfe tcam usage tcam-stage egress";
     output {
       choice output_c {
         case output-tag {
           leaf output {
             type string;
           }
         }
         case multichassis-tag {
           anyxml multi-routing-engine-results;
         }
       }
     }
   }
   rpc get-pfe-tcam-usage-egress-tcam-stage-detail {
     description "Show tcam usage for egress tcam-stage in detail";
     junos:command "show pfe tcam usage tcam-stage egress detail";
     output {
       choice output_c {
         case output-tag {
           leaf output {
             type string;
           }
         }
         case multichassis-tag {
           anyxml multi-routing-engine-results;
         }
       }
     }
   }
   rpc get-pfe-tcam-usage-egress-app {
     description "Show tcam usage for a tcam app";
     junos:command "show pfe tcam usage tcam-stage egress app";
     output {
       choice output_c {
         case output-tag {
           leaf output {
             type string;
           }
         }
         case multichassis-tag {
           anyxml multi-routing-engine-results;
         }
       }
     }
   }
   rpc get-pfe-tcam-usage-egress-tcam-stage-detail-bd-tpid-swap {
     description "Bridge domain vlan-map with swap tpid operation";
     junos:command "show pfe tcam usage tcam-stage egress app bd-tpid-swap";
     output {
       choice output_c {
         case output-tag {
           leaf output {
             type string;
           }
         }
         case multichassis-tag {
           anyxml multi-routing-engine-results;
         }
       }
     }
   }
   rpc get-pfe-tcam-usage-egress-tcam-stage-detail-fw-family-out {
     description "Family level egress firewall";
     junos:command "show pfe tcam usage tcam-stage egress app fw-family-out";
     output {
       choice output_c {
         case output-tag {
           leaf output {
             type string;
           }
         }
         case multichassis-tag {
           anyxml multi-routing-engine-results;
         }
       }
     }
   }
   rpc get-pfe-tcam-usage-egress-tcam-stage-detail-fw-inet6-family-out {
     description "Inet6 Family level egress firewall";
     junos:command "show pfe tcam usage tcam-stage egress app fw-inet6-family-out";
     output {
       choice output_c {
         case output-tag {
           leaf output {
             type string;
           }
         }
         case multichassis-tag {
           anyxml multi-routing-engine-results;
         }
       }
     }
   }
   rpc get-pfe-tcam-usage-egress-tcam-stage-detail-fw-ifl-out {
     description "Ifl level egress firewall";
     junos:command "show pfe tcam usage tcam-stage egress app fw-ifl-out";
     output {
       choice output_c {
         case output-tag {
           leaf output {
             type string;
           }
         }
         case multichassis-tag {
           anyxml multi-routing-engine-results;
         }
       }
     }
   }
   rpc get-pfe-tcam-usage-egress-tcam-stage-detail-ifl-statistics-out {
     description "Ifl level statistics (egress)";
     junos:command "show pfe tcam usage tcam-stage egress app ifl-statistics-out";
     output {
       choice output_c {
         case output-tag {
           leaf output {
             type string;
           }
         }
         case multichassis-tag {
           anyxml multi-routing-engine-results;
         }
       }
     }
   }
   rpc get-pfe-tcam-usage-egress-tcam-stage-detail-irb-cos-rw {
     description "IRB CoS rewrite";
     junos:command "show pfe tcam usage tcam-stage egress app irb-cos-rw";
     output {
       choice output_c {
         case output-tag {
           leaf output {
             type string;
           }
         }
         case multichassis-tag {
           anyxml multi-routing-engine-results;
         }
       }
     }
   }
   rpc get-pfe-tcam-usage-egress-tcam-stage-detail-lfm-802.3ah-out {
     description "Lfm-802.3ah (egress)";
     junos:command "show pfe tcam usage tcam-stage egress app lfm-802.3ah-out";
     output {
       choice output_c {
         case output-tag {
           leaf output {
             type string;
           }
         }
         case multichassis-tag {
           anyxml multi-routing-engine-results;
         }
       }
     }
   }
   rpc get-pfe-tcam-usage-ingress-tcam-stage {
     description "Show tcam usage for ingress tcam-stage";
     junos:command "show pfe tcam usage tcam-stage ingress";
     output {
       choice output_c {
         case output-tag {
           leaf output {
             type string;
           }
         }
         case multichassis-tag {
           anyxml multi-routing-engine-results;
         }
       }
     }
   }
   rpc get-pfe-tcam-usage-ingress-tcam-stage-detail {
     description "Show tcam usage for ingress tcam-stage in detail";
     junos:command "show pfe tcam usage tcam-stage ingress detail";
     output {
       choice output_c {
         case output-tag {
           leaf output {
             type string;
           }
         }
         case multichassis-tag {
           anyxml multi-routing-engine-results;
         }
       }
     }
   }
   rpc get-pfe-tcam-usage-ingress-app {
     description "Show tcam usage for a tcam app";
     junos:command "show pfe tcam usage tcam-stage ingress app";
     output {
       choice output_c {
         case output-tag {
           leaf output {
             type string;
           }
         }
         case multichassis-tag {
           anyxml multi-routing-engine-results;
         }
       }
     }
   }
   rpc get-pfe-tcam-usage-ingress-app-cfm-bd-filter {
     description "Cfm implicit bridge-domain filters";
     junos:command "show pfe tcam usage tcam-stage ingress app cfm-bd-filter";
     output {
       choice output_c {
         case output-tag {
           leaf output {
             type string;
           }
         }
         case multichassis-tag {
           anyxml multi-routing-engine-results;
         }
       }
     }
   }
   rpc get-pfe-tcam-usage-ingress-app-cfm-filter {
     description "Cfm implicit filters";
     junos:command "show pfe tcam usage tcam-stage ingress app cfm-filter";
     output {
       choice output_c {
         case output-tag {
           leaf output {
             type string;
           }
         }
         case multichassis-tag {
           anyxml multi-routing-engine-results;
         }
       }
     }
   }
   rpc get-pfe-tcam-usage-ingress-app-cfm-vpls-filter {
     description "Cfm implicit vpls filters";
     junos:command "show pfe tcam usage tcam-stage ingress app cfm-vpls-filter";
     output {
       choice output_c {
         case output-tag {
           leaf output {
             type string;
           }
         }
         case multichassis-tag {
           anyxml multi-routing-engine-results;
         }
       }
     }
   }
   rpc get-pfe-tcam-usage-ingress-app-cfm-vpls-ifl-filter {
     description "Cfm implicit vpls ifl filters";
     junos:command "show pfe tcam usage tcam-stage ingress app cfm-vpls-ifl-filter";
     output {
       choice output_c {
         case output-tag {
           leaf output {
             type string;
           }
         }
         case multichassis-tag {
           anyxml multi-routing-engine-results;
         }
       }
     }
   }
   rpc get-pfe-tcam-usage-ingress-app-fw-ccc-in {
     description "Ccc family ingress firewall";
     junos:command "show pfe tcam usage tcam-stage ingress app fw-ccc-in";
     output {
       choice output_c {
         case output-tag {
           leaf output {
             type string;
           }
         }
         case multichassis-tag {
           anyxml multi-routing-engine-results;
         }
       }
     }
   }
   rpc get-pfe-tcam-usage-ingress-app-fw-ifl-in {
     description "Ifl level ingress firewall";
     junos:command "show pfe tcam usage tcam-stage ingress app fw-ifl-in";
     output {
       choice output_c {
         case output-tag {
           leaf output {
             type string;
           }
         }
         case multichassis-tag {
           anyxml multi-routing-engine-results;
         }
       }
     }
   }
   rpc get-pfe-tcam-usage-ingress-app-fw-inet-ftf {
     description "Inet family ingress firewall on a forwarding-table";
     junos:command "show pfe tcam usage tcam-stage ingress app fw-inet-ftf";
     output {
       choice output_c {
         case output-tag {
           leaf output {
             type string;
           }
         }
         case multichassis-tag {
           anyxml multi-routing-engine-results;
         }
       }
     }
   }
   rpc get-pfe-tcam-usage-ingress-app-fw-inet-in {
     description "Inet family ingress firewall";
     junos:command "show pfe tcam usage tcam-stage ingress app fw-inet-in";
     output {
       choice output_c {
         case output-tag {
           leaf output {
             type string;
           }
         }
         case multichassis-tag {
           anyxml multi-routing-engine-results;
         }
       }
     }
   }
   rpc get-pfe-tcam-usage-ingress-app-fw-inet-rpf {
     description "Inet family ingress firewall on rpf fail check";
     junos:command "show pfe tcam usage tcam-stage ingress app fw-inet-rpf";
     output {
       choice output_c {
         case output-tag {
           leaf output {
             type string;
           }
         }
         case multichassis-tag {
           anyxml multi-routing-engine-results;
         }
       }
     }
   }
   rpc get-pfe-tcam-usage-ingress-app-fw-inet6-ftf {
     description "Inet6 family ingress firewall on a forwarding-table";
     junos:command "show pfe tcam usage tcam-stage ingress app fw-inet6-ftf";
     output {
       choice output_c {
         case output-tag {
           leaf output {
             type string;
           }
         }
         case multichassis-tag {
           anyxml multi-routing-engine-results;
         }
       }
     }
   }
   rpc get-pfe-tcam-usage-ingress-app-fw-inet6-in {
     description "Inet6 family ingress firewall";
     junos:command "show pfe tcam usage tcam-stage ingress app fw-inet6-in";
     output {
       choice output_c {
         case output-tag {
           leaf output {
             type string;
           }
         }
         case multichassis-tag {
           anyxml multi-routing-engine-results;
         }
       }
     }
   }
   rpc get-pfe-tcam-usage-ingress-app-fw-inet6-rpf {
     description "Inet6 family ingress firewall on a rpf fail check";
     junos:command "show pfe tcam usage tcam-stage ingress app fw-inet6-rpf";
     output {
       choice output_c {
         case output-tag {
           leaf output {
             type string;
           }
         }
         case multichassis-tag {
           anyxml multi-routing-engine-results;
         }
       }
     }
   }
   rpc get-pfe-tcam-usage-ingress-app-fw-l2-in {
     description "Bridge family ingress firewall on layer2 interface";
     junos:command "show pfe tcam usage tcam-stage ingress app fw-l2-in";
     output {
       choice output_c {
         case output-tag {
           leaf output {
             type string;
           }
         }
         case multichassis-tag {
           anyxml multi-routing-engine-results;
         }
       }
     }
   }
   rpc get-pfe-tcam-usage-ingress-app-fw-mpls-in {
     description "Mpls family ingress firewall";
     junos:command "show pfe tcam usage tcam-stage ingress app fw-mpls-in";
     output {
       choice output_c {
         case output-tag {
           leaf output {
             type string;
           }
         }
         case multichassis-tag {
           anyxml multi-routing-engine-results;
         }
       }
     }
   }
   rpc get-pfe-tcam-usage-ingress-app-fw-vpls-in {
     description "VPLS family ingress firewall on vpls interface";
     junos:command "show pfe tcam usage tcam-stage ingress app fw-vpls-in";
     output {
       choice output_c {
         case output-tag {
           leaf output {
             type string;
           }
         }
         case multichassis-tag {
           anyxml multi-routing-engine-results;
         }
       }
     }
   }
   rpc get-pfe-tcam-usage-ingress-app-gr-ifl-statistics-egr {
     description "GR Ifl level statistics (egress)";
     junos:command "show pfe tcam usage tcam-stage ingress app gr-ifl-stats-egr";
     output {
       choice output_c {
         case output-tag {
           leaf output {
             type string;
           }
         }
         case multichassis-tag {
           anyxml multi-routing-engine-results;
         }
       }
     }
   }
   rpc get-pfe-tcam-usage-ingress-app-gr-ifl-statistics-ing {
     description "GR Ifl level statistics (ingress)";
     junos:command "show pfe tcam usage tcam-stage ingress app gr-ifl-stats-ing";
     output {
       choice output_c {
         case output-tag {
           leaf output {
             type string;
           }
         }
         case multichassis-tag {
           anyxml multi-routing-engine-results;
         }
       }
     }
   }
   rpc get-pfe-tcam-usage-ingress-app-gr-ifl-statistics-preing {
     description "GR Ifl level statistics (pre-ingress)";
     junos:command "show pfe tcam usage tcam-stage ingress app gr-ifl-stats-preing";
     output {
       choice output_c {
         case output-tag {
           leaf output {
             type string;
           }
         }
         case multichassis-tag {
           anyxml multi-routing-engine-results;
         }
       }
     }
   }
   rpc get-pfe-tcam-usage-ingress-app-ifl-statistics-in {
     description "Ifl level statistics (ingress)";
     junos:command "show pfe tcam usage tcam-stage ingress app ifl-statistics-in";
     output {
       choice output_c {
         case output-tag {
           leaf output {
             type string;
           }
         }
         case multichassis-tag {
           anyxml multi-routing-engine-results;
         }
       }
     }
   }
   rpc get-pfe-tcam-usage-ingress-app-irb-fixed-cos {
     description "IRB fixed classifier filter entries";
     junos:command "show pfe tcam usage tcam-stage ingress app irb-fixed-cos";
     output {
       choice output_c {
         case output-tag {
           leaf output {
             type string;
           }
         }
         case multichassis-tag {
           anyxml multi-routing-engine-results;
         }
       }
     }
   }
   rpc get-pfe-tcam-usage-ingress-app-mrouter-port-in {
     description "Multicast router port for snooping";
     junos:command "show pfe tcam usage tcam-stage ingress app mrouter-port-in";
     output {
       choice output_c {
         case output-tag {
           leaf output {
             type string;
           }
         }
         case multichassis-tag {
           anyxml multi-routing-engine-results;
         }
       }
     }
   }
   rpc get-pfe-tcam-usage-ingress-app-lo0-inet-fil {
     description "Lo0 Inet Filter";
     junos:command "show pfe tcam usage tcam-stage ingress app lo0-inet-fil";
     output {
       choice output_c {
         case output-tag {
           leaf output {
             type string;
           }
         }
         case multichassis-tag {
           anyxml multi-routing-engine-results;
         }
       }
     }
   }
   rpc get-pfe-tcam-usage-ingress-app-lo0-inet6-fil {
     description "Lo0 Inet6 Filter";
     junos:command "show pfe tcam usage tcam-stage ingress app lo0-inet6-fil";
     output {
       choice output_c {
         case output-tag {
           leaf output {
             type string;
           }
         }
         case multichassis-tag {
           anyxml multi-routing-engine-results;
         }
       }
     }
   }
   rpc get-pfe-tcam-usage-ingress-app-mac-drop-cnt {
     description "Statistics for drops by mac-validate/src-mac filters";
     junos:command "show pfe tcam usage tcam-stage ingress app mac-drop-cnt";
     output {
       choice output_c {
         case output-tag {
           leaf output {
             type string;
           }
         }
         case multichassis-tag {
           anyxml multi-routing-engine-results;
         }
       }
     }
   }
   rpc get-pfe-tcam-usage-ingress-app-no-local-switching {
     description "Bridge no-local-switching";
     junos:command "show pfe tcam usage tcam-stage ingress app no-local-switching";
     output {
       choice output_c {
         case output-tag {
           leaf output {
             type string;
           }
         }
         case multichassis-tag {
           anyxml multi-routing-engine-results;
         }
       }
     }
   }
   rpc get-pfe-tcam-usage-pre-ingress-tcam-stage {
     description "Show tcam usage for pre-ingress tcam-stage";
     junos:command "show pfe tcam usage tcam-stage pre-ingress";
     output {
       choice output_c {
         case output-tag {
           leaf output {
             type string;
           }
         }
         case multichassis-tag {
           anyxml multi-routing-engine-results;
         }
       }
     }
   }
   rpc get-pfe-tcam-usage-pre-ingress-tcam-stage-detail {
     description "Show tcam usage for pre-ingress tcam-stage in detail";
     junos:command "show pfe tcam usage tcam-stage pre-ingress detail";
     output {
       choice output_c {
         case output-tag {
           leaf output {
             type string;
           }
         }
         case multichassis-tag {
           anyxml multi-routing-engine-results;
         }
       }
     }
   }
   rpc get-pfe-tcam-usage-pre-ingress-app {
     description "Show tcam usage for a tcam app";
     junos:command "show pfe tcam usage tcam-stage pre-ingress app";
     output {
       choice output_c {
         case output-tag {
           leaf output {
             type string;
           }
         }
         case multichassis-tag {
           anyxml multi-routing-engine-results;
         }
       }
     }
   }
   rpc get-pfe-tcam-usage-pre-ingress-app-cos-fc {
     description "Ifl level fixed classifier";
     junos:command "show pfe tcam usage tcam-stage pre-ingress app cos-fc";
     output {
       choice output_c {
         case output-tag {
           leaf output {
             type string;
           }
         }
         case multichassis-tag {
           anyxml multi-routing-engine-results;
         }
       }
     }
   }
   rpc get-pfe-tcam-usage-pre-ingress-app-fw-fbf {
     description "Firewall filter based forwarding";
     junos:command "show pfe tcam usage tcam-stage pre-ingress app fw-fbf";
     output {
       choice output_c {
         case output-tag {
           leaf output {
             type string;
           }
         }
         case multichassis-tag {
           anyxml multi-routing-engine-results;
         }
       }
     }
   }
   rpc get-pfe-tcam-usage-pre-ingress-app-fw-fbf-inet6 {
     description "Firewall filter based forwarding for Inet6";
     junos:command "show pfe tcam usage tcam-stage pre-ingress app fw-fbf-inet6";
     output {
       choice output_c {
         case output-tag {
           leaf output {
             type string;
           }
         }
         case multichassis-tag {
           anyxml multi-routing-engine-results;
         }
       }
     }
   }
   rpc get-pfe-tcam-usage-pre-ingress-app-fw-semantics {
     description "Firewall sharing semantics for cli configured firewall";
     junos:command "show pfe tcam usage tcam-stage pre-ingress app fw-semantics";
     output {
       choice output_c {
         case output-tag {
           leaf output {
             type string;
           }
         }
         case multichassis-tag {
           anyxml multi-routing-engine-results;
         }
       }
     }
   }
   rpc get-pfe-tcam-usage-pre-ingress-app-ifd-src-mac-fil {
     description "Ifd level source mac filter";
     junos:command "show pfe tcam usage tcam-stage pre-ingress app ifd-src-mac-fil";
     output {
       choice output_c {
         case output-tag {
           leaf output {
             type string;
           }
         }
         case multichassis-tag {
           anyxml multi-routing-engine-results;
         }
       }
     }
   }
   rpc get-pfe-tcam-usage-pre-ingress-app-ing-out-iff {
     description "Ingress app on behalf of egress family filter for log/syslog";
     junos:command "show pfe tcam usage tcam-stage pre-ingress app ing-out-iff";
     output {
       choice output_c {
         case output-tag {
           leaf output {
             type string;
           }
         }
         case multichassis-tag {
           anyxml multi-routing-engine-results;
         }
       }
     }
   }
   rpc get-pfe-tcam-usage-pre-ingress-app-ip-mac-val {
     description "Ip mac validate";
     junos:command "show pfe tcam usage tcam-stage pre-ingress app ip-mac-val";
     output {
       choice output_c {
         case output-tag {
           leaf output {
             type string;
           }
         }
         case multichassis-tag {
           anyxml multi-routing-engine-results;
         }
       }
     }
   }
   rpc get-pfe-tcam-usage-pre-ingress-app-ip-mac-val-bcast {
     description "Ip mac validate for broadcast";
     junos:command "show pfe tcam usage tcam-stage pre-ingress app ip-mac-val-bcast";
     output {
       choice output_c {
         case output-tag {
           leaf output {
             type string;
           }
         }
         case multichassis-tag {
           anyxml multi-routing-engine-results;
         }
       }
     }
   }
   rpc get-pfe-tcam-usage-pre-ingress-app-rfc2544-layer2-in {
     description "Rfc2544 for layer2 service (ingress)";
     junos:command "show pfe tcam usage tcam-stage pre-ingress app rfc2544-layer2-in";
     output {
       choice output_c {
         case output-tag {
           leaf output {
             type string;
           }
         }
         case multichassis-tag {
           anyxml multi-routing-engine-results;
         }
       }
     }
   }
   rpc get-pfe-tcam-usage-app {
     description "Show tcam usage for a tcam app";
     junos:command "show pfe tcam usage app";
     output {
       choice output_c {
         case output-tag {
           leaf output {
             type string;
           }
         }
         case multichassis-tag {
           anyxml multi-routing-engine-results;
         }
       }
     }
   }
   rpc get-pfe-tcam-usage-app-bd-tpid-swap {
     description "Bridge domain vlan-map with swap tpid operation";
     junos:command "show pfe tcam usage app bd-tpid-swap";
     output {
       choice output_c {
         case output-tag {
           leaf output {
             type string;
           }
         }
         case multichassis-tag {
           anyxml multi-routing-engine-results;
         }
       }
     }
   }
   rpc get-pfe-tcam-usage-app-fw-family-out {
     description "Family level egress firewall";
     junos:command "show pfe tcam usage app fw-family-out";
     output {
       choice output_c {
         case output-tag {
           leaf output {
             type string;
           }
         }
         case multichassis-tag {
           anyxml multi-routing-engine-results;
         }
       }
     }
   }
   rpc get-pfe-tcam-usage-app-fw-inet6-family-out {
     description "Inet6 Family level egress firewall";
     junos:command "show pfe tcam usage app fw-inet6-family-out";
     output {
       choice output_c {
         case output-tag {
           leaf output {
             type string;
           }
         }
         case multichassis-tag {
           anyxml multi-routing-engine-results;
         }
       }
     }
   }
   rpc get-pfe-tcam-usage-app-fw-ifl-out {
     description "Ifl level egress firewall";
     junos:command "show pfe tcam usage app fw-ifl-out";
     output {
       choice output_c {
         case output-tag {
           leaf output {
             type string;
           }
         }
         case multichassis-tag {
           anyxml multi-routing-engine-results;
         }
       }
     }
   }
   rpc get-pfe-tcam-usage-app-ifl-statistics-out {
     description "Ifl level statistics (egress)";
     junos:command "show pfe tcam usage app ifl-statistics-out";
     output {
       choice output_c {
         case output-tag {
           leaf output {
             type string;
           }
         }
         case multichassis-tag {
           anyxml multi-routing-engine-results;
         }
       }
     }
   }
   rpc get-pfe-tcam-usage-app-irb-cos-rw {
     description "IRB CoS rewrite";
     junos:command "show pfe tcam usage app irb-cos-rw";
     output {
       choice output_c {
         case output-tag {
           leaf output {
             type string;
           }
         }
         case multichassis-tag {
           anyxml multi-routing-engine-results;
         }
       }
     }
   }
   rpc get-pfe-tcam-usage-app-lfm-802.3ah-out {
     description "Lfm-802.3ah (egress)";
     junos:command "show pfe tcam usage app lfm-802.3ah-out";
     output {
       choice output_c {
         case output-tag {
           leaf output {
             type string;
           }
         }
         case multichassis-tag {
           anyxml multi-routing-engine-results;
         }
       }
     }
   }
   rpc get-pfe-tcam-usage-app-cfm-bd-filter {
     description "Cfm implicit bridge-domain filters";
     junos:command "show pfe tcam usage app cfm-bd-filter";
     output {
       choice output_c {
         case output-tag {
           leaf output {
             type string;
           }
         }
         case multichassis-tag {
           anyxml multi-routing-engine-results;
         }
       }
     }
   }
   rpc get-pfe-tcam-usage-app-cfm-filter {
     description "Cfm implicit filters";
     junos:command "show pfe tcam usage app cfm-filter";
     output {
       choice output_c {
         case output-tag {
           leaf output {
             type string;
           }
         }
         case multichassis-tag {
           anyxml multi-routing-engine-results;
         }
       }
     }
   }
   rpc get-pfe-tcam-usage-app-cfm-vpls-filter {
     description "Cfm implicit vpls filters";
     junos:command "show pfe tcam usage app cfm-vpls-filter";
     output {
       choice output_c {
         case output-tag {
           leaf output {
             type string;
           }
         }
         case multichassis-tag {
           anyxml multi-routing-engine-results;
         }
       }
     }
   }
   rpc get-pfe-tcam-usage-app-cfm-vpls-ifl-filter {
     description "Cfm implicit vpls ifl filters";
     junos:command "show pfe tcam usage app cfm-vpls-ifl-filter";
     output {
       choice output_c {
         case output-tag {
           leaf output {
             type string;
           }
         }
         case multichassis-tag {
           anyxml multi-routing-engine-results;
         }
       }
     }
   }
   rpc get-pfe-tcam-usage-app-fw-ccc-in {
     description "Ccc family ingress firewall";
     junos:command "show pfe tcam usage app fw-ccc-in";
     output {
       choice output_c {
         case output-tag {
           leaf output {
             type string;
           }
         }
         case multichassis-tag {
           anyxml multi-routing-engine-results;
         }
       }
     }
   }
   rpc get-pfe-tcam-usage-app-fw-ifl-in {
     description "Ifl level ingress firewall";
     junos:command "show pfe tcam usage app fw-ifl-in";
     output {
       choice output_c {
         case output-tag {
           leaf output {
             type string;
           }
         }
         case multichassis-tag {
           anyxml multi-routing-engine-results;
         }
       }
     }
   }
   rpc get-pfe-tcam-usage-app-fw-inet-ftf {
     description "Inet family ingress firewall on a forwarding-table";
     junos:command "show pfe tcam usage app fw-inet-ftf";
     output {
       choice output_c {
         case output-tag {
           leaf output {
             type string;
           }
         }
         case multichassis-tag {
           anyxml multi-routing-engine-results;
         }
       }
     }
   }
   rpc get-pfe-tcam-usage-app-fw-inet-in {
     description "Inet family ingress firewall";
     junos:command "show pfe tcam usage app fw-inet-in";
     output {
       choice output_c {
         case output-tag {
           leaf output {
             type string;
           }
         }
         case multichassis-tag {
           anyxml multi-routing-engine-results;
         }
       }
     }
   }
   rpc get-pfe-tcam-usage-app-fw-inet-rpf {
     description "Inet family ingress firewall on rpf fail check";
     junos:command "show pfe tcam usage app fw-inet-rpf";
     output {
       choice output_c {
         case output-tag {
           leaf output {
             type string;
           }
         }
         case multichassis-tag {
           anyxml multi-routing-engine-results;
         }
       }
     }
   }
   rpc get-pfe-tcam-usage-app-fw-inet6-ftf {
     description "Inet6 family ingress firewall on a forwarding-table";
     junos:command "show pfe tcam usage app fw-inet6-ftf";
     output {
       choice output_c {
         case output-tag {
           leaf output {
             type string;
           }
         }
         case multichassis-tag {
           anyxml multi-routing-engine-results;
         }
       }
     }
   }
   rpc get-pfe-tcam-usage-app-fw-inet6-in {
     description "Inet6 family ingress firewall";
     junos:command "show pfe tcam usage app fw-inet6-in";
     output {
       choice output_c {
         case output-tag {
           leaf output {
             type string;
           }
         }
         case multichassis-tag {
           anyxml multi-routing-engine-results;
         }
       }
     }
   }
   rpc get-pfe-tcam-usage-app-fw-inet6-rpf {
     description "Inet6 family ingress firewall on a rpf fail check";
     junos:command "show pfe tcam usage app fw-inet6-rpf";
     output {
       choice output_c {
         case output-tag {
           leaf output {
             type string;
           }
         }
         case multichassis-tag {
           anyxml multi-routing-engine-results;
         }
       }
     }
   }
   rpc get-pfe-tcam-usage-app-fw-l2-in {
     description "Bridge family ingress firewall on layer2 interface";
     junos:command "show pfe tcam usage app fw-l2-in";
     output {
       choice output_c {
         case output-tag {
           leaf output {
             type string;
           }
         }
         case multichassis-tag {
           anyxml multi-routing-engine-results;
         }
       }
     }
   }
   rpc get-pfe-tcam-usage-app-fw-mpls-in {
     description "Mpls family ingress firewall";
     junos:command "show pfe tcam usage app fw-mpls-in";
     output {
       choice output_c {
         case output-tag {
           leaf output {
             type string;
           }
         }
         case multichassis-tag {
           anyxml multi-routing-engine-results;
         }
       }
     }
   }
   rpc get-pfe-tcam-usage-app-fw-vpls-in {
     description "VPLS family ingress firewall on vpls interface";
     junos:command "show pfe tcam usage app fw-vpls-in";
     output {
       choice output_c {
         case output-tag {
           leaf output {
             type string;
           }
         }
         case multichassis-tag {
           anyxml multi-routing-engine-results;
         }
       }
     }
   }
   rpc get-pfe-tcam-usage-app-gr-ifl-statistics-egr {
     description "GR Ifl level statistics (egress)";
     junos:command "show pfe tcam usage app gr-ifl-stats-egr";
     output {
       choice output_c {
         case output-tag {
           leaf output {
             type string;
           }
         }
         case multichassis-tag {
           anyxml multi-routing-engine-results;
         }
       }
     }
   }
   rpc get-pfe-tcam-usage-app-gr-ifl-statistics-ing {
     description "GR Ifl level statistics (ingress)";
     junos:command "show pfe tcam usage app gr-ifl-stats-ing";
     output {
       choice output_c {
         case output-tag {
           leaf output {
             type string;
           }
         }
         case multichassis-tag {
           anyxml multi-routing-engine-results;
         }
       }
     }
   }
   rpc get-pfe-tcam-usage-app-gr-ifl-statistics-preing {
     description "GR Ifl level statistics (pre-ingress)";
     junos:command "show pfe tcam usage app gr-ifl-stats-preing";
     output {
       choice output_c {
         case output-tag {
           leaf output {
             type string;
           }
         }
         case multichassis-tag {
           anyxml multi-routing-engine-results;
         }
       }
     }
   }
   rpc get-pfe-tcam-usage-app-ifl-statistics-in {
     description "Ifl level statistics (ingress)";
     junos:command "show pfe tcam usage app ifl-statistics-in";
     output {
       choice output_c {
         case output-tag {
           leaf output {
             type string;
           }
         }
         case multichassis-tag {
           anyxml multi-routing-engine-results;
         }
       }
     }
   }
   rpc get-pfe-tcam-usage-app-irb-fixed-cos {
     description "IRB fixed classifier filter entries";
     junos:command "show pfe tcam usage app irb-fixed-cos";
     output {
       choice output_c {
         case output-tag {
           leaf output {
             type string;
           }
         }
         case multichassis-tag {
           anyxml multi-routing-engine-results;
         }
       }
     }
   }
   rpc get-pfe-tcam-usage-app-mrouter-port-in {
     description "Multicast router port for snooping";
     junos:command "show pfe tcam usage app mrouter-port-in";
     output {
       choice output_c {
         case output-tag {
           leaf output {
             type string;
           }
         }
         case multichassis-tag {
           anyxml multi-routing-engine-results;
         }
       }
     }
   }
   rpc get-pfe-tcam-usage-app-lo0-inet-fil {
     description "Lo0 Inet Filter";
     junos:command "show pfe tcam usage app lo0-inet-fil";
     output {
       choice output_c {
         case output-tag {
           leaf output {
             type string;
           }
         }
         case multichassis-tag {
           anyxml multi-routing-engine-results;
         }
       }
     }
   }
   rpc get-pfe-tcam-usage-app-lo0-inet6-fil {
     description "Lo0 Inet6 Filter";
     junos:command "show pfe tcam usage app lo0-inet6-fil";
     output {
       choice output_c {
         case output-tag {
           leaf output {
             type string;
           }
         }
         case multichassis-tag {
           anyxml multi-routing-engine-results;
         }
       }
     }
   }
   rpc get-pfe-tcam-usage-app-mac-drop-cnt {
     description "Statistics for drops by mac-validate/src-mac filters";
     junos:command "show pfe tcam usage app mac-drop-cnt";
     output {
       choice output_c {
         case output-tag {
           leaf output {
             type string;
           }
         }
         case multichassis-tag {
           anyxml multi-routing-engine-results;
         }
       }
     }
   }
   rpc get-pfe-tcam-usage-app-no-local-switching {
     description "Bridge no-local-switching";
     junos:command "show pfe tcam usage app no-local-switching";
     output {
       choice output_c {
         case output-tag {
           leaf output {
             type string;
           }
         }
         case multichassis-tag {
           anyxml multi-routing-engine-results;
         }
       }
     }
   }
   rpc get-pfe-tcam-usage-app-cos-fc {
     description "Ifl level fixed classifier";
     junos:command "show pfe tcam usage app cos-fc";
     output {
       choice output_c {
         case output-tag {
           leaf output {
             type string;
           }
         }
         case multichassis-tag {
           anyxml multi-routing-engine-results;
         }
       }
     }
   }
   rpc get-pfe-tcam-usage-app-fw-fbf {
     description "Firewall filter based forwarding";
     junos:command "show pfe tcam usage app fw-fbf";
     output {
       choice output_c {
         case output-tag {
           leaf output {
             type string;
           }
         }
         case multichassis-tag {
           anyxml multi-routing-engine-results;
         }
       }
     }
   }
   rpc get-pfe-tcam-usage-app-fw-fbf-inet6 {
     description "Firewall filter based forwarding for Inet6";
     junos:command "show pfe tcam usage app fw-fbf-inet6";
     output {
       choice output_c {
         case output-tag {
           leaf output {
             type string;
           }
         }
         case multichassis-tag {
           anyxml multi-routing-engine-results;
         }
       }
     }
   }
   rpc get-pfe-tcam-usage-app-fw-semantics {
     description "Firewall sharing semantics for cli configured firewall";
     junos:command "show pfe tcam usage app fw-semantics";
     output {
       choice output_c {
         case output-tag {
           leaf output {
             type string;
           }
         }
         case multichassis-tag {
           anyxml multi-routing-engine-results;
         }
       }
     }
   }
   rpc get-pfe-tcam-usage-app-ifd-src-mac-fil {
     description "Ifd level source mac filter";
     junos:command "show pfe tcam usage app ifd-src-mac-fil";
     output {
       choice output_c {
         case output-tag {
           leaf output {
             type string;
           }
         }
         case multichassis-tag {
           anyxml multi-routing-engine-results;
         }
       }
     }
   }
   rpc get-pfe-tcam-usage-app-ing-out-iff {
     description "Ingress app on behalf of egress family filter for log/syslog";
     junos:command "show pfe tcam usage app ing-out-iff";
     output {
       choice output_c {
         case output-tag {
           leaf output {
             type string;
           }
         }
         case multichassis-tag {
           anyxml multi-routing-engine-results;
         }
       }
     }
   }
   rpc get-pfe-tcam-usage-app-ip-mac-val {
     description "Ip mac validate";
     junos:command "show pfe tcam usage app ip-mac-val";
     output {
       choice output_c {
         case output-tag {
           leaf output {
             type string;
           }
         }
         case multichassis-tag {
           anyxml multi-routing-engine-results;
         }
       }
     }
   }
   rpc get-pfe-tcam-usage-app-ip-mac-val-bcast {
     description "Ip mac validate for broadcast";
     junos:command "show pfe tcam usage app ip-mac-val-bcast";
     output {
       choice output_c {
         case output-tag {
           leaf output {
             type string;
           }
         }
         case multichassis-tag {
           anyxml multi-routing-engine-results;
         }
       }
     }
   }
   rpc get-pfe-tcam-usage-app-rfc2544-layer2-in {
     description "Rfc2544 for layer2 service (ingress)";
     junos:command "show pfe tcam usage app rfc2544-layer2-in";
     output {
       choice output_c {
         case output-tag {
           leaf output {
             type string;
           }
         }
         case multichassis-tag {
           anyxml multi-routing-engine-results;
         }
       }
     }
   }
   rpc get-pfe-tcam-errors {
     description "Show packet forwarding engine tcam errors";
     junos:command "show pfe tcam errors";
     output {
       choice output_c {
         case output-tag {
           leaf output {
             type string;
           }
         }
         case multichassis-tag {
           anyxml multi-routing-engine-results;
         }
       }
     }
   }
   rpc get-pfe-tcam-errors-all-tcam-stages {
     description "Show packet forwarding engine tcam errors at all tcam stages";
     junos:command "show pfe tcam errors all-tcam-stages";
     output {
       choice output_c {
         case output-tag {
           leaf output {
             type string;
           }
         }
         case multichassis-tag {
           anyxml multi-routing-engine-results;
         }
       }
     }
   }
   rpc get-pfe-tcam-errors-all-tcam-stages-detail {
     description "Show packet forwarding engine tcam errors at all tcam stages in detail";
     junos:command "show pfe tcam errors all-tcam-stages detail";
     output {
       choice output_c {
         case output-tag {
           leaf output {
             type string;
           }
         }
         case multichassis-tag {
           anyxml multi-routing-engine-results;
         }
       }
     }
   }
   rpc get-pfe-tcam-errors-egress-tcam-stage {
     description "Show tcam errors for egress tcam-stage";
     junos:command "show pfe tcam errors tcam-stage egress";
     output {
       choice output_c {
         case output-tag {
           leaf output {
             type string;
           }
         }
         case multichassis-tag {
           anyxml multi-routing-engine-results;
         }
       }
     }
   }
   rpc get-pfe-tcam-errors-egress-tcam-stage-detail {
     description "Show tcam errors for egress tcam-stage in detail";
     junos:command "show pfe tcam errors tcam-stage egress detail";
     output {
       choice output_c {
         case output-tag {
           leaf output {
             type string;
           }
         }
         case multichassis-tag {
           anyxml multi-routing-engine-results;
         }
       }
     }
   }
   rpc get-pfe-tcam-errors-egress-app {
     description "Show tcam errors for a tcam app";
     junos:command "show pfe tcam errors tcam-stage egress app";
     output {
       choice output_c {
         case output-tag {
           leaf output {
             type string;
           }
         }
         case multichassis-tag {
           anyxml multi-routing-engine-results;
         }
       }
     }
   }
   rpc get-pfe-tcam-errors-egress-app-bd-tpid-swap {
     description "Bridge domain vlan-map with swap tpid operation";
     junos:command "show pfe tcam errors tcam-stage egress app bd-tpid-swap";
     output {
       choice output_c {
         case output-tag {
           leaf output {
             type string;
           }
         }
         case multichassis-tag {
           anyxml multi-routing-engine-results;
         }
       }
     }
   }
   rpc get-pfe-tcam-errors-egress-app-fw-family-out {
     description "Family level egress firewall";
     junos:command "show pfe tcam errors tcam-stage egress app fw-family-out";
     output {
       choice output_c {
         case output-tag {
           leaf output {
             type string;
           }
         }
         case multichassis-tag {
           anyxml multi-routing-engine-results;
         }
       }
     }
   }
   rpc get-pfe-tcam-errors-egress-app-fw-inet6-family-out {
     description "Inet6 Family level egress firewall";
     junos:command "show pfe tcam errors tcam-stage egress app fw-inet6-family-out";
     output {
       choice output_c {
         case output-tag {
           leaf output {
             type string;
           }
         }
         case multichassis-tag {
           anyxml multi-routing-engine-results;
         }
       }
     }
   }
   rpc get-pfe-tcam-errors-egress-app-fw-ifl-out {
     description "Ifl level egress firewall";
     junos:command "show pfe tcam errors tcam-stage egress app fw-ifl-out";
     output {
       choice output_c {
         case output-tag {
           leaf output {
             type string;
           }
         }
         case multichassis-tag {
           anyxml multi-routing-engine-results;
         }
       }
     }
   }
   rpc get-pfe-tcam-errors-egress-app-ifl-statistics-out {
     description "Ifl level statistics (egress)";
     junos:command "show pfe tcam errors tcam-stage egress app ifl-statistics-out";
     output {
       choice output_c {
         case output-tag {
           leaf output {
             type string;
           }
         }
         case multichassis-tag {
           anyxml multi-routing-engine-results;
         }
       }
     }
   }
   rpc get-pfe-tcam-errors-egress-app-irb-cos-rw {
     description "IRB CoS rewrite";
     junos:command "show pfe tcam errors tcam-stage egress app irb-cos-rw";
     output {
       choice output_c {
         case output-tag {
           leaf output {
             type string;
           }
         }
         case multichassis-tag {
           anyxml multi-routing-engine-results;
         }
       }
     }
   }
   rpc get-pfe-tcam-errors-egress-app-lfm-802.3ah-out {
     description "Lfm-802.3ah (egress)";
     junos:command "show pfe tcam errors tcam-stage egress app lfm-802.3ah-out";
     output {
       choice output_c {
         case output-tag {
           leaf output {
             type string;
           }
         }
         case multichassis-tag {
           anyxml multi-routing-engine-results;
         }
       }
     }
   }
   rpc get-pfe-tcam-errors-ingress-tcam-stage {
     description "Show tcam errors for ingress tcam-stage";
     junos:command "show pfe tcam errors tcam-stage ingress";
     output {
       choice output_c {
         case output-tag {
           leaf output {
             type string;
           }
         }
         case multichassis-tag {
           anyxml multi-routing-engine-results;
         }
       }
     }
   }
   rpc get-pfe-tcam-errors-ingress-tcam-stage-app {
     description "Show tcam errors for a tcam app";
     junos:command "show pfe tcam errors tcam-stage ingress app";
     output {
       choice output_c {
         case output-tag {
           leaf output {
             type string;
           }
         }
         case multichassis-tag {
           anyxml multi-routing-engine-results;
         }
       }
     }
   }
   rpc get-pfe-tcam-errors-ingress-tcam-stage-cfm-bd-filter {
     description "Cfm implicit bridge-domain filters";
     junos:command "show pfe tcam errors tcam-stage ingress app cfm-bd-filter";
     output {
       choice output_c {
         case output-tag {
           leaf output {
             type string;
           }
         }
         case multichassis-tag {
           anyxml multi-routing-engine-results;
         }
       }
     }
   }
   rpc get-pfe-tcam-errors-ingress-tcam-stage-cfm-filter {
     description "Cfm implicit filters";
     junos:command "show pfe tcam errors tcam-stage ingress app cfm-filter";
     output {
       choice output_c {
         case output-tag {
           leaf output {
             type string;
           }
         }
         case multichassis-tag {
           anyxml multi-routing-engine-results;
         }
       }
     }
   }
   rpc get-pfe-tcam-errors-ingress-tcam-stage-cfm-vpls-filter {
     description "Cfm implicit vpls filters";
     junos:command "show pfe tcam errors tcam-stage ingress app cfm-vpls-filter";
     output {
       choice output_c {
         case output-tag {
           leaf output {
             type string;
           }
         }
         case multichassis-tag {
           anyxml multi-routing-engine-results;
         }
       }
     }
   }
   rpc get-pfe-tcam-errors-ingress-tcam-stage-cfm-vpls-ifl-filter {
     description "Cfm implicit vpls ifl filters";
     junos:command "show pfe tcam errors tcam-stage ingress app cfm-vpls-ifl-filter";
     output {
       choice output_c {
         case output-tag {
           leaf output {
             type string;
           }
         }
         case multichassis-tag {
           anyxml multi-routing-engine-results;
         }
       }
     }
   }
   rpc get-pfe-tcam-errors-ingress-tcam-stage-fw-ccc-in {
     description "Ccc family ingress firewall";
     junos:command "show pfe tcam errors tcam-stage ingress app fw-ccc-in";
     output {
       choice output_c {
         case output-tag {
           leaf output {
             type string;
           }
         }
         case multichassis-tag {
           anyxml multi-routing-engine-results;
         }
       }
     }
   }
   rpc get-pfe-tcam-errors-ingress-tcam-stage-fw-ifl-in {
     description "Ifl level ingress firewall";
     junos:command "show pfe tcam errors tcam-stage ingress app fw-ifl-in";
     output {
       choice output_c {
         case output-tag {
           leaf output {
             type string;
           }
         }
         case multichassis-tag {
           anyxml multi-routing-engine-results;
         }
       }
     }
   }
   rpc get-pfe-tcam-errors-ingress-tcam-stage-fw-inet-ftf {
     description "Inet family ingress firewall on a forwarding-table";
     junos:command "show pfe tcam errors tcam-stage ingress app fw-inet-ftf";
     output {
       choice output_c {
         case output-tag {
           leaf output {
             type string;
           }
         }
         case multichassis-tag {
           anyxml multi-routing-engine-results;
         }
       }
     }
   }
   rpc get-pfe-tcam-errors-ingress-tcam-stage-fw-inet-in {
     description "Inet family ingress firewall";
     junos:command "show pfe tcam errors tcam-stage ingress app fw-inet-in";
     output {
       choice output_c {
         case output-tag {
           leaf output {
             type string;
           }
         }
         case multichassis-tag {
           anyxml multi-routing-engine-results;
         }
       }
     }
   }
   rpc get-pfe-tcam-errors-ingress-tcam-stage-fw-inet-rpf {
     description "Inet family ingress firewall on rpf fail check";
     junos:command "show pfe tcam errors tcam-stage ingress app fw-inet-rpf";
     output {
       choice output_c {
         case output-tag {
           leaf output {
             type string;
           }
         }
         case multichassis-tag {
           anyxml multi-routing-engine-results;
         }
       }
     }
   }
   rpc get-pfe-tcam-errors-ingress-tcam-stage-fw-inet6-ftf {
     description "Inet6 family ingress firewall on a forwarding-table";
     junos:command "show pfe tcam errors tcam-stage ingress app fw-inet6-ftf";
     output {
       choice output_c {
         case output-tag {
           leaf output {
             type string;
           }
         }
         case multichassis-tag {
           anyxml multi-routing-engine-results;
         }
       }
     }
   }
   rpc get-pfe-tcam-errors-ingress-tcam-stage-fw-inet6-in {
     description "Inet6 family ingress firewall";
     junos:command "show pfe tcam errors tcam-stage ingress app fw-inet6-in";
     output {
       choice output_c {
         case output-tag {
           leaf output {
             type string;
           }
         }
         case multichassis-tag {
           anyxml multi-routing-engine-results;
         }
       }
     }
   }
   rpc get-pfe-tcam-errors-ingress-tcam-stage-fw-inet6-rpf {
     description "Inet6 family ingress firewall on a rpf fail check";
     junos:command "show pfe tcam errors tcam-stage ingress app fw-inet6-rpf";
     output {
       choice output_c {
         case output-tag {
           leaf output {
             type string;
           }
         }
         case multichassis-tag {
           anyxml multi-routing-engine-results;
         }
       }
     }
   }
   rpc get-pfe-tcam-errors-ingress-tcam-stage-fw-l2-in {
     description "Bridge family ingress firewall on layer2 interface";
     junos:command "show pfe tcam errors tcam-stage ingress app fw-l2-in";
     output {
       choice output_c {
         case output-tag {
           leaf output {
             type string;
           }
         }
         case multichassis-tag {
           anyxml multi-routing-engine-results;
         }
       }
     }
   }
   rpc get-pfe-tcam-errors-ingress-tcam-stage-fw-mpls-in {
     description "Mpls family ingress firewall";
     junos:command "show pfe tcam errors tcam-stage ingress app fw-mpls-in";
     output {
       choice output_c {
         case output-tag {
           leaf output {
             type string;
           }
         }
         case multichassis-tag {
           anyxml multi-routing-engine-results;
         }
       }
     }
   }
   rpc get-pfe-tcam-errors-ingress-tcam-stage-fw-vpls-in {
     description "VPLS family ingress firewall on vpls interface";
     junos:command "show pfe tcam errors tcam-stage ingress app fw-vpls-in";
     output {
       choice output_c {
         case output-tag {
           leaf output {
             type string;
           }
         }
         case multichassis-tag {
           anyxml multi-routing-engine-results;
         }
       }
     }
   }
   rpc get-pfe-tcam-errors-ingress-tcam-stage-gr-ifl-statistics-egr {
     description "GR Ifl level statistics (egress)";
     junos:command "show pfe tcam errors tcam-stage ingress app gr-ifl-stats-egr";
     output {
       choice output_c {
         case output-tag {
           leaf output {
             type string;
           }
         }
         case multichassis-tag {
           anyxml multi-routing-engine-results;
         }
       }
     }
   }
   rpc get-pfe-tcam-errors-ingress-tcam-stage-gr-ifl-statistics-ing {
     description "GR Ifl level statistics (ingress)";
     junos:command "show pfe tcam errors tcam-stage ingress app gr-ifl-stats-ing";
     output {
       choice output_c {
         case output-tag {
           leaf output {
             type string;
           }
         }
         case multichassis-tag {
           anyxml multi-routing-engine-results;
         }
       }
     }
   }
   rpc get-pfe-tcam-errors-ingress-tcam-stage-gr-ifl-statistics-preing {
     description "GR Ifl level statistics (pre-ingress)";
     junos:command "show pfe tcam errors tcam-stage ingress app gr-ifl-stats-preing";
     output {
       choice output_c {
         case output-tag {
           leaf output {
             type string;
           }
         }
         case multichassis-tag {
           anyxml multi-routing-engine-results;
         }
       }
     }
   }
   rpc get-pfe-tcam-errors-ingress-tcam-stage-ifl-statistics-in {
     description "Ifl level statistics (ingress)";
     junos:command "show pfe tcam errors tcam-stage ingress app ifl-statistics-in";
     output {
       choice output_c {
         case output-tag {
           leaf output {
             type string;
           }
         }
         case multichassis-tag {
           anyxml multi-routing-engine-results;
         }
       }
     }
   }
   rpc get-pfe-tcam-errors-ingress-tcam-stage-irb-fixed-cos {
     description "IRB fixed classifier filter entries";
     junos:command "show pfe tcam errors tcam-stage ingress app irb-fixed-cos";
     output {
       choice output_c {
         case output-tag {
           leaf output {
             type string;
           }
         }
         case multichassis-tag {
           anyxml multi-routing-engine-results;
         }
       }
     }
   }
   rpc get-pfe-tcam-errors-ingress-tcam-stage-mrouter-port-in {
     description "Multicast router port for snooping";
     junos:command "show pfe tcam errors tcam-stage ingress app mrouter-port-in";
     output {
       choice output_c {
         case output-tag {
           leaf output {
             type string;
           }
         }
         case multichassis-tag {
           anyxml multi-routing-engine-results;
         }
       }
     }
   }
   rpc get-pfe-tcam-errors-ingress-tcam-stage-lo0-inet-fil {
     description "Lo0 Inet Filter";
     junos:command "show pfe tcam errors tcam-stage ingress app lo0-inet-fil";
     output {
       choice output_c {
         case output-tag {
           leaf output {
             type string;
           }
         }
         case multichassis-tag {
           anyxml multi-routing-engine-results;
         }
       }
     }
   }
   rpc get-pfe-tcam-errors-ingress-tcam-stage-lo0-inet6-fil {
     description "Lo0 Inet6 Filter";
     junos:command "show pfe tcam errors tcam-stage ingress app lo0-inet6-fil";
     output {
       choice output_c {
         case output-tag {
           leaf output {
             type string;
           }
         }
         case multichassis-tag {
           anyxml multi-routing-engine-results;
         }
       }
     }
   }
   rpc get-pfe-tcam-errors-ingress-tcam-stage-mac-drop-cnt {
     description "Statistics for drops by mac-validate/src-mac filters";
     junos:command "show pfe tcam errors tcam-stage ingress app mac-drop-cnt";
     output {
       choice output_c {
         case output-tag {
           leaf output {
             type string;
           }
         }
         case multichassis-tag {
           anyxml multi-routing-engine-results;
         }
       }
     }
   }
   rpc get-pfe-tcam-errors-ingress-tcam-stage-no-local-switching {
     description "Bridge no-local-switching";
     junos:command "show pfe tcam errors tcam-stage ingress app no-local-switching";
     output {
       choice output_c {
         case output-tag {
           leaf output {
             type string;
           }
         }
         case multichassis-tag {
           anyxml multi-routing-engine-results;
         }
       }
     }
   }
   rpc get-pfe-tcam-errors-pre-ingress-tcam-stage {
     description "Show tcam errors for pre-ingress tcam-stage";
     junos:command "show pfe tcam errors tcam-stage pre-ingress";
     output {
       choice output_c {
         case output-tag {
           leaf output {
             type string;
           }
         }
         case multichassis-tag {
           anyxml multi-routing-engine-results;
         }
       }
     }
   }
   rpc get-pfe-tcam-errors-pre-ingress-tcam-stage-detail {
     description "Show tcam errors for pre-ingress tcam-stage in detail";
     junos:command "show pfe tcam errors tcam-stage pre-ingress detail";
     output {
       choice output_c {
         case output-tag {
           leaf output {
             type string;
           }
         }
         case multichassis-tag {
           anyxml multi-routing-engine-results;
         }
       }
     }
   }
   rpc get-pfe-tcam-errors-pre-ingress-app {
     description "Show tcam errors for a tcam app";
     junos:command "show pfe tcam errors tcam-stage pre-ingress app";
     output {
       choice output_c {
         case output-tag {
           leaf output {
             type string;
           }
         }
         case multichassis-tag {
           anyxml multi-routing-engine-results;
         }
       }
     }
   }
   rpc get-pfe-tcam-errors-pre-ingress-app-cos-fc {
     description "Ifl level fixed classifier";
     junos:command "show pfe tcam errors tcam-stage pre-ingress app cos-fc";
     output {
       choice output_c {
         case output-tag {
           leaf output {
             type string;
           }
         }
         case multichassis-tag {
           anyxml multi-routing-engine-results;
         }
       }
     }
   }
   rpc get-pfe-tcam-errors-pre-ingress-app-fw-fbf {
     description "Firewall filter based forwarding";
     junos:command "show pfe tcam errors tcam-stage pre-ingress app fw-fbf";
     output {
       choice output_c {
         case output-tag {
           leaf output {
             type string;
           }
         }
         case multichassis-tag {
           anyxml multi-routing-engine-results;
         }
       }
     }
   }
   rpc get-pfe-tcam-errors-pre-ingress-app-fw-fbf-inet6 {
     description "Firewall filter based forwarding for Inet6";
     junos:command "show pfe tcam errors tcam-stage pre-ingress app fw-fbf-inet6";
     output {
       choice output_c {
         case output-tag {
           leaf output {
             type string;
           }
         }
         case multichassis-tag {
           anyxml multi-routing-engine-results;
         }
       }
     }
   }
   rpc get-pfe-tcam-errors-pre-ingress-app-fw-semantics {
     description "Firewall sharing semantics for cli configured firewall";
     junos:command "show pfe tcam errors tcam-stage pre-ingress app fw-semantics";
     output {
       choice output_c {
         case output-tag {
           leaf output {
             type string;
           }
         }
         case multichassis-tag {
           anyxml multi-routing-engine-results;
         }
       }
     }
   }
   rpc get-pfe-tcam-errors-pre-ingress-app-ifd-src-mac-fil {
     description "Ifd level source mac filter";
     junos:command "show pfe tcam errors tcam-stage pre-ingress app ifd-src-mac-fil";
     output {
       choice output_c {
         case output-tag {
           leaf output {
             type string;
           }
         }
         case multichassis-tag {
           anyxml multi-routing-engine-results;
         }
       }
     }
   }
   rpc get-pfe-tcam-errors-pre-ingress-app-ing-out-iff {
     description "Ingress app on behalf of egress family filter for log/syslog";
     junos:command "show pfe tcam errors tcam-stage pre-ingress app ing-out-iff";
     output {
       choice output_c {
         case output-tag {
           leaf output {
             type string;
           }
         }
         case multichassis-tag {
           anyxml multi-routing-engine-results;
         }
       }
     }
   }
   rpc get-pfe-tcam-errors-pre-ingress-app-ip-mac-val {
     description "Ip mac validate";
     junos:command "show pfe tcam errors tcam-stage pre-ingress app ip-mac-val";
     output {
       choice output_c {
         case output-tag {
           leaf output {
             type string;
           }
         }
         case multichassis-tag {
           anyxml multi-routing-engine-results;
         }
       }
     }
   }
   rpc get-pfe-tcam-errors-pre-ingress-app-ip-mac-val-bcast {
     description "Ip mac validate for broadcast";
     junos:command "show pfe tcam errors tcam-stage pre-ingress app ip-mac-val-bcast";
     output {
       choice output_c {
         case output-tag {
           leaf output {
             type string;
           }
         }
         case multichassis-tag {
           anyxml multi-routing-engine-results;
         }
       }
     }
   }
   rpc get-pfe-tcam-errors-pre-ingress-app-rfc2544-layer2-in {
     description "Rfc2544 for layer2 service (ingress)";
     junos:command "show pfe tcam errors tcam-stage pre-ingress app rfc2544-layer2-in";
     output {
       choice output_c {
         case output-tag {
           leaf output {
             type string;
           }
         }
         case multichassis-tag {
           anyxml multi-routing-engine-results;
         }
       }
     }
   }
   rpc get-pfe-tcam-errors-app {
     description "Show tcam errors for a tcam app";
     junos:command "show pfe tcam errors app";
     output {
       choice output_c {
         case output-tag {
           leaf output {
             type string;
           }
         }
         case multichassis-tag {
           anyxml multi-routing-engine-results;
         }
       }
     }
   }
   rpc get-pfe-tcam-errors-app-bd-tpid-swap {
     description "Bridge domain vlan-map with swap tpid operation";
     junos:command "show pfe tcam errors app bd-tpid-swap";
     output {
       choice output_c {
         case output-tag {
           leaf output {
             type string;
           }
         }
         case multichassis-tag {
           anyxml multi-routing-engine-results;
         }
       }
     }
   }
   rpc get-pfe-tcam-errors-app-fw-family-out {
     description "Family level egress firewall";
     junos:command "show pfe tcam errors app fw-family-out";
     output {
       choice output_c {
         case output-tag {
           leaf output {
             type string;
           }
         }
         case multichassis-tag {
           anyxml multi-routing-engine-results;
         }
       }
     }
   }
   rpc get-pfe-tcam-errors-app-fw-inet6-family-out {
     description "Inet6 Family level egress firewall";
     junos:command "show pfe tcam errors app fw-inet6-family-out";
     output {
       choice output_c {
         case output-tag {
           leaf output {
             type string;
           }
         }
         case multichassis-tag {
           anyxml multi-routing-engine-results;
         }
       }
     }
   }
   rpc get-pfe-tcam-errors-app-fw-ifl-out {
     description "Ifl level egress firewall";
     junos:command "show pfe tcam errors app fw-ifl-out";
     output {
       choice output_c {
         case output-tag {
           leaf output {
             type string;
           }
         }
         case multichassis-tag {
           anyxml multi-routing-engine-results;
         }
       }
     }
   }
   rpc get-pfe-tcam-errors-app-ifl-statistics-out {
     description "Ifl level statistics (egress)";
     junos:command "show pfe tcam errors app ifl-statistics-out";
     output {
       choice output_c {
         case output-tag {
           leaf output {
             type string;
           }
         }
         case multichassis-tag {
           anyxml multi-routing-engine-results;
         }
       }
     }
   }
   rpc get-pfe-tcam-errors-app-irb-cos-rw {
     description "IRB CoS rewrite";
     junos:command "show pfe tcam errors app irb-cos-rw";
     output {
       choice output_c {
         case output-tag {
           leaf output {
             type string;
           }
         }
         case multichassis-tag {
           anyxml multi-routing-engine-results;
         }
       }
     }
   }
   rpc get-pfe-tcam-errors-app-lfm-802.3ah-out {
     description "Lfm-802.3ah (egress)";
     junos:command "show pfe tcam errors app lfm-802.3ah-out";
     output {
       choice output_c {
         case output-tag {
           leaf output {
             type string;
           }
         }
         case multichassis-tag {
           anyxml multi-routing-engine-results;
         }
       }
     }
   }
   rpc get-pfe-tcam-errors-app-cfm-bd-filter {
     description "Cfm implicit bridge-domain filters";
     junos:command "show pfe tcam errors app cfm-bd-filter";
     output {
       choice output_c {
         case output-tag {
           leaf output {
             type string;
           }
         }
         case multichassis-tag {
           anyxml multi-routing-engine-results;
         }
       }
     }
   }
   rpc get-pfe-tcam-errors-app-cfm-filter {
     description "Cfm implicit filters";
     junos:command "show pfe tcam errors app cfm-filter";
     output {
       choice output_c {
         case output-tag {
           leaf output {
             type string;
           }
         }
         case multichassis-tag {
           anyxml multi-routing-engine-results;
         }
       }
     }
   }
   rpc get-pfe-tcam-errors-app-cfm-vpls-filter {
     description "Cfm implicit vpls filters";
     junos:command "show pfe tcam errors app cfm-vpls-filter";
     output {
       choice output_c {
         case output-tag {
           leaf output {
             type string;
           }
         }
         case multichassis-tag {
           anyxml multi-routing-engine-results;
         }
       }
     }
   }
   rpc get-pfe-tcam-errors-app-cfm-vpls-ifl-filter {
     description "Cfm implicit vpls ifl filters";
     junos:command "show pfe tcam errors app cfm-vpls-ifl-filter";
     output {
       choice output_c {
         case output-tag {
           leaf output {
             type string;
           }
         }
         case multichassis-tag {
           anyxml multi-routing-engine-results;
         }
       }
     }
   }
   rpc get-pfe-tcam-errors-app-fw-ccc-in {
     description "Ccc family ingress firewall";
     junos:command "show pfe tcam errors app fw-ccc-in";
     output {
       choice output_c {
         case output-tag {
           leaf output {
             type string;
           }
         }
         case multichassis-tag {
           anyxml multi-routing-engine-results;
         }
       }
     }
   }
   rpc get-pfe-tcam-errors-app-fw-ifl-in {
     description "Ifl level ingress firewall";
     junos:command "show pfe tcam errors app fw-ifl-in";
     output {
       choice output_c {
         case output-tag {
           leaf output {
             type string;
           }
         }
         case multichassis-tag {
           anyxml multi-routing-engine-results;
         }
       }
     }
   }
   rpc get-pfe-tcam-errors-app-fw-inet-ftf {
     description "Inet family ingress firewall on a forwarding-table";
     junos:command "show pfe tcam errors app fw-inet-ftf";
     output {
       choice output_c {
         case output-tag {
           leaf output {
             type string;
           }
         }
         case multichassis-tag {
           anyxml multi-routing-engine-results;
         }
       }
     }
   }
   rpc get-pfe-tcam-errors-app-fw-inet-in {
     description "Inet family ingress firewall";
     junos:command "show pfe tcam errors app fw-inet-in";
     output {
       choice output_c {
         case output-tag {
           leaf output {
             type string;
           }
         }
         case multichassis-tag {
           anyxml multi-routing-engine-results;
         }
       }
     }
   }
   rpc get-pfe-tcam-errors-app-fw-inet-rpf {
     description "Inet family ingress firewall on rpf fail check";
     junos:command "show pfe tcam errors app fw-inet-rpf";
     output {
       choice output_c {
         case output-tag {
           leaf output {
             type string;
           }
         }
         case multichassis-tag {
           anyxml multi-routing-engine-results;
         }
       }
     }
   }
   rpc get-pfe-tcam-errors-app-fw-inet6-ftf {
     description "Inet6 family ingress firewall on a forwarding-table";
     junos:command "show pfe tcam errors app fw-inet6-ftf";
     output {
       choice output_c {
         case output-tag {
           leaf output {
             type string;
           }
         }
         case multichassis-tag {
           anyxml multi-routing-engine-results;
         }
       }
     }
   }
   rpc get-pfe-tcam-errors-app-fw-inet6-in {
     description "Inet6 family ingress firewall";
     junos:command "show pfe tcam errors app fw-inet6-in";
     output {
       choice output_c {
         case output-tag {
           leaf output {
             type string;
           }
         }
         case multichassis-tag {
           anyxml multi-routing-engine-results;
         }
       }
     }
   }
   rpc get-pfe-tcam-errors-app-fw-inet6-rpf {
     description "Inet6 family ingress firewall on a rpf fail check";
     junos:command "show pfe tcam errors app fw-inet6-rpf";
     output {
       choice output_c {
         case output-tag {
           leaf output {
             type string;
           }
         }
         case multichassis-tag {
           anyxml multi-routing-engine-results;
         }
       }
     }
   }
   rpc get-pfe-tcam-errors-app-fw-l2-in {
     description "Bridge family ingress firewall on layer2 interface";
     junos:command "show pfe tcam errors app fw-l2-in";
     output {
       choice output_c {
         case output-tag {
           leaf output {
             type string;
           }
         }
         case multichassis-tag {
           anyxml multi-routing-engine-results;
         }
       }
     }
   }
   rpc get-pfe-tcam-errors-app-fw-mpls-in {
     description "Mpls family ingress firewall";
     junos:command "show pfe tcam errors app fw-mpls-in";
     output {
       choice output_c {
         case output-tag {
           leaf output {
             type string;
           }
         }
         case multichassis-tag {
           anyxml multi-routing-engine-results;
         }
       }
     }
   }
   rpc get-pfe-tcam-errors-app-fw-vpls-in {
     description "VPLS family ingress firewall on vpls interface";
     junos:command "show pfe tcam errors app fw-vpls-in";
     output {
       choice output_c {
         case output-tag {
           leaf output {
             type string;
           }
         }
         case multichassis-tag {
           anyxml multi-routing-engine-results;
         }
       }
     }
   }
   rpc get-pfe-tcam-errors-app-gr-ifl-statistics-egr {
     description "GR Ifl level statistics (egress)";
     junos:command "show pfe tcam errors app gr-ifl-stats-egr";
     output {
       choice output_c {
         case output-tag {
           leaf output {
             type string;
           }
         }
         case multichassis-tag {
           anyxml multi-routing-engine-results;
         }
       }
     }
   }
   rpc get-pfe-tcam-errors-app-gr-ifl-statistics-ing {
     description "GR Ifl level statistics (ingress)";
     junos:command "show pfe tcam errors app gr-ifl-stats-ing";
     output {
       choice output_c {
         case output-tag {
           leaf output {
             type string;
           }
         }
         case multichassis-tag {
           anyxml multi-routing-engine-results;
         }
       }
     }
   }
   rpc get-pfe-tcam-errors-app-gr-ifl-statistics-preing {
     description "GR Ifl level statistics (pre-ingress)";
     junos:command "show pfe tcam errors app gr-ifl-stats-preing";
     output {
       choice output_c {
         case output-tag {
           leaf output {
             type string;
           }
         }
         case multichassis-tag {
           anyxml multi-routing-engine-results;
         }
       }
     }
   }
   rpc get-pfe-tcam-errors-app-ifl-statistics-in {
     description "Ifl level statistics (ingress)";
     junos:command "show pfe tcam errors app ifl-statistics-in";
     output {
       choice output_c {
         case output-tag {
           leaf output {
             type string;
           }
         }
         case multichassis-tag {
           anyxml multi-routing-engine-results;
         }
       }
     }
   }
   rpc get-pfe-tcam-errors-app-irb-fixed-cos {
     description "IRB fixed classifier filter entries";
     junos:command "show pfe tcam errors app irb-fixed-cos";
     output {
       choice output_c {
         case output-tag {
           leaf output {
             type string;
           }
         }
         case multichassis-tag {
           anyxml multi-routing-engine-results;
         }
       }
     }
   }
   rpc get-pfe-tcam-errors-app-mrouter-port-in {
     description "Multicast router port for snooping";
     junos:command "show pfe tcam errors app mrouter-port-in";
     output {
       choice output_c {
         case output-tag {
           leaf output {
             type string;
           }
         }
         case multichassis-tag {
           anyxml multi-routing-engine-results;
         }
       }
     }
   }
   rpc get-pfe-tcam-errors-app-lo0-inet-fil {
     description "Lo0 Inet Filter";
     junos:command "show pfe tcam errors app lo0-inet-fil";
     output {
       choice output_c {
         case output-tag {
           leaf output {
             type string;
           }
         }
         case multichassis-tag {
           anyxml multi-routing-engine-results;
         }
       }
     }
   }
   rpc get-pfe-tcam-errors-app-lo0-inet6-fil {
     description "Lo0 Inet6 Filter";
     junos:command "show pfe tcam errors app lo0-inet6-fil";
     output {
       choice output_c {
         case output-tag {
           leaf output {
             type string;
           }
         }
         case multichassis-tag {
           anyxml multi-routing-engine-results;
         }
       }
     }
   }
   rpc get-pfe-tcam-errors-app-mac-drop-cnt {
     description "Statistics for drops by mac-validate/src-mac filters";
     junos:command "show pfe tcam errors app mac-drop-cnt";
     output {
       choice output_c {
         case output-tag {
           leaf output {
             type string;
           }
         }
         case multichassis-tag {
           anyxml multi-routing-engine-results;
         }
       }
     }
   }
   rpc get-pfe-tcam-errors-app-no-local-switching {
     description "Bridge no-local-switching";
     junos:command "show pfe tcam errors app no-local-switching";
     output {
       choice output_c {
         case output-tag {
           leaf output {
             type string;
           }
         }
         case multichassis-tag {
           anyxml multi-routing-engine-results;
         }
       }
     }
   }
   rpc get-pfe-tcam-errors-app-cos-fc {
     description "Ifl level fixed classifier";
     junos:command "show pfe tcam errors app cos-fc";
     output {
       choice output_c {
         case output-tag {
           leaf output {
             type string;
           }
         }
         case multichassis-tag {
           anyxml multi-routing-engine-results;
         }
       }
     }
   }
   rpc get-pfe-tcam-errors-app-fw-fbf {
     description "Firewall filter based forwarding";
     junos:command "show pfe tcam errors app fw-fbf";
     output {
       choice output_c {
         case output-tag {
           leaf output {
             type string;
           }
         }
         case multichassis-tag {
           anyxml multi-routing-engine-results;
         }
       }
     }
   }
   rpc get-pfe-tcam-errors-app-fw-fbf-inet6 {
     description "Firewall filter based forwarding for Inet6";
     junos:command "show pfe tcam errors app fw-fbf-inet6";
     output {
       choice output_c {
         case output-tag {
           leaf output {
             type string;
           }
         }
         case multichassis-tag {
           anyxml multi-routing-engine-results;
         }
       }
     }
   }
   rpc get-pfe-tcam-errors-app-fw-semantics {
     description "Firewall sharing semantics for cli configured firewall";
     junos:command "show pfe tcam errors app fw-semantics";
     output {
       choice output_c {
         case output-tag {
           leaf output {
             type string;
           }
         }
         case multichassis-tag {
           anyxml multi-routing-engine-results;
         }
       }
     }
   }
   rpc get-pfe-tcam-errors-app-ifd-src-mac-fil {
     description "Ifd level source mac filter";
     junos:command "show pfe tcam errors app ifd-src-mac-fil";
     output {
       choice output_c {
         case output-tag {
           leaf output {
             type string;
           }
         }
         case multichassis-tag {
           anyxml multi-routing-engine-results;
         }
       }
     }
   }
   rpc get-pfe-tcam-errors-app-ing-out-iff {
     description "Ingress app on behalf of egress family filter for log/syslog";
     junos:command "show pfe tcam errors app ing-out-iff";
     output {
       choice output_c {
         case output-tag {
           leaf output {
             type string;
           }
         }
         case multichassis-tag {
           anyxml multi-routing-engine-results;
         }
       }
     }
   }
   rpc get-pfe-tcam-errors-app-ip-mac-val {
     description "Ip mac validate";
     junos:command "show pfe tcam errors app ip-mac-val";
     output {
       choice output_c {
         case output-tag {
           leaf output {
             type string;
           }
         }
         case multichassis-tag {
           anyxml multi-routing-engine-results;
         }
       }
     }
   }
   rpc get-pfe-tcam-errors-app-ip-mac-val-bcast {
     description "Ip mac validate for broadcast";
     junos:command "show pfe tcam errors app ip-mac-val-bcast";
     output {
       choice output_c {
         case output-tag {
           leaf output {
             type string;
           }
         }
         case multichassis-tag {
           anyxml multi-routing-engine-results;
         }
       }
     }
   }
   rpc get-pfe-tcam-errors-app-rfc2544-layer2-in {
     description "Rfc2544 for layer2 service (ingress)";
     junos:command "show pfe tcam errors app rfc2544-layer2-in";
     output {
       choice output_c {
         case output-tag {
           leaf output {
             type string;
           }
         }
         case multichassis-tag {
           anyxml multi-routing-engine-results;
         }
       }
     }
   }
   rpc get-pfe-tcam-app-list {
     description "Show tcam apps";
     junos:command "show pfe tcam app";
     output {
       choice output_c {
         case output-tag {
           leaf output {
             type string;
           }
         }
         case multichassis-tag {
           anyxml multi-routing-engine-results;
         }
       }
     }
   }
   rpc get-pfe-tcam-app-list-bd-tpid-swap {
     description "Bridge domain vlan-map with swap tpid operation";
     junos:command "show pfe tcam app bd-tpid-swap";
     output {
       choice output_c {
         case output-tag {
           leaf output {
             type string;
           }
         }
         case multichassis-tag {
           anyxml multi-routing-engine-results;
         }
       }
     }
   }
   rpc get-pfe-tcam-app-list-fw-family-out {
     description "Family level egress firewall";
     junos:command "show pfe tcam app fw-family-out";
     output {
       choice output_c {
         case output-tag {
           leaf output {
             type string;
           }
         }
         case multichassis-tag {
           anyxml multi-routing-engine-results;
         }
       }
     }
   }
   rpc get-pfe-tcam-app-list-fw-inet6-family-out {
     description "Inet6 Family level egress firewall";
     junos:command "show pfe tcam app fw-inet6-family-out";
     output {
       choice output_c {
         case output-tag {
           leaf output {
             type string;
           }
         }
         case multichassis-tag {
           anyxml multi-routing-engine-results;
         }
       }
     }
   }
   rpc get-pfe-tcam-app-list-fw-ifl-out {
     description "Ifl level egress firewall";
     junos:command "show pfe tcam app fw-ifl-out";
     output {
       choice output_c {
         case output-tag {
           leaf output {
             type string;
           }
         }
         case multichassis-tag {
           anyxml multi-routing-engine-results;
         }
       }
     }
   }
   rpc get-pfe-tcam-app-list-ifl-statistics-out {
     description "Ifl level statistics (egress)";
     junos:command "show pfe tcam app ifl-statistics-out";
     output {
       choice output_c {
         case output-tag {
           leaf output {
             type string;
           }
         }
         case multichassis-tag {
           anyxml multi-routing-engine-results;
         }
       }
     }
   }
   rpc get-pfe-tcam-app-list-irb-cos-rw {
     description "IRB CoS rewrite";
     junos:command "show pfe tcam app irb-cos-rw";
     output {
       choice output_c {
         case output-tag {
           leaf output {
             type string;
           }
         }
         case multichassis-tag {
           anyxml multi-routing-engine-results;
         }
       }
     }
   }
   rpc get-pfe-tcam-app-list-lfm-802.3ah-out {
     description "Lfm-802.3ah (egress)";
     junos:command "show pfe tcam app lfm-802.3ah-out";
     output {
       choice output_c {
         case output-tag {
           leaf output {
             type string;
           }
         }
         case multichassis-tag {
           anyxml multi-routing-engine-results;
         }
       }
     }
   }
   rpc get-pfe-tcam-app-list-cfm-bd-filter {
     description "Cfm implicit bridge-domain filters";
     junos:command "show pfe tcam app cfm-bd-filter";
     output {
       choice output_c {
         case output-tag {
           leaf output {
             type string;
           }
         }
         case multichassis-tag {
           anyxml multi-routing-engine-results;
         }
       }
     }
   }
   rpc get-pfe-tcam-app-list-cfm-filter {
     description "Cfm implicit filters";
     junos:command "show pfe tcam app cfm-filter";
     output {
       choice output_c {
         case output-tag {
           leaf output {
             type string;
           }
         }
         case multichassis-tag {
           anyxml multi-routing-engine-results;
         }
       }
     }
   }
   rpc get-pfe-tcam-app-list-cfm-vpls-filter {
     description "Cfm implicit vpls filters";
     junos:command "show pfe tcam app cfm-vpls-filter";
     output {
       choice output_c {
         case output-tag {
           leaf output {
             type string;
           }
         }
         case multichassis-tag {
           anyxml multi-routing-engine-results;
         }
       }
     }
   }
   rpc get-pfe-tcam-app-list-cfm-vpls-ifl-filter {
     description "Cfm implicit vpls ifl filters";
     junos:command "show pfe tcam app cfm-vpls-ifl-filter";
     output {
       choice output_c {
         case output-tag {
           leaf output {
             type string;
           }
         }
         case multichassis-tag {
           anyxml multi-routing-engine-results;
         }
       }
     }
   }
   rpc get-pfe-tcam-app-list-fw-ccc-in {
     description "Ccc family ingress firewall";
     junos:command "show pfe tcam app fw-ccc-in";
     output {
       choice output_c {
         case output-tag {
           leaf output {
             type string;
           }
         }
         case multichassis-tag {
           anyxml multi-routing-engine-results;
         }
       }
     }
   }
   rpc get-pfe-tcam-app-list-fw-ifl-in {
     description "Ifl level ingress firewall";
     junos:command "show pfe tcam app fw-ifl-in";
     output {
       choice output_c {
         case output-tag {
           leaf output {
             type string;
           }
         }
         case multichassis-tag {
           anyxml multi-routing-engine-results;
         }
       }
     }
   }
   rpc get-pfe-tcam-app-list-fw-inet-ftf {
     description "Inet family ingress firewall on a forwarding-table";
     junos:command "show pfe tcam app fw-inet-ftf";
     output {
       choice output_c {
         case output-tag {
           leaf output {
             type string;
           }
         }
         case multichassis-tag {
           anyxml multi-routing-engine-results;
         }
       }
     }
   }
   rpc get-pfe-tcam-app-list-fw-inet-in {
     description "Inet family ingress firewall";
     junos:command "show pfe tcam app fw-inet-in";
     output {
       choice output_c {
         case output-tag {
           leaf output {
             type string;
           }
         }
         case multichassis-tag {
           anyxml multi-routing-engine-results;
         }
       }
     }
   }
   rpc get-pfe-tcam-app-list-fw-inet-rpf {
     description "Inet family ingress firewall on rpf fail check";
     junos:command "show pfe tcam app fw-inet-rpf";
     output {
       choice output_c {
         case output-tag {
           leaf output {
             type string;
           }
         }
         case multichassis-tag {
           anyxml multi-routing-engine-results;
         }
       }
     }
   }
   rpc get-pfe-tcam-app-list-fw-inet6-ftf {
     description "Inet6 family ingress firewall on a forwarding-table";
     junos:command "show pfe tcam app fw-inet6-ftf";
     output {
       choice output_c {
         case output-tag {
           leaf output {
             type string;
           }
         }
         case multichassis-tag {
           anyxml multi-routing-engine-results;
         }
       }
     }
   }
   rpc get-pfe-tcam-app-list-fw-inet6-in {
     description "Inet6 family ingress firewall";
     junos:command "show pfe tcam app fw-inet6-in";
     output {
       choice output_c {
         case output-tag {
           leaf output {
             type string;
           }
         }
         case multichassis-tag {
           anyxml multi-routing-engine-results;
         }
       }
     }
   }
   rpc get-pfe-tcam-app-list-fw-inet6-rpf {
     description "Inet6 family ingress firewall on a rpf fail check";
     junos:command "show pfe tcam app fw-inet6-rpf";
     output {
       choice output_c {
         case output-tag {
           leaf output {
             type string;
           }
         }
         case multichassis-tag {
           anyxml multi-routing-engine-results;
         }
       }
     }
   }
   rpc get-pfe-tcam-app-list-fw-l2-in {
     description "Bridge family ingress firewall on layer2 interface";
     junos:command "show pfe tcam app fw-l2-in";
     output {
       choice output_c {
         case output-tag {
           leaf output {
             type string;
           }
         }
         case multichassis-tag {
           anyxml multi-routing-engine-results;
         }
       }
     }
   }
   rpc get-pfe-tcam-app-list-fw-mpls-in {
     description "Mpls family ingress firewall";
     junos:command "show pfe tcam app fw-mpls-in";
     output {
       choice output_c {
         case output-tag {
           leaf output {
             type string;
           }
         }
         case multichassis-tag {
           anyxml multi-routing-engine-results;
         }
       }
     }
   }
   rpc get-pfe-tcam-app-list-fw-vpls-in {
     description "VPLS family ingress firewall on vpls interface";
     junos:command "show pfe tcam app fw-vpls-in";
     output {
       choice output_c {
         case output-tag {
           leaf output {
             type string;
           }
         }
         case multichassis-tag {
           anyxml multi-routing-engine-results;
         }
       }
     }
   }
   rpc get-pfe-tcam-app-list-gr-ifl-statistics-egr {
     description "GR Ifl level statistics (egress)";
     junos:command "show pfe tcam app gr-ifl-stats-egr";
     output {
       choice output_c {
         case output-tag {
           leaf output {
             type string;
           }
         }
         case multichassis-tag {
           anyxml multi-routing-engine-results;
         }
       }
     }
   }
   rpc get-pfe-tcam-app-list-gr-ifl-statistics-ing {
     description "GR Ifl level statistics (ingress)";
     junos:command "show pfe tcam app gr-ifl-stats-ing";
     output {
       choice output_c {
         case output-tag {
           leaf output {
             type string;
           }
         }
         case multichassis-tag {
           anyxml multi-routing-engine-results;
         }
       }
     }
   }
   rpc get-pfe-tcam-app-list-gr-ifl-statistics-preing {
     description "GR Ifl level statistics (pre-ingress)";
     junos:command "show pfe tcam app gr-ifl-stats-preing";
     output {
       choice output_c {
         case output-tag {
           leaf output {
             type string;
           }
         }
         case multichassis-tag {
           anyxml multi-routing-engine-results;
         }
       }
     }
   }
   rpc get-pfe-tcam-app-list-ifl-statistics-in {
     description "Ifl level statistics (ingress)";
     junos:command "show pfe tcam app ifl-statistics-in";
     output {
       choice output_c {
         case output-tag {
           leaf output {
             type string;
           }
         }
         case multichassis-tag {
           anyxml multi-routing-engine-results;
         }
       }
     }
   }
   rpc get-pfe-tcam-app-list-irb-fixed-cos {
     description "IRB fixed classifier filter entries";
     junos:command "show pfe tcam app irb-fixed-cos";
     output {
       choice output_c {
         case output-tag {
           leaf output {
             type string;
           }
         }
         case multichassis-tag {
           anyxml multi-routing-engine-results;
         }
       }
     }
   }
   rpc get-pfe-tcam-app-list-mrouter-port-in {
     description "Multicast router port for snooping";
     junos:command "show pfe tcam app mrouter-port-in";
     output {
       choice output_c {
         case output-tag {
           leaf output {
             type string;
           }
         }
         case multichassis-tag {
           anyxml multi-routing-engine-results;
         }
       }
     }
   }
   rpc get-pfe-tcam-app-list-lo0-inet-fil {
     description "Lo0 Inet Filter";
     junos:command "show pfe tcam app lo0-inet-fil";
     output {
       choice output_c {
         case output-tag {
           leaf output {
             type string;
           }
         }
         case multichassis-tag {
           anyxml multi-routing-engine-results;
         }
       }
     }
   }
   rpc get-pfe-tcam-app-list-lo0-inet6-fil {
     description "Lo0 Inet6 Filter";
     junos:command "show pfe tcam app lo0-inet6-fil";
     output {
       choice output_c {
         case output-tag {
           leaf output {
             type string;
           }
         }
         case multichassis-tag {
           anyxml multi-routing-engine-results;
         }
       }
     }
   }
   rpc get-pfe-tcam-app-list-mac-drop-cnt {
     description "Statistics for drops by mac-validate/src-mac filters";
     junos:command "show pfe tcam app mac-drop-cnt";
     output {
       choice output_c {
         case output-tag {
           leaf output {
             type string;
           }
         }
         case multichassis-tag {
           anyxml multi-routing-engine-results;
         }
       }
     }
   }
   rpc get-pfe-tcam-app-list-no-local-switching {
     description "Bridge no-local-switching";
     junos:command "show pfe tcam app no-local-switching";
     output {
       choice output_c {
         case output-tag {
           leaf output {
             type string;
           }
         }
         case multichassis-tag {
           anyxml multi-routing-engine-results;
         }
       }
     }
   }
   rpc get-pfe-tcam-app-list-cos-fc {
     description "Ifl level fixed classifier";
     junos:command "show pfe tcam app cos-fc";
     output {
       choice output_c {
         case output-tag {
           leaf output {
             type string;
           }
         }
         case multichassis-tag {
           anyxml multi-routing-engine-results;
         }
       }
     }
   }
   rpc get-pfe-tcam-app-list-fw-fbf {
     description "Firewall filter based forwarding";
     junos:command "show pfe tcam app fw-fbf";
     output {
       choice output_c {
         case output-tag {
           leaf output {
             type string;
           }
         }
         case multichassis-tag {
           anyxml multi-routing-engine-results;
         }
       }
     }
   }
   rpc get-pfe-tcam-app-list-fw-fbf-inet6 {
     description "Firewall filter based forwarding for Inet6";
     junos:command "show pfe tcam app fw-fbf-inet6";
     output {
       choice output_c {
         case output-tag {
           leaf output {
             type string;
           }
         }
         case multichassis-tag {
           anyxml multi-routing-engine-results;
         }
       }
     }
   }
   rpc get-pfe-tcam-app-list-fw-semantics {
     description "Firewall sharing semantics for cli configured firewall";
     junos:command "show pfe tcam app fw-semantics";
     output {
       choice output_c {
         case output-tag {
           leaf output {
             type string;
           }
         }
         case multichassis-tag {
           anyxml multi-routing-engine-results;
         }
       }
     }
   }
   rpc get-pfe-tcam-app-list-ifd-src-mac-fil {
     description "Ifd level source mac filter";
     junos:command "show pfe tcam app ifd-src-mac-fil";
     output {
       choice output_c {
         case output-tag {
           leaf output {
             type string;
           }
         }
         case multichassis-tag {
           anyxml multi-routing-engine-results;
         }
       }
     }
   }
   rpc get-pfe-tcam-app-list-ing-out-iff {
     description "Ingress app on behalf of egress family filter for log/syslog";
     junos:command "show pfe tcam app ing-out-iff";
     output {
       choice output_c {
         case output-tag {
           leaf output {
             type string;
           }
         }
         case multichassis-tag {
           anyxml multi-routing-engine-results;
         }
       }
     }
   }
   rpc get-pfe-tcam-app-list-ip-mac-val {
     description "Ip mac validate";
     junos:command "show pfe tcam app ip-mac-val";
     output {
       choice output_c {
         case output-tag {
           leaf output {
             type string;
           }
         }
         case multichassis-tag {
           anyxml multi-routing-engine-results;
         }
       }
     }
   }
   rpc get-pfe-tcam-app-list-ip-mac-val-bcast {
     description "Ip mac validate for broadcast";
     junos:command "show pfe tcam app ip-mac-val-bcast";
     output {
       choice output_c {
         case output-tag {
           leaf output {
             type string;
           }
         }
         case multichassis-tag {
           anyxml multi-routing-engine-results;
         }
       }
     }
   }
   rpc get-pfe-tcam-app-list-rfc2544-layer2-in {
     description "Rfc2544 for layer2 service (ingress)";
     junos:command "show pfe tcam app rfc2544-layer2-in";
     output {
       choice output_c {
         case output-tag {
           leaf output {
             type string;
           }
         }
         case multichassis-tag {
           anyxml multi-routing-engine-results;
         }
       }
     }
   }
   rpc get-sflow-pfe-information {
     description "Show sflow information";
     junos:command "show pfe sflow";
     output {
       choice output_c {
         case output-tag {
           leaf output {
             type string;
           }
         }
         case multichassis-tag {
           anyxml multi-routing-engine-results;
         }
       }
     }
   }
   rpc get-vxlan-mcast-stats-information {
     description "Show sflow vxlan egress multicast statistics";
     junos:command "show pfe sflow egress-mcast-stats";
     output {
       choice output_c {
         case output-tag {
           leaf output {
             type string;
           }
         }
         case multichassis-tag {
           anyxml multi-routing-engine-results;
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping pfe-information-block {
     list pfe {
       leaf slot-index {
         type int32;
         description "Slot index";
       }
       leaf slot-type {
         type string;
         description "Packet Forwarding Engine component type";
       }
       leaf slot-state {
         type string;
         description "Slot state";
       }
       leaf mgmt-state {
         type string;
         description "Management state";
       }
       leaf up-time {
         type string;
         description "Time since the slot is up";
       }
     }
   }
   grouping pfe-statistics-block {
     container pfe-multicast-stats {
       container pfe-queue-counters {
         description "Queue counter statistics";
         list pfe-queue {
           description "Counters for a single queue";
           leaf number {
             type int32;
             description "Queue number";
           }
           leaf forwarding-class-name {
             type string;
             description "Forwarding class name associated with queue";
           }
           leaf queued-packets-na {
             type string;
             description "Queued packets not available";
           }
           leaf queued-bytes-na {
             type string;
             description "Queued bytes not available";
           }
           leaf queued-packets {
             type int32;
             description "Queued packet count";
           }
           leaf queued-packets-rate {
             type int32;
             description "Rate at which packets are queued";
           }
           leaf queued-bytes {
             type int32;
             description "Queued bytes count";
           }
           leaf queued-bytes-rate {
             type int32;
             description "Rate at which bytes are queued";
           }
           leaf tail-drop-packets {
             type int32;
             description "Number of packets dropped at the tail of the queue";
           }
           leaf tail-drop-packets-rate {
             type int32;
             description "Rate at which packets are dropped at tail of queue";
           }
           leaf red-packets {
             type int32;
             description "Number of packets dropped due to RED";
           }
           leaf red-packets-rate {
             type int32;
             description "Rate at which packets are dropped due to RED";
           }
           leaf red-packets-low {
             type int32;
             description "Number of RED dropped low-loss packets";
           }
           leaf red-packets-rate-low {
             type int32;
             description "RED drop rate for low-loss packets";
           }
           leaf red-packets-high {
             type int32;
             description "Number of RED dropped high-loss packets";
           }
           leaf red-packets-rate-high {
             type int32;
             description "RED drop rate for high-loss packets";
           }
           leaf red-bytes {
             type int32;
             description "Number of bytes dropped due to RED";
           }
           leaf red-bytes-rate {
             type int32;
             description "Rate at which bytes are dropped due to RED";
           }
           leaf red-bytes-low {
             type int32;
             description "Number of RED dropped low-loss bytes";
           }
           leaf red-bytes-rate-low {
             type int32;
             description "RED drop rate for low-loss bytes";
           }
           leaf red-bytes-high {
             type int32;
             description "Number of RED dropped high-loss bytes";
           }
           leaf red-bytes-rate-high {
             type int32;
             description "RED drop rate for high-loss bytes";
           }
           leaf trans-packets {
             type int32;
             description "Total number of transmitted packets";
           }
           leaf trans-bytes {
             type int32;
             description "Total number of transmitted bytes";
           }
           leaf trans-packets-rate {
             type int32;
             description "Rate at which packets are transmitted";
           }
           leaf trans-bytes-rate {
             type int32;
             description "Rate at which bytes are transmitted";
           }
           leaf tail-drop-packets-na {
             type string;
             description "Number of packets dropped due to tail drop not available";
           }
           leaf rate-limit-drop-packets {
             type int32;
             description "Number of packets dropped by rate-limit for the queue";
           }
           leaf rate-limit-drop-packets-rate {
             type int32;
             description "Rate at which packets are dropped by rate-limit for the queue";
           }
           leaf rate-limit-drop-packets-na {
             type string;
             description "Number of packets dropped due to rate-limit drop not available";
           }
           leaf rate-limit-drop-bytes {
             type int32;
             description "Number of bytes dropped at the tail of the queue";
           }
           leaf rate-limit-drop-bytes-rate {
             type int32;
             description "Rate at which bytes are dropped at the tail of the queue";
           }
           leaf rate-limit-drop-bytes-na {
             type string;
             description "Number of bytes dropped due to tail drop not available";
           }
           leaf red-packets-na {
             type string;
             description "Number of packets dropped due to RED not available";
           }
           leaf red-bytes-na {
             type string;
             description "Number of bytes dropped due to RED not available";
           }
           leaf red-packets-ln {
             type int32;
             description "Number of RED dropped low-loss, non-TCP packets";
           }
           leaf red-bytes-ln {
             type int32;
             description "Number of RED dropped low-loss, non-TCP bytes";
           }
           leaf red-packets-rate-ln {
             type int32;
             description "RED drop rate for low-loss, non-TCP packets";
           }
           leaf red-bytes-rate-ln {
             type int32;
             description "RED drop rate for low-loss, non-TCP bytes";
           }
           leaf red-packets-lt {
             type int32;
             description "Number of RED dropped of low-loss, TCP packets";
           }
           leaf red-bytes-lt {
             type int32;
             description "Number of RED dropped low-loss, TCP bytes";
           }
           leaf red-packets-rate-lt {
             type int32;
             description "RED drop rate for low-loss, TCP packets";
           }
           leaf red-bytes-rate-lt {
             type int32;
             description "RED drop rate for low-loss, TCP bytes";
           }
           leaf red-packets-ht {
             type int32;
             description "Number of RED dropped high-loss, TCP packets";
           }
           leaf red-bytes-ht {
             type int32;
             description "Number of RED dropped high-loss, TCP bytes";
           }
           leaf red-packets-rate-ht {
             type int32;
             description "RED drop rate for high-loss, TCP packets";
           }
           leaf red-bytes-rate-ht {
             type int32;
             description "RED drop rate for high-loss, TCP bytes";
           }
           leaf red-packets-hn {
             type int32;
             description "Number of RED dropped high-loss, non-TCP packets";
           }
           leaf red-bytes-hn {
             type int32;
             description "Number of RED dropped high-loss, non-TCP bytes";
           }
           leaf red-packets-rate-hn {
             type int32;
             description "RED drop rate for high-loss, non-TCP packets";
           }
           leaf red-bytes-rate-hn {
             type int32;
             description "RED drop rate for high-loss, non-TCP bytes";
           }
           leaf red-packets-medium-low {
             type int32;
             description "Number of RED dropped medium-low-loss packets";
           }
           leaf red-bytes-medium-low {
             type int32;
             description "Number of RED dropped medium-low-loss bytes";
           }
           leaf red-packets-rate-medium-low {
             type int32;
             description "RED drop rate for medium-low-loss packets";
           }
           leaf red-bytes-rate-medium-low {
             type int32;
             description "RED drop rate for medium-low-loss bytes";
           }
           leaf red-packets-medium-high {
             type int32;
             description "Number of RED dropped medium-high-loss packets";
           }
           leaf red-bytes-medium-high {
             type int32;
             description "Number of RED dropped medium-high-loss bytes";
           }
           leaf red-packets-rate-medium-high {
             type int32;
             description "RED drop rate for medium-high-loss packets";
           }
           leaf red-bytes-rate-medium-high {
             type int32;
             description "RED drop rate for medium-high-loss bytes";
           }
           leaf red-packets-medium {
             type int32;
             description "Number of RED dropped medium-loss packets";
           }
           leaf red-bytes-medium {
             type int32;
             description "Number of RED dropped medium-loss bytes";
           }
           leaf red-packets-rate-medium {
             type int32;
             description "RED drop rate for medium-loss packets";
           }
           leaf red-bytes-rate-medium {
             type int32;
             description "RED drop rate for medium-loss bytes";
           }
           leaf timestamp {
             type int32;
             description "Last packet enqueued timestamp";
           }
         }
       }
     }
     container pfe-cpu-stats {
       container pfe-queue-counters {
         description "Queue counter statistics";
         list pfe-queue {
           description "Counters for a single queue";
           leaf number {
             type int32;
             description "Queue number";
           }
           leaf forwarding-class-name {
             type string;
             description "Forwarding class name associated with queue";
           }
           leaf queued-packets-na {
             type string;
             description "Queued packets not available";
           }
           leaf queued-bytes-na {
             type string;
             description "Queued bytes not available";
           }
           leaf queued-packets {
             type int32;
             description "Queued packet count";
           }
           leaf queued-packets-rate {
             type int32;
             description "Rate at which packets are queued";
           }
           leaf queued-bytes {
             type int32;
             description "Queued bytes count";
           }
           leaf queued-bytes-rate {
             type int32;
             description "Rate at which bytes are queued";
           }
           leaf tail-drop-packets {
             type int32;
             description "Number of packets dropped at the tail of the queue";
           }
           leaf tail-drop-packets-rate {
             type int32;
             description "Rate at which packets are dropped at tail of queue";
           }
           leaf red-packets {
             type int32;
             description "Number of packets dropped due to RED";
           }
           leaf red-packets-rate {
             type int32;
             description "Rate at which packets are dropped due to RED";
           }
           leaf red-packets-low {
             type int32;
             description "Number of RED dropped low-loss packets";
           }
           leaf red-packets-rate-low {
             type int32;
             description "RED drop rate for low-loss packets";
           }
           leaf red-packets-high {
             type int32;
             description "Number of RED dropped high-loss packets";
           }
           leaf red-packets-rate-high {
             type int32;
             description "RED drop rate for high-loss packets";
           }
           leaf red-bytes {
             type int32;
             description "Number of bytes dropped due to RED";
           }
           leaf red-bytes-rate {
             type int32;
             description "Rate at which bytes are dropped due to RED";
           }
           leaf red-bytes-low {
             type int32;
             description "Number of RED dropped low-loss bytes";
           }
           leaf red-bytes-rate-low {
             type int32;
             description "RED drop rate for low-loss bytes";
           }
           leaf red-bytes-high {
             type int32;
             description "Number of RED dropped high-loss bytes";
           }
           leaf red-bytes-rate-high {
             type int32;
             description "RED drop rate for high-loss bytes";
           }
           leaf trans-packets {
             type int32;
             description "Total number of transmitted packets";
           }
           leaf trans-bytes {
             type int32;
             description "Total number of transmitted bytes";
           }
           leaf trans-packets-rate {
             type int32;
             description "Rate at which packets are transmitted";
           }
           leaf trans-bytes-rate {
             type int32;
             description "Rate at which bytes are transmitted";
           }
           leaf tail-drop-packets-na {
             type string;
             description "Number of packets dropped due to tail drop not available";
           }
           leaf rate-limit-drop-packets {
             type int32;
             description "Number of packets dropped by rate-limit for the queue";
           }
           leaf rate-limit-drop-packets-rate {
             type int32;
             description "Rate at which packets are dropped by rate-limit for the queue";
           }
           leaf rate-limit-drop-packets-na {
             type string;
             description "Number of packets dropped due to rate-limit drop not available";
           }
           leaf rate-limit-drop-bytes {
             type int32;
             description "Number of bytes dropped at the tail of the queue";
           }
           leaf rate-limit-drop-bytes-rate {
             type int32;
             description "Rate at which bytes are dropped at the tail of the queue";
           }
           leaf rate-limit-drop-bytes-na {
             type string;
             description "Number of bytes dropped due to tail drop not available";
           }
           leaf red-packets-na {
             type string;
             description "Number of packets dropped due to RED not available";
           }
           leaf red-bytes-na {
             type string;
             description "Number of bytes dropped due to RED not available";
           }
           leaf red-packets-ln {
             type int32;
             description "Number of RED dropped low-loss, non-TCP packets";
           }
           leaf red-bytes-ln {
             type int32;
             description "Number of RED dropped low-loss, non-TCP bytes";
           }
           leaf red-packets-rate-ln {
             type int32;
             description "RED drop rate for low-loss, non-TCP packets";
           }
           leaf red-bytes-rate-ln {
             type int32;
             description "RED drop rate for low-loss, non-TCP bytes";
           }
           leaf red-packets-lt {
             type int32;
             description "Number of RED dropped of low-loss, TCP packets";
           }
           leaf red-bytes-lt {
             type int32;
             description "Number of RED dropped low-loss, TCP bytes";
           }
           leaf red-packets-rate-lt {
             type int32;
             description "RED drop rate for low-loss, TCP packets";
           }
           leaf red-bytes-rate-lt {
             type int32;
             description "RED drop rate for low-loss, TCP bytes";
           }
           leaf red-packets-ht {
             type int32;
             description "Number of RED dropped high-loss, TCP packets";
           }
           leaf red-bytes-ht {
             type int32;
             description "Number of RED dropped high-loss, TCP bytes";
           }
           leaf red-packets-rate-ht {
             type int32;
             description "RED drop rate for high-loss, TCP packets";
           }
           leaf red-bytes-rate-ht {
             type int32;
             description "RED drop rate for high-loss, TCP bytes";
           }
           leaf red-packets-hn {
             type int32;
             description "Number of RED dropped high-loss, non-TCP packets";
           }
           leaf red-bytes-hn {
             type int32;
             description "Number of RED dropped high-loss, non-TCP bytes";
           }
           leaf red-packets-rate-hn {
             type int32;
             description "RED drop rate for high-loss, non-TCP packets";
           }
           leaf red-bytes-rate-hn {
             type int32;
             description "RED drop rate for high-loss, non-TCP bytes";
           }
           leaf red-packets-medium-low {
             type int32;
             description "Number of RED dropped medium-low-loss packets";
           }
           leaf red-bytes-medium-low {
             type int32;
             description "Number of RED dropped medium-low-loss bytes";
           }
           leaf red-packets-rate-medium-low {
             type int32;
             description "RED drop rate for medium-low-loss packets";
           }
           leaf red-bytes-rate-medium-low {
             type int32;
             description "RED drop rate for medium-low-loss bytes";
           }
           leaf red-packets-medium-high {
             type int32;
             description "Number of RED dropped medium-high-loss packets";
           }
           leaf red-bytes-medium-high {
             type int32;
             description "Number of RED dropped medium-high-loss bytes";
           }
           leaf red-packets-rate-medium-high {
             type int32;
             description "RED drop rate for medium-high-loss packets";
           }
           leaf red-bytes-rate-medium-high {
             type int32;
             description "RED drop rate for medium-high-loss bytes";
           }
           leaf red-packets-medium {
             type int32;
             description "Number of RED dropped medium-loss packets";
           }
           leaf red-bytes-medium {
             type int32;
             description "Number of RED dropped medium-loss bytes";
           }
           leaf red-packets-rate-medium {
             type int32;
             description "RED drop rate for medium-loss packets";
           }
           leaf red-bytes-rate-medium {
             type int32;
             description "RED drop rate for medium-loss bytes";
           }
           leaf timestamp {
             type int32;
             description "Last packet enqueued timestamp";
           }
         }
       }
     }
     container pfe-tail-drop-statistics {
       container pfe-queue-counters {
         description "Queue counter statistics";
         list pfe-queue {
           description "Counters for a single queue";
           leaf tail-drop-packets {
             type int32;
             description "Number of packets dropped at the tail of the queue";
           }
           leaf tail-drop-packets-rate {
             type int32;
             description "Rate at which packets are dropped at tail of queue";
           }
           leaf trans-packets {
             type int32;
             description "Total number of transmitted packets";
           }
           leaf trans-bytes {
             type int32;
             description "Total number of transmitted bytes";
           }
           leaf trans-packets-rate {
             type int32;
             description "Rate at which packets are transmitted";
           }
           leaf trans-bytes-rate {
             type int32;
             description "Rate at which bytes are transmitted";
           }
           leaf tail-drop-packets-na {
             type string;
             description "Number of packets dropped due to tail drop not available";
           }
           leaf rate-limit-drop-packets {
             type int32;
             description "Number of packets dropped by rate-limit for the queue";
           }
           leaf rate-limit-drop-packets-rate {
             type int32;
             description "Rate at which packets are dropped by rate-limit for the queue";
           }
           leaf rate-limit-drop-packets-na {
             type string;
             description "Number of packets dropped due to rate-limit drop not available";
           }
           leaf rate-limit-drop-bytes {
             type int32;
             description "Number of bytes dropped at the tail of the queue";
           }
           leaf rate-limit-drop-bytes-rate {
             type int32;
             description "Rate at which bytes are dropped at the tail of the queue";
           }
           leaf rate-limit-drop-bytes-na {
             type string;
             description "Number of bytes dropped due to tail drop not available";
           }
           leaf red-packets-na {
             type string;
             description "Number of packets dropped due to RED not available";
           }
           leaf red-bytes-na {
             type string;
             description "Number of bytes dropped due to RED not available";
           }
           leaf red-packets-ln {
             type int32;
             description "Number of RED dropped low-loss, non-TCP packets";
           }
           leaf red-bytes-ln {
             type int32;
             description "Number of RED dropped low-loss, non-TCP bytes";
           }
           leaf red-packets-rate-ln {
             type int32;
             description "RED drop rate for low-loss, non-TCP packets";
           }
           leaf red-bytes-rate-ln {
             type int32;
             description "RED drop rate for low-loss, non-TCP bytes";
           }
           leaf red-packets-lt {
             type int32;
             description "Number of RED dropped of low-loss, TCP packets";
           }
           leaf red-bytes-lt {
             type int32;
             description "Number of RED dropped low-loss, TCP bytes";
           }
           leaf red-packets-rate-lt {
             type int32;
             description "RED drop rate for low-loss, TCP packets";
           }
           leaf red-bytes-rate-lt {
             type int32;
             description "RED drop rate for low-loss, TCP bytes";
           }
           leaf red-packets-ht {
             type int32;
             description "Number of RED dropped high-loss, TCP packets";
           }
           leaf red-bytes-ht {
             type int32;
             description "Number of RED dropped high-loss, TCP bytes";
           }
           leaf red-packets-rate-ht {
             type int32;
             description "RED drop rate for high-loss, TCP packets";
           }
           leaf red-bytes-rate-ht {
             type int32;
             description "RED drop rate for high-loss, TCP bytes";
           }
           leaf red-packets-hn {
             type int32;
             description "Number of RED dropped high-loss, non-TCP packets";
           }
           leaf red-bytes-hn {
             type int32;
             description "Number of RED dropped high-loss, non-TCP bytes";
           }
           leaf red-packets-rate-hn {
             type int32;
             description "RED drop rate for high-loss, non-TCP packets";
           }
           leaf red-bytes-rate-hn {
             type int32;
             description "RED drop rate for high-loss, non-TCP bytes";
           }
           leaf red-packets-medium-low {
             type int32;
             description "Number of RED dropped medium-low-loss packets";
           }
           leaf red-bytes-medium-low {
             type int32;
             description "Number of RED dropped medium-low-loss bytes";
           }
           leaf red-packets-rate-medium-low {
             type int32;
             description "RED drop rate for medium-low-loss packets";
           }
           leaf red-bytes-rate-medium-low {
             type int32;
             description "RED drop rate for medium-low-loss bytes";
           }
           leaf red-packets-medium-high {
             type int32;
             description "Number of RED dropped medium-high-loss packets";
           }
           leaf red-bytes-medium-high {
             type int32;
             description "Number of RED dropped medium-high-loss bytes";
           }
           leaf red-packets-rate-medium-high {
             type int32;
             description "RED drop rate for medium-high-loss packets";
           }
           leaf red-bytes-rate-medium-high {
             type int32;
             description "RED drop rate for medium-high-loss bytes";
           }
           leaf red-packets-medium {
             type int32;
             description "Number of RED dropped medium-loss packets";
           }
           leaf red-bytes-medium {
             type int32;
             description "Number of RED dropped medium-loss bytes";
           }
           leaf red-packets-rate-medium {
             type int32;
             description "RED drop rate for medium-loss packets";
           }
           leaf red-bytes-rate-medium {
             type int32;
             description "RED drop rate for medium-loss bytes";
           }
           leaf timestamp {
             type int32;
             description "Last packet enqueued timestamp";
           }
         }
       }
     }
     container pfe-voq-drop-statistics {
       container pfe-voq-drop-counter {
         description "VOQ drops";
         leaf pfe_fpc_slot {
           type int32;
           description "FPC_Slot id";
         }
         list pfe-voq-dev-drop {
           description "Drops for a single device";
           leaf num {
             type int32;
             description "Device number";
           }
           leaf tail-dropped-buffers1 {
             type int32;
             description "Tail dropped buffers voq-1";
           }
           leaf tail-dropped-buffers2 {
             type int32;
             description "Tail dropped buffers voq-2";
           }
           leaf ecc-dropped-buffers1 {
             type int32;
             description "Drops due to ECC error voq-1";
           }
           leaf ecc-dropped-buffers2 {
             type int32;
             description "Drops due to ECC error voq-2";
           }
           leaf device-dropped-buffers1 {
             type int32;
             description "Drops due to device disabled voq-1";
           }
           leaf device-dropped-buffers2 {
             type int32;
             description "Drops due to device disabled voq-2";
           }
         }
       }
     }
     container pfe-mem-error-statistics {
       container pfe-mem-error-counter {
         description "Memory errors";
         leaf pfe_fpc_num {
           type int32;
           description "FPC_Slot id";
         }
         list pfe-mem-dev-error {
           description "Errors for a single device";
           leaf num-dev {
             type int32;
             description "Device number";
           }
           leaf ingress-dsu-parity {
             type int32;
             description "IngressDSU parity errors";
           }
           leaf ingress-dsu-ecc {
             type int32;
             description "IngressDSU ECC errors";
           }
           leaf egress-dsu-parity {
             type int32;
             description "EgressDSU parity errors";
           }
           leaf egress-dsu-ecc {
             type int32;
             description "EgressDSU ECC errors";
           }
           leaf csu0-parity {
             type int32;
             description "Channel Service Unit parity errors";
           }
           leaf csu0-ecc {
             type int32;
             description "Channel Service Unit ECC errors";
           }
           leaf lpm0-parity {
             type int32;
             description "Longest Prefix Match 0 parity errors";
           }
           leaf lpm0-ecc {
             type int32;
             description "Longest Prefix Match 0 ECC errors";
           }
           leaf lpm1-parity {
             type int32;
             description "Longest Prefix Match 1 parity errors";
           }
           leaf lpm1-ecc {
             type int32;
             description "Longest Prefix Match 1 ECC errors";
           }
           leaf lpm2-parity {
             type int32;
             description "Longest Prefix Match 2 parity errors";
           }
           leaf lpm2-ecc {
             type int32;
             description "Longest Prefix Match 2 ECC errors";
           }
           leaf csu1-parity {
             type int32;
             description "Channel Service Unit 1 parity errors";
           }
           leaf csu1-ecc {
             type int32;
             description "Channel Service Unit 1 ECC errors";
           }
         }
       }
     }
     container pfe-total-tail-drop {
       container pfe-queue-counters {
         description "Queue counter statistics";
         list pfe-queue {
           description "Counters for a single queue";
           leaf tail-drop-packets {
             type int32;
             description "Number of packets dropped at the tail of the queue";
           }
           leaf trans-packets {
             type int32;
             description "Total number of transmitted packets";
           }
           leaf trans-bytes {
             type int32;
             description "Total number of transmitted bytes";
           }
           leaf trans-packets-rate {
             type int32;
             description "Rate at which packets are transmitted";
           }
           leaf trans-bytes-rate {
             type int32;
             description "Rate at which bytes are transmitted";
           }
           leaf tail-drop-packets-na {
             type string;
             description "Number of packets dropped due to tail drop not available";
           }
           leaf rate-limit-drop-packets {
             type int32;
             description "Number of packets dropped by rate-limit for the queue";
           }
           leaf rate-limit-drop-packets-rate {
             type int32;
             description "Rate at which packets are dropped by rate-limit for the queue";
           }
           leaf rate-limit-drop-packets-na {
             type string;
             description "Number of packets dropped due to rate-limit drop not available";
           }
           leaf rate-limit-drop-bytes {
             type int32;
             description "Number of bytes dropped at the tail of the queue";
           }
           leaf rate-limit-drop-bytes-rate {
             type int32;
             description "Rate at which bytes are dropped at the tail of the queue";
           }
           leaf rate-limit-drop-bytes-na {
             type string;
             description "Number of bytes dropped due to tail drop not available";
           }
           leaf red-packets-na {
             type string;
             description "Number of packets dropped due to RED not available";
           }
           leaf red-bytes-na {
             type string;
             description "Number of bytes dropped due to RED not available";
           }
           leaf red-packets-ln {
             type int32;
             description "Number of RED dropped low-loss, non-TCP packets";
           }
           leaf red-bytes-ln {
             type int32;
             description "Number of RED dropped low-loss, non-TCP bytes";
           }
           leaf red-packets-rate-ln {
             type int32;
             description "RED drop rate for low-loss, non-TCP packets";
           }
           leaf red-bytes-rate-ln {
             type int32;
             description "RED drop rate for low-loss, non-TCP bytes";
           }
           leaf red-packets-lt {
             type int32;
             description "Number of RED dropped of low-loss, TCP packets";
           }
           leaf red-bytes-lt {
             type int32;
             description "Number of RED dropped low-loss, TCP bytes";
           }
           leaf red-packets-rate-lt {
             type int32;
             description "RED drop rate for low-loss, TCP packets";
           }
           leaf red-bytes-rate-lt {
             type int32;
             description "RED drop rate for low-loss, TCP bytes";
           }
           leaf red-packets-ht {
             type int32;
             description "Number of RED dropped high-loss, TCP packets";
           }
           leaf red-bytes-ht {
             type int32;
             description "Number of RED dropped high-loss, TCP bytes";
           }
           leaf red-packets-rate-ht {
             type int32;
             description "RED drop rate for high-loss, TCP packets";
           }
           leaf red-bytes-rate-ht {
             type int32;
             description "RED drop rate for high-loss, TCP bytes";
           }
           leaf red-packets-hn {
             type int32;
             description "Number of RED dropped high-loss, non-TCP packets";
           }
           leaf red-bytes-hn {
             type int32;
             description "Number of RED dropped high-loss, non-TCP bytes";
           }
           leaf red-packets-rate-hn {
             type int32;
             description "RED drop rate for high-loss, non-TCP packets";
           }
           leaf red-bytes-rate-hn {
             type int32;
             description "RED drop rate for high-loss, non-TCP bytes";
           }
           leaf red-packets-medium-low {
             type int32;
             description "Number of RED dropped medium-low-loss packets";
           }
           leaf red-bytes-medium-low {
             type int32;
             description "Number of RED dropped medium-low-loss bytes";
           }
           leaf red-packets-rate-medium-low {
             type int32;
             description "RED drop rate for medium-low-loss packets";
           }
           leaf red-bytes-rate-medium-low {
             type int32;
             description "RED drop rate for medium-low-loss bytes";
           }
           leaf red-packets-medium-high {
             type int32;
             description "Number of RED dropped medium-high-loss packets";
           }
           leaf red-bytes-medium-high {
             type int32;
             description "Number of RED dropped medium-high-loss bytes";
           }
           leaf red-packets-rate-medium-high {
             type int32;
             description "RED drop rate for medium-high-loss packets";
           }
           leaf red-bytes-rate-medium-high {
             type int32;
             description "RED drop rate for medium-high-loss bytes";
           }
           leaf red-packets-medium {
             type int32;
             description "Number of RED dropped medium-loss packets";
           }
           leaf red-bytes-medium {
             type int32;
             description "Number of RED dropped medium-loss bytes";
           }
           leaf red-packets-rate-medium {
             type int32;
             description "RED drop rate for medium-loss packets";
           }
           leaf red-bytes-rate-medium {
             type int32;
             description "RED drop rate for medium-loss bytes";
           }
           leaf timestamp {
             type int32;
             description "Last packet enqueued timestamp";
           }
         }
       }
     }
     container pfe-fpc-details {
       leaf pfe-fpc-index {
         type int32;
         description "FPC slot index";
       }
       leaf pfe-index {
         type int32;
         description "Pfe index";
       }
     }
     container pfe-traffic-statistics {
       leaf pfe-input-packets {
         type uint64;
         description "Packet Forwarding Engine input packets";
       }
       leaf input-pps {
         type uint64;
         description "Input packets (per second)";
       }
       leaf pfe-output-packets {
         type uint64;
         description "Packet Forwarding Engine output packets";
       }
       leaf output-pps {
         type uint64;
         description "Output packets (per second)";
       }
       leaf pfe-fabric-input {
         type uint64;
         description "Packet Forwarding Engine fabric packets";
       }
       leaf pfe-fabric-input-pps {
         type uint64;
         description "Packet Forwarding Engine fabric packet per second";
       }
       leaf pfe-fabric-output {
         type uint64;
         description "Packet Forwarding Engine fabric packets";
       }
       leaf pfe-fabric-output-pps {
         type uint64;
         description "Packet Forwarding Engine fabric packet per second";
       }
       leaf pfe-fabric-input-cps {
         type uint64;
         description "Packet Forwarding Engine fabric cell per second";
       }
       leaf pfe-fabric-output-cps {
         type uint64;
         description "Packet Forwarding Engine fabric cell per second";
       }
     }
     list pfe-fabric-statistics {
       leaf pfe-fabric-prefix {
         type string;
         description "Packet Forwarding Engine fabric prefix";
       }
       leaf pfe-fabric-packets {
         type uint64;
         description "Packet Forwarding Engine fabric packets";
       }
       leaf pfe-fabric-bytes {
         type uint64;
         description "Packet Forwarding Engine fabric bytes";
       }
     }
     container pfe-local-traffic-statistics {
       leaf pfe-input-packets {
         type uint64;
         description "Packet Forwarding Engine input packets";
       }
       leaf pfe-output-packets {
         type uint64;
         description "Packet Forwarding Engine output packets";
       }
       leaf software-input-control-drops {
         type uint64;
         description "Drop count of control-priority packets received from host";
       }
       leaf software-input-high-drops {
         type uint64;
         description "Drop count of high-priority packets received from host";
       }
       leaf software-input-medium-drops {
         type uint64;
         description "Drop count of medium-priority packets received from host";
       }
       leaf software-input-low-drops {
         type uint64;
         description "Drop count of low-priority packets received from host";
       }
       leaf software-output-low-drops {
         type uint64;
         description "Drop count of low-priority packets sent to host";
       }
       leaf hardware-input-drops {
         type uint64;
         description "Low-priority packets discarded by hardware";
       }
     }
     container pfe-local-protocol-statistics {
       leaf hdlc-keepalive-count {
         type uint64;
         description "HDLC keepalive packet count";
       }
       leaf atm-oam-count {
         type uint64;
         description "ATM OAM packet count";
       }
       leaf fr-lmi-count {
         type uint64;
         description "Frame Relay LMI packet count";
       }
       leaf ppp-lcp-ncp-count {
         type uint64;
         description "PPP LCP/NCP packet count";
       }
       leaf ospf-hello-count {
         type uint64;
         description "OSPF hello packets";
       }
       leaf ospf3-hello-count {
         type uint64;
         description "OSPF3 hello packets";
       }
       leaf rsvp-hello-count {
         type uint64;
         description "RSVP hello packets";
       }
       leaf ldp-hello-count {
         type uint64;
         description "LDP hello packets";
       }
       leaf bfd-count {
         type uint64;
         description "BFD packets";
       }
       leaf isis-iih-count {
         type uint64;
         description "IS-IS IIH packets";
       }
       leaf lacp-count {
         type uint64;
         description "LACP packet count";
       }
       leaf arp-count {
         type uint64;
         description "ARP packet count";
       }
       leaf ether-oam-count {
         type uint64;
         description "ETHER OAM packet count";
       }
       leaf unknown-count {
         type uint64;
         description "Unknown packet count";
       }
     }
     container pfe-bfd-statistics-detail {
       leaf bfd-invalid-iif {
         type uint64;
         description "Packets with an invalid interface";
       }
       leaf bfd-invalid-iff {
         type uint64;
         description "Packets having an invalid address family ";
       }
       leaf bfd-bad-checksum {
         type uint64;
         description "Packets having incorrect checksum";
       }
       leaf bfd-bad-options {
         type uint64;
         description "Packets having incorrect options";
       }
       leaf bfd-bad-length {
         type uint64;
         description "Packets having incorrect length";
       }
       leaf bfd-bad-udp-checksum {
         type uint64;
         description "Packets having incorrect udp checksum";
       }
       leaf bfd-bad-udp-length {
         type uint64;
         description "Pckets having incorrect udp length";
       }
       leaf bfd-bad-udp-ports {
         type uint64;
         description "Packets with incorrect udp destination ports";
       }
       leaf bfd-no-local-ifl {
         type uint64;
         description "Packets with local logical interface lookup failures";
       }
       leaf bfd-bad-ifl-prefix-length {
         type uint64;
         description "Packets with logical interface prefix length mismatch";
       }
       leaf bfd-rx-queue-overflow {
         type uint64;
         description "Packet drops due to RX Queue overflow";
       }
       leaf bfd-out-of-packets {
         type uint64;
         description "Packet allocation failures";
       }
       leaf bfd-total-packets {
         type uint64;
         description "Packets received";
       }
       leaf bfd-total-absorbed {
         type uint64;
         description "Packets absorbed";
       }
       leaf bfd-transmit-errors {
         type uint64;
         description "Packets failed to transmit";
       }
     }
     container pfe-cfm-statistics-detail {
       leaf cfm-packets-transmitted {
         type uint32;
         description "Total packets transmitted";
       }
       leaf cfm-packets-transmit-error {
         type uint32;
         description "Packets failed to transmit";
       }
       leaf cfm-packets-received {
         type uint32;
         description "Total packets received on pfe";
       }
       leaf cfm-packets-sent-to-re {
         type uint32;
         description "Packets send to RE";
       }
       leaf cfm-packets-absorbed {
         type uint32;
         description "Packets absorbed";
       }
       leaf cfm-packets-received-invalid-length {
         type uint32;
         description "Packets received with invalid length";
       }
       leaf cfm-packets-dropped {
         type uint32;
         description "Packets dropped on pfe";
       }
       leaf cfm-packets-received-with-sequence-number {
         type uint32;
         description "Packets received with sequence number";
       }
     }
     container pfe-lfm-statistics-detail {
       leaf lfm-packets-transmitted {
         type uint32;
         description "Total packets transmitted";
       }
       leaf lfm-packets-transmit-error {
         type uint32;
         description "Packets failed to transmit";
       }
       leaf lfm-packets-received {
         type uint32;
         description "Total packets received on pfe";
       }
       leaf lfm-packets-sent-to-re {
         type uint32;
         description "Packets send to RE";
       }
       leaf lfm-packets-absorbed {
         type uint32;
         description "Packets absorbed";
       }
       leaf lfm-packets-dropped {
         type uint32;
         description "Packets dropped on pfe";
       }
     }
     container pfe-vrrp-statistics-detail {
       leaf vrrp-packets-transmitted {
         type uint32;
         description "Total packets transmitted";
       }
       leaf vrrp-packets-transmit-error {
         type uint32;
         description "Packets failed to transmit";
       }
       leaf vrrp-packets-received {
         type uint32;
         description "Total packets received on pfe";
       }
       leaf vrrp-packets-sent-to-re {
         type uint32;
         description "Packets send to RE";
       }
       leaf vrrp-packets-absorbed {
         type uint32;
         description "Packets absorbed";
       }
       leaf vrrp-packets-dropped {
         type uint32;
         description "Packets dropped on pfe";
       }
     }
     container pfe-hardware-discard-statistics {
       leaf timeout-discard {
         type uint64;
         description "Packets discarded because of a timeout";
       }
       leaf truncated-key-discard {
         type uint64;
         description "Truncated key packets";
       }
       leaf bits-to-test-discard {
         type uint64;
         description "Packets failing bit-to test";
       }
       leaf data-error-discard {
         type uint64;
         description "Packets with data errors";
       }
       leaf tcp-header-error-discard {
         type uint64;
         description "Packets with TCP header length errors";
       }
       leaf stack-underflow-discard {
         type uint64;
         description "Packets discarded because of stack underflow";
       }
       leaf stack-overflow-discard {
         type uint64;
         description "Packets discarded because of stack overflow";
       }
       leaf bad-route-discard {
         type uint64;
         description "Packets discarded because of bad route";
       }
       leaf nexthop-discard {
         type uint64;
         description "Packets discarded because of an extended or illegal nexthop";
       }
       leaf invalid-iif-discard {
         type uint64;
         description "Packets coming in through an invalid interface";
       }
       leaf info-cell-discard {
         type uint64;
         description "Number of discarded info-cells";
       }
       leaf fabric-discard {
         type uint64;
         description "Number of packets discarded by the fabric";
       }
       leaf unicast-eapol-discard {
         type uint64;
         description "EAPOL packets with unicast destimation MAC";
       }
     }
     container pfe-chip-statistics {
       leaf input-checksum {
         type uint64;
         description "Packets having input checksum error";
       }
       leaf output-mtu {
         type uint64;
         description "Packets having output mtu error";
       }
     }
     container pfe-bandwidth-statistics-detail {
       leaf pfe-configured-bandwidth-unlimited {
         type string;
         description "Configured transmit bandwidth of the pfe";
       }
       leaf pfe-configured-bandwidth {
         type uint64;
         description "Configured transmit bandwidth of the pfe";
       }
       leaf pfe-bandwidth {
         type uint64;
         description "Current transmit bandwidth of the pfe";
       }
       leaf pfe-average-bandwidth {
         type uint64;
         description "Average transmit bandwidth of the pfe";
       }
     }
     container pfe-lpbk-stream-statistics {
       leaf lpbk-packets {
         type uint64;
         description "Packet Forwarding Engine loopback stream cumulative packets";
       }
       leaf lpbk-pps {
         type uint64;
         description "Packet Forwarding Engine loopback stream packets (per second)";
       }
       leaf lpbk-bytes {
         type uint64;
         description "Packet Forwarding Engine loopback stream cumulative bytes";
       }
       leaf lpbk-bps {
         type uint64;
         description "Packet Forwarding Engine loopback stream bits (per second)";
       }
       leaf lpbk-drop-packets {
         type uint64;
         description "Packet Forwarding Engine loopback stream cumulative drop packets";
       }
       leaf lpbk-drop-pps {
         type uint64;
         description "Packet Forwarding Engine loopback stream drop packets (per second)";
       }
       leaf lpbk-drop-bytes {
         type uint64;
         description "Packet Forwarding Engine loopback stream cumulative drop bytes";
       }
       leaf lpbk-drop-bps {
         type uint64;
         description "Packet Forwarding Engine loopback stream drop bits (per second)";
       }
     }
   }
   grouping pfe-stats-error-block {
     leaf pfe-indx {
       type uint64;
       description "Pfe instance";
     }
     leaf error-element-name {
       type string;
     }
     leaf counter {
       type uint64;
       description "Error stats counter";
     }
   }
 }
