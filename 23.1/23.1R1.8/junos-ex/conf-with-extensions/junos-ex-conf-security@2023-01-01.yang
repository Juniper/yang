/*
 * Copyright (c) 2023 Juniper Networks, Inc.
 * All rights reserved.
 */
 module junos-ex-conf-security {
   namespace "http://yang.juniper.net/junos-ex/conf/security";

   prefix jc-security;

   import junos-common-ddl-extensions {
     prefix junos;
     revision-date 2023-01-01;
   }

   import junos-common-types {
     prefix jt;
     revision-date 2023-01-01;
   }

   import junos-ex-conf-root {
     prefix jc;
     revision-date 2023-01-01;
   }

   organization "Juniper Networks, Inc.";

   contact "yang-support@juniper.net";

   description "Junos security configuration module";

   revision 2023-01-01 {
     description "Junos: 23.1R1.8";
   }

   augment /jc:configuration {
     uses security-group;
   }
   augment /jc:configuration/jc:groups {
     uses security-group;
   }
   grouping security-group {
     container security {
       description "Security configuration";
       uses apply-advanced;
       container alarms {
         description "Configure security alarms";
         uses apply-advanced;
         container audible {
           presence "enable audible";
           description "Beep when new security alarms arrive";
           uses apply-advanced;
           leaf continuous {
             description "Keep beeping until all security alarms have been cleared";
             type empty;
           }
         }
         container potential-violation {
           description "Configure potential security violations";
           uses apply-advanced;
           leaf authentication {
             description "Raise alarm for specified number of authentication failures";
             type union {
               type string {
                 pattern "<.*>|$.*";
               }
               type uint32 {
                 range "2 .. 10";
               }
             }
           }
           leaf cryptographic-self-test {
             description "Raise alarm for cryptographic self test failures";
             type empty;
           }
           leaf key-generation-self-test {
             description "Raise alarm for key generation self test failures";
             type empty;
           }
           leaf non-cryptographic-self-test {
             description "Raise alarm for non-cryptographic self test failures";
             type empty;
           }
           container policy {
             description "Raise alarm for flow policy violations";
           }
           container replay-attacks {
             presence "enable replay-attacks";
             description "No. of Replay attacks before which an alarm needs to be raised";
             uses apply-advanced;
             leaf threshold {
               description "Replay threshold value";
               default "1000";
               type union {
                 type string {
                   pattern "<.*>|$.*";
                 }
                 type uint32 {
                   range "1 .. 1000000000";
                 }
               }
             }
           }
           leaf security-log-percent-full {
             description "Raise alarm when security log exceeds this percent capacity";
             type union {
               type string {
                 pattern "<.*>|$.*";
               }
               type uint8 {
                 range "0 .. 100";
               }
             }
           }
         }
       }
       container log {
         description "Configure auditable security logs";
         uses log-object;
       }
       container certificates {
         description "X.509 certificate configuration";
         uses apply-advanced;
         list local {
           key name;
           ordered-by user;
           description "Local X.509 certificate configuration";
           uses certificate-object;
         }
         leaf path-length {
           description "Maximum certificate path length";
           default "15";
           type union {
             type string {
               pattern "<.*>|$.*";
             }
             type uint32 {
               range "0 .. 15";
             }
           }
         }
         leaf maximum-certificates {
           description "Maximum number of certificates to cache";
           default "1024";
           type union {
             type string {
               pattern "<.*>|$.*";
             }
             type uint32 {
               range "64 .. 4294967295";
             }
           }
         }
         leaf cache-size {
           description "Maximum size of certificate cache";
           units "bytes";
           type string;
         }
         leaf cache-timeout-negative {
           description "Time in seconds to cache negative responses";
           default "20";
           type union {
             type string {
               pattern "<.*>|$.*";
             }
             type uint32 {
               range "10 .. 4294967295";
             }
           }
         }
         leaf enrollment-retry {
           description "Number of retry attempts for an enrollment request";
           type union {
             type string {
               pattern "<.*>|$.*";
             }
             type uint32 {
               range "0 .. 1080";
             }
           }
         }
         list certification-authority {
           key name;
           ordered-by user;
           description "CA X.509 certificate configuration";
           leaf name {
             description "CA profile name";
             junos:cli-feature "nokeyword";
             type string {
               junos:posix-pattern "^.{1,32}$";
               junos:pattern-message "Must be string of 32 characters or less";
             }
           }
           uses apply-advanced;
           leaf ca-name {
             description "CA name";
             type string;
           }
           leaf file {
             description "File to read certificate from";
             type string;
           }
           leaf crl {
             description "File to read crl from";
             type string;
           }
           leaf enrollment-url {
             description "URL";
             type string;
           }
           leaf ldap-url {
             description "URL";
             type string;
           }
           leaf encoding {
             description "Encoding to use for certificate or CRL on disk";
             default "binary";
             type enumeration {
               enum "binary" {
                 description "DER encoding";
               }
               enum "pem" {
                 description "Privacy-enhanced-mail encoding, base64";
               }
             }
           }
         }
       }
       container authentication-key-chains {
         description "Authentication key chain configuration";
         uses security-authentication-key-chains;
       }
       container ssh-known-hosts {
         description "SSH known host list";
         uses apply-advanced;
         list host {
           key name;
           ordered-by user;
           description "SSH known host entry";
           leaf name {
             description "Host name";
             junos:cli-feature "nokeyword";
             type string;
           }
           uses apply-advanced;
           leaf rsa1-key {
             description "Base64 encoded RSA key (protocol version 1)";
             type string;
           }
           leaf rsa-key {
             description "Base64 encoded RSA key";
             type string;
           }
           leaf dsa-key {
             description "Base64 encoded DSA key";
             type string;
           }
           leaf ecdsa-key {
             description "Base64 encoded ECDSA key";
             status deprecated;
             type string;
           }
           leaf ecdsa-sha2-nistp256-key {
             description "Base64 encoded ECDSA-SHA2-NIST256 key";
             type string;
           }
           leaf ecdsa-sha2-nistp384-key {
             description "Base64 encoded ECDSA-SHA2-NIST384 key";
             type string;
           }
           leaf ecdsa-sha2-nistp521-key {
             description "Base64 encoded ECDSA-SHA2-NIST521 key";
             type string;
           }
           leaf ed25519-key {
             description "Base64 encoded ED25519 key";
             type string;
           }
         }
       }
       container pki {
         description "PKI service configuration";
         presence "enable pki";
         uses security-pki;
       }
       container group-vpn {
         description "Group VPN configuration";
         uses security-group-vpn;
       }
       container traceoptions {
         description "Trace options for IPSec key management";
         uses security-traceoptions;
       }
       container ipsec {
         description "IPSec configuration";
         uses security-ipsec-vpn;
       }
       container ike {
         description "IKE configuration";
         uses security-ike;
       }
       container macsec {
         description "MAC Security configuration";
         uses security-macsec;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
     }
   }
   grouping certificate-object {
     leaf name {
       description "Simple name to identify this certificate";
       junos:cli-feature "nokeyword";
       type string;
     }
     uses apply-advanced;
     leaf certificate {
       description "Certificate and private key string";
       junos:cli-feature "nokeyword";
       type string;
     }
   }
   grouping log-object {
     description "Configure auditable security logs";
     uses apply-advanced;
     list exclude {
       key name;
       ordered-by user;
       junos:cli-feature "homogeneous";
       description "List of security log criteria to exclude from the audit log";
       status deprecated;
       leaf name {
         description "Exclude criteria name";
         junos:cli-feature "nokeyword";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         junos:cli-feature "homogeneous";
         description "List of security log criteria to exclude from the audit log";
         junos:must "(!(\".. .. exclude\"))";
         junos:must-message "'security log cache exclude' and 'security log exclude' are mutually exclusive";
         leaf name {
           description "Exclude criteria name";
           junos:cli-feature "nokeyword";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         junos:must "(!(\".. .. limit\"))";
         junos:must-message "'security log cache limit' and 'security log limit' are mutually exclusive";
         type union {
           type uint32;
           type string {
             pattern "<.*>|$.*";
           }
         }
       }
     }
   }
   grouping macro-data-type {
     leaf name {
       description "Keyword part of the keyword-value pair";
       junos:cli-feature "nokeyword";
       type string;
     }
     leaf value {
       description "Value part of the keyword-value pair";
       junos:cli-feature "nokeyword";
       type string;
     }
   }
   grouping security-authentication-key-chains {
     uses apply-advanced;
     list key-chain {
       key name;
       description "Key chain configuration";
       leaf name {
         description "Name of authentication key chain";
         junos:cli-feature "nokeyword";
         type string {
           junos:posix-pattern "!^((__.*__)|(.*[ ].*)|(.{33,}))$";
           junos:pattern-message "Must be string of 32 characters or less with no spaces";
         }
       }
       uses apply-advanced;
       leaf description {
         description "Text description of this authentication-key-chain";
         type string {
           length "1 .. 80";
         }
       }
       leaf tolerance {
         description "Clock skew tolerance";
         default "3600";
         units "seconds";
         type union {
           type string {
             pattern "<.*>|$.*";
           }
           type uint32 {
             range "0 .. 4294967295";
           }
         }
       }
       list key {
         key name;
         description "Authentication element configuration";
         leaf name {
           description "Authentication element identifier";
           junos:cli-feature "nokeyword";
           type union {
             type string {
               pattern "<.*>|$.*";
             }
             type uint32 {
               range "0 .. 63";
             }
           }
         }
         uses apply-advanced;
         leaf secret {
           description "Authentication key";
           type string {
             length "1 .. 126";
           }
         }
         leaf key-name {
           description "Key name in hexadecimal format used for macsec";
           type string {
             length "2 .. 64";
             junos:posix-pattern "^([0-9a-fA-F][0-9a-fA-F]){1,32}$";
             junos:pattern-message "Must be an even-length string up to 64 hexadecimal digits (0-9, a-f, A-F)";
           }
         }
         leaf start-time {
           description "Start time for key transmission (YYYY-MM-DD.HH:MM)";
           type jt:time;
         }
         leaf algorithm {
           description "Authentication algorithm";
           default "md5";
           type enumeration {
             enum "md5" {
               description "Message Digest 5";
             }
             enum "hmac-sha-1" {
               description "Hash-based Message Authentication Code (SHA1) (96 bits)";
               junos:must "(\".. options isis-enhanced\")";
               junos:must-message "sha algorithm required isis-enhanced";
             }
             enum "ao" {
               description "TCP Authentication Option";
             }
             enum "sha-1" {
               description "SHA1";
               junos:must "(\".. options isis-enhanced\")";
               junos:must-message "sha algorithm required isis-enhanced";
             }
           }
         }
         leaf fallback {
           description "Fallback authentication algorithm";
           type enumeration {
             enum "hmac-sha-1" {
               description "Hash-based Message Authentication
                        Code (SHA1) (96 bits)";
               junos:must "(\".. options isis-enhanced\")";
               junos:must-message "sha algorithm required isis-enhanced";
             }
             enum "sha-1" {
               description "SHA1";
               junos:must "(\".. options isis-enhanced\")";
               junos:must-message "sha algorithm required isis-enhanced";
             }
           }
         }
         leaf options {
           description "Protocol's transmission encoding format";
           default "basic";
           type enumeration {
             enum "basic" {
               description "Rudimentary encoding format";
             }
             enum "isis-enhanced" {
               description "RFC 5310 based encoding";
             }
           }
         }
         container ao-attribute {
           junos:must "(!(\".. authentication-key\"))";
           junos:must-message "Cannot be configured with authentication-key";
           junos:must "(\".. algorithm ao\")";
           junos:must-message "Can only be configured with authentication-algorithm ao";
           description "TCP Authentication option attributes";
           uses apply-advanced;
           leaf send-id {
             description "Send id for TCP-AO entry";
             type union {
               type string {
                 pattern "<.*>|$.*";
               }
               type uint32 {
                 range "0 .. 255";
               }
             }
           }
           leaf recv-id {
             description "Recv id for TCP-AO entry";
             type union {
               type string {
                 pattern "<.*>|$.*";
               }
               type uint32 {
                 range "0 .. 255";
               }
             }
           }
           leaf tcp-ao-option {
             description "Include TCP-AO option within message header";
             default "disabled";
             type enumeration {
               enum "enabled" {
                 description "Include the TCP-AO option";
               }
               enum "disabled" {
                 description "Not include the TCP-AO option";
               }
             }
           }
           leaf cryptographic-algorithm {
             description "Cryptographic algorithm for TCP-AO Traffic key and MAC digest generation";
             default "hmac-sha-1-96";
             type enumeration {
               enum "hmac-sha-1-96" {
                 description "Hash-based Message Authentication Code (SHA1) (96 bits)";
               }
               enum "aes-128-cmac-96" {
                 description "Cipher-based Message Authentication Code (AES128) (96 bits)";
               }
             }
           }
         }
       }
     }
   }
   grouping security-group-vpn {
     uses apply-advanced;
     container member {
       description "Group VPN member configuration";
       uses gvpn-member;
     }
   }
   grouping gvpn-member {
     uses apply-advanced;
     container ike {
       description "Group VPN IKE configuration";
       uses gvpn-member-ike;
     }
     container ipsec {
       description "Group VPN IPsec configuration";
       uses gvpn-member-ipsec-vpn;
     }
   }
   grouping gvpn-member-ike {
     uses apply-advanced;
     container traceoptions {
       description "Trace options for Group VPN Member";
       uses apply-advanced;
       leaf no-remote-trace {
         description "Disable remote tracing";
         junos:must "(\"system tracing\")";
         junos:must-message "'no-remote-trace' is valid only when [system tracing] is configured";
         type empty;
       }
       container file {
         junos:cli-feature "oneliner";
         description "Trace file information";
         leaf filename {
           description "Name of file in which to write trace information";
           junos:cli-feature "nokeyword";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         junos:cli-feature "oneliner";
         description "Tracing parameters";
         leaf name {
           junos:cli-feature "nokeyword";
           type enumeration {
             enum "timer" {
               description "Trace internal timer events";
             }
             enum "routing-socket" {
               description "Trace routing socket messages";
             }
             enum "parse" {
               description "Trace configuration processing";
             }
             enum "config" {
               description "Trace configuration download processing";
             }
             enum "ike" {
               description "Trace IKE module processing";
             }
             enum "policy-manager" {
               description "Trace policy manager processing";
             }
             enum "general" {
               description "Trace general events";
             }
             enum "database" {
               description "Trace security associations database events";
             }
             enum "certificates" {
               description "Trace certificate events";
             }
             enum "snmp" {
               description "Trace SNMP operations";
             }
             enum "thread" {
               description "Trace thread processing";
             }
             enum "high-availability" {
               description "Trace high-availability operations";
             }
             enum "next-hop-tunnels" {
               description "Trace next-hop-tunnels operations";
             }
             enum "all" {
               description "Trace everything";
             }
           }
         }
       }
       container gateway-filter {
         description "Set gateway filter for trace";
         uses apply-advanced;
         leaf local-address {
           description "Use an IP address to identify the local gateway";
           type jt:ipv4addr;
         }
         leaf remote-address {
           description "Use an IP address to identify the remote gateway";
           type jt:ipv4addr;
         }
       }
     }
     list proposal {
       key name;
       ordered-by user;
       description "Define an IKE proposal";
       uses gvpn-member-ike-proposal;
     }
     list policy {
       key name;
       ordered-by user;
       description "Define an IKE policy";
       uses gvpn-ike-policy;
     }
     list gateway {
       key name;
       ordered-by user;
       description "Define an IKE gateway";
       leaf name {
         description "Label for the remote (peer) gateway";
         junos:cli-feature "nokeyword";
         junos:must "(!(\"security ike gateway $$\"))";
         junos:must-message "Gateway already defined under [security ike]";
         type string {
           length "1 .. 32";
         }
       }
       uses apply-advanced;
       leaf ike-policy {
         description "Name of the IKE policy";
         junos:must "(!(\"security ike policy $$\"))";
         junos:must-message "Policy already defined under [security ike]";
         junos:must "(\"security group-vpn member ike policy $$\")";
         junos:must-message "Referenced IKE policy must be defined under [edit security group-vpn member ike policy]";
         type string {
           length "1 .. 32";
         }
       }
       container local-identity {
         junos:cli-feature "oneliner";
         description "Set the local IKE identity";
         choice identity-type {
           case case_1 {
             container inet {
               description "Use an IPv4 address";
               uses apply-advanced;
               leaf identity-ipv4 {
                 description "The local IPv4 identity";
                 junos:cli-feature "nokeyword";
                 type jt:ipv4addr;
               }
             }
           }
           case case_2 {
             container hostname {
               description "Use a fully-qualified domain name";
               uses apply-advanced;
               leaf identity-hostname {
                 description "The local hostname";
                 junos:cli-feature "nokeyword";
                 type string;
               }
             }
           }
           case case_3 {
             container user-at-hostname {
               description "Use an e-mail address";
               uses apply-advanced;
               leaf identity-user {
                 description "The local user-FQDN";
                 junos:cli-feature "nokeyword";
                 type string;
               }
             }
           }
           case case_4 {
             leaf distinguished-name {
               description "Use a distinguished name specified in local certificate";
               type empty;
             }
           }
         }
       }
       leaf local-address {
         description "Local IPv4 address for group member";
         junos:must "(!(any \"security group-vpn member ike gateway <*> server-address $$\"))";
         junos:must-message "Member can not have the same local address as server";
         type jt:ipv4addr;
       }
       leaf routing-instance {
         description "Name of routing instance that hosts local address";
         default "default";
         junos:must "(\"routing-instances $$\")";
         junos:must-message "Referenced routing-instance must be defined";
         type string;
       }
     }
   }
   grouping gvpn-ike-policy {
     leaf name {
       description "Name of policy";
       junos:cli-feature "nokeyword";
       junos:must "((\".. proposals\" || \".. proposal-set\"))";
       junos:must-message "IKE policy must have either proposals or proposal-set configured";
       junos:must "(((\".. certificate local-certificate\" || \".. pre-shared-key\") && !((\".. certificate local-certificate\" && \".. pre-shared-key\"))))";
       junos:must-message "IKE policy must have either local certificate or pre-shared key configured";
       junos:must "(!(\"security ike policy $$\"))";
       junos:must-message "Policy already defined under [security ike policy]";
       type string {
         length "1 .. 32";
       }
     }
     uses apply-advanced;
     leaf mode {
       description "Define the IKE mode for Phase 1";
       default "main";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       junos:cli-feature "nokeyword";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     container certificate {
       description "Certificate configuration";
       uses apply-advanced;
       leaf local-certificate {
         description "Local certificate identifier";
         type string {
           junos:posix-pattern "^.{1,32}$";
           junos:pattern-message "Must be string of 32 characters or less";
         }
       }
       container trusted-ca {
         junos:cli-feature "oneliner";
         description "Specify the CA to use";
         status deprecated;
         choice ca {
           case case_1 {
             leaf ca-index {
               description "Index of the preferred CA to use";
               junos:cli-feature "nokeyword";
               type union {
                 type uint32;
                 type string {
                   pattern "<.*>|$.*";
                 }
               }
             }
           }
           case case_2 {
             leaf use-all {
               description "Use all configured CAs";
               type empty;
             }
           }
         }
       }
       leaf peer-certificate-type {
         description "Preferred type of certificate from peer";
         default "x509-signature";
         type enumeration {
           enum "pkcs7" {
             description "PKCS7 encoding";
           }
           enum "x509-signature" {
             description "X509 signature encoding";
           }
         }
       }
     }
     leaf proposal-set {
       description "Types of default IKE proposal-set";
       type enumeration {
         enum "basic" {
           description "IKE proposal-set for basic";
           junos:must "(!(\".. proposals\"))";
           junos:must-message "IKE policy must not have both proposals and proposal-set configured";
         }
         enum "compatible" {
           description "IKE proposal-set for compatible";
           junos:must "(!(\".. proposals\"))";
           junos:must-message "IKE policy must not have both proposals and proposal-set configured";
         }
         enum "standard" {
           description "IKE proposal-set for standard";
           junos:must "(!(\".. proposals\"))";
           junos:must-message "IKE policy must not have both proposals and proposal-set configured";
         }
       }
     }
     container pre-shared-key {
       junos:cli-feature "oneliner";
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping gvpn-member-ike-proposal {
     leaf name {
       description "Name of the IKE proposal";
       junos:cli-feature "nokeyword";
       junos:must "(!(\"security ike proposal $$\"))";
       junos:must-message "Proposal already defined under [security ike proposal]";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
       }
     }
     leaf dh-group {
       description "Define Diffie-Hellman group";
       type enumeration {
         enum "group1" {
           description "Diffie-Hellman Group 1";
         }
         enum "group2" {
           description "Diffie-Hellman Group 2";
         }
         enum "group5" {
           description "Diffie-Hellman Group 5";
         }
         enum "group14" {
           description "Diffie-Hellman Group 14";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       default "180";
       units "seconds";
       type union {
         type string {
           pattern "<.*>|$.*";
         }
         type uint32 {
           range "180 .. 86400";
         }
       }
     }
   }
   grouping gvpn-member-ipsec-vpn {
     uses apply-advanced;
     list vpn {
       key name;
       ordered-by user;
       description "Define an IPSec VPN";
       uses ipsec-gvpn-member-template;
     }
   }
   grouping ipsec-gvpn-member-template {
     description "Configure a Group VPN";
     leaf name {
       description "Name of the VPN";
       junos:cli-feature "nokeyword";
       junos:must "(!(\"security ipsec vpn $$\"))";
       junos:must-message "VPN already defined under [security ipsec]";
       type string {
         length "1 .. 32";
       }
     }
     uses apply-advanced;
     leaf ike-gateway {
       description "Name of IKE gateway";
       junos:must "(\"security group-vpn member ike gateway $$\")";
       junos:must-message "Referenced IKE gateway must be defined under [edit security group-vpn member ike gateway]";
       type string {
         length "1 .. 32";
       }
     }
     leaf group {
       description "Enable Group VPN by defining group id";
       junos:must "((\".. no-group-check\" || unique \"security group-vpn member ipsec vpn <*> group $$\"))";
       junos:must-message "Group id must be unique among group vpns";
       type union {
         type string {
           pattern "<.*>|$.*";
         }
         type uint32 {
           range "1 .. 65535";
         }
       }
     }
     leaf match-direction {
       description "Direction for which the rule match is applied";
       type enumeration {
         enum "input" {
           description "Match on input to interface";
         }
         enum "output" {
           description "Match on output from interface";
         }
       }
     }
     leaf tunnel-mtu {
       description "Maximum transmit packet size";
       default "1500";
       type union {
         type string {
           pattern "<.*>|$.*";
         }
         type uint32 {
           range "256 .. 9192";
         }
       }
     }
     leaf df-bit {
       description "Specifies how to handle the Don't Fragment bit";
       default "clear";
       type enumeration {
         enum "clear" {
           description "Clear DF bit of outer header";
         }
         enum "set" {
           description "Set DF bit of outer header";
         }
         enum "copy" {
           description "Copy DF bit from inner header";
         }
       }
     }
     leaf forward-policy-mismatch {
       description "Enables forwarding of policy mismatch packets";
       type empty;
     }
     container fail-open {
       description "List of fail open rules";
       uses ipsec_gvpn_fail_open_rule_object;
     }
   }
   grouping ipsec_gvpn_fail_open_rule_object {
     uses apply-advanced;
     list rule {
       key name;
       ordered-by user;
       description "Define fail open rules upto 10";
       max-elements 10;
       uses ipsec_gvpn_rule_address_object;
     }
   }
   grouping ipsec_gvpn_rule_address_object {
     leaf name {
       description "Rule name";
       junos:cli-feature "nokeyword";
       type string {
         length "1 .. 63";
         junos:posix-pattern "^[[:alnum:]][[:alnum:]_-]*$";
         junos:pattern-message "Must be a string beginning with a number or letter and consisting of letters, numbers, dashes and underscores.";
       }
     }
     uses apply-advanced;
     container source-address {
       description "Match IP source address";
       presence "enable source-address";
       uses ipsec_gvpn_addr_object;
     }
     container destination-address {
       description "Match IP destination address";
       presence "enable destination-address";
       uses ipsec_gvpn_addr_object;
     }
   }
   grouping ipsec_gvpn_addr_object {
     uses apply-advanced;
     leaf address {
       description "Prefix to match";
       junos:cli-feature "nokeyword";
       type jt:ipv4prefix-only;
     }
   }
   grouping security-ike {
     uses apply-advanced;
     container traceoptions {
       description "Trace options for IPSec key management";
       uses security-traceoptions;
     }
     container respond-bad-spi {
       presence "enable respond-bad-spi";
       junos:cli-feature "oneliner";
       description "Respond to IPSec packets with bad SPI values";
       leaf max-responses {
         description "Maximum number of times to respond";
         junos:cli-feature "nokeyword";
         default "5";
         type union {
           type string {
             pattern "<.*>|$.*";
           }
           type uint32 {
             range "1 .. 30";
           }
         }
       }
     }
     list proposal {
       key name;
       ordered-by user;
       description "Define an IKE proposal";
       uses ike-proposal;
     }
     list policy {
       key name;
       ordered-by user;
       description "Define an IKE policy";
       uses ike-policy;
     }
     list gateway {
       key name;
       ordered-by user;
       description "Define an IKE gateway";
       leaf name {
         description "Label for the remote (peer) gateway";
         junos:cli-feature "nokeyword";
         type string {
           length "1 .. 32";
         }
       }
       uses apply-advanced;
       leaf ike-policy {
         description "Name of the IKE policy";
         junos:must "(!((\"security ike policy $$ mode main\" && (\"security ike policy $$ pre-shared-key\" && \".. dynamic\"))))";
         junos:must-message "Main mode for dynamic peer with Preshared key based authentication is not allowed";
         junos:must "(\"security ike policy $$\")";
         junos:must-message "Referenced IKE policy must be defined under [edit security ike policy]";
         type string {
           length "1 .. 32";
         }
       }
       choice remote-identifier {
         case case_1 {
           leaf-list address {
             ordered-by user;
             description "Addresses or hostnames of peer:1 primary, upto 4 backups";
             type string;
           }
         }
         case case_2 {
           container dynamic {
             junos:cli-feature "oneliner-plus";
             description "Site to site peer with dynamic IP address";
             uses apply-advanced;
             choice remote-id-type {
               case case_1 {
                 container distinguished-name {
                   presence "enable distinguished-name";
                   description "Use a distinguished name: ";
                   uses apply-advanced;
                   choice name-type {
                     case case_1 {
                       leaf container {
                         description "Specify the container string";
                         type string;
                       }
                     }
                     case case_2 {
                       leaf wildcard {
                         description "Specify the wildcard string";
                         type string;
                       }
                     }
                   }
                 }
               }
               case case_2 {
                 leaf hostname {
                   description "Use a fully-qualified domain name";
                   type string;
                 }
               }
               case case_3 {
                 leaf inet {
                   description "Use an IPV4 address to identify the dynamic peer";
                   type jt:ipv4addr;
                 }
               }
               case case_4 {
                 leaf inet6 {
                   description "Use an IPV6 address to identify the dynamic peer";
                   type jt:ipv6addr;
                 }
               }
               case case_5 {
                 leaf user-at-hostname {
                   description "Use an e-mail address";
                   type string;
                 }
               }
             }
             leaf connections-limit {
               description "Maximum number of users connected to gateway";
               type union {
                 type uint32;
                 type string {
                   pattern "<.*>|$.*";
                 }
               }
             }
             leaf ike-user-type {
               description "Type of the IKE ID";
               type enumeration {
                 enum "group-ike-id" {
                   description "Email address or FQDN shared as IKED ID by multiple users";
                 }
                 enum "shared-ike-id" {
                   description "Email address shared as IKED ID by multiple users";
                   junos:must "(\" .. .. xauth\")";
                   junos:must-message "Need to configure xauth at [edit security ike gateway]";
                 }
               }
             }
           }
         }
       }
       container dead-peer-detection {
         presence "enable dead-peer-detection";
         junos:cli-feature "oneliner-plus";
         description "Enable RFC-3706 DPD";
         uses apply-advanced;
         leaf always-send {
           description "Send DPD messages periodically, regardless of traffic";
           type empty;
         }
         leaf interval {
           description "The interval at which to send DPD messages";
           default "10";
           units "seconds";
           type union {
             type string {
               pattern "<.*>|$.*";
             }
             type uint32 {
               range "10 .. 60";
             }
           }
         }
         leaf threshold {
           description "Maximum number of DPD retransmissions";
           default "5";
           type union {
             type string {
               pattern "<.*>|$.*";
             }
             type uint32 {
               range "1 .. 5";
             }
           }
         }
       }
       leaf no-nat-traversal {
         description "Disable IPSec NAT traversal";
         type empty;
       }
       leaf nat-keepalive {
         description "Interval at which to send NAT keepalives";
         default "5";
         units "seconds";
         type union {
           type string {
             pattern "<.*>|$.*";
           }
           type uint32 {
             range "1 .. 300";
           }
         }
       }
       container local-identity {
         junos:cli-feature "oneliner";
         description "Set the local IKE identity";
         choice identity-type {
           case case_1 {
             container inet {
               description "Use an IPv4 address";
               uses apply-advanced;
               leaf identity-ipv4 {
                 description "The local IPv4 identity";
                 junos:cli-feature "nokeyword";
                 type jt:ipv4addr;
               }
             }
           }
           case case_2 {
             container inet6 {
               description "Use an IPv6 address";
               uses apply-advanced;
               leaf identity-ipv6 {
                 description "The local IPv6 identity";
                 junos:cli-feature "nokeyword";
                 type jt:ipv6addr;
               }
             }
           }
           case case_3 {
             container hostname {
               description "Use a fully-qualified domain name";
               uses apply-advanced;
               leaf identity-hostname {
                 description "The local hostname";
                 junos:cli-feature "nokeyword";
                 type string;
               }
             }
           }
           case case_4 {
             container user-at-hostname {
               description "Use an e-mail address";
               uses apply-advanced;
               leaf identity-user {
                 description "The local user-FQDN";
                 junos:cli-feature "nokeyword";
                 type string;
               }
             }
           }
           case case_5 {
             leaf distinguished-name {
               description "Use a distinguished name specified in local certificate";
               type empty;
             }
           }
         }
       }
       container remote-identity {
         junos:must "(!(\".. dynamic\"))";
         junos:must-message "Since the remote gateway is dynamic, Define remote identity under dynamic";
         junos:cli-feature "oneliner";
         description "Set the remote IKE identity";
         choice identity-type {
           case case_1 {
             container inet {
               description "Use an IPv4 address";
               uses apply-advanced;
               leaf identity-ipv4 {
                 description "The remote IPv4 identity";
                 junos:cli-feature "nokeyword";
                 type jt:ipv4addr;
               }
             }
           }
           case case_2 {
             container inet6 {
               description "Use an IPv6 address";
               uses apply-advanced;
               leaf identity-ipv6 {
                 description "The remote IPv6 identity";
                 junos:cli-feature "nokeyword";
                 type jt:ipv6addr;
               }
             }
           }
           case case_3 {
             container hostname {
               description "Use a fully-qualified domain name";
               uses apply-advanced;
               leaf identity-hostname {
                 description "The remote hostname";
                 junos:cli-feature "nokeyword";
                 type string;
               }
             }
           }
           case case_4 {
             container user-at-hostname {
               description "Use an e-mail address";
               uses apply-advanced;
               leaf identity-user {
                 description "The remote user-FQDN";
                 junos:cli-feature "nokeyword";
                 type string;
               }
             }
           }
           case case_5 {
             container distinguished-name {
               presence "enable distinguished-name";
               description "Use a distinguished name: ";
               uses apply-advanced;
               leaf container {
                 description "Specify the container string";
                 type string;
               }
               leaf wildcard {
                 description "Specify the wildcard string";
                 type string;
               }
             }
           }
         }
       }
       leaf external-interface {
         description "External interface for IKE negotiations";
         junos:must "(!(\"interfaces $$ family bridge\"))";
         junos:must-message "Bridge interface is not allowed as external-interface";
         junos:must "(\"interfaces $$-IFL\")";
         junos:must-message "Referenced interface must be configured under [edit interfaces] hierarchy";
         type union {
           type jt:interface-unit;
           type string {
             pattern "<.*>|$.*";
           }
         }
       }
       container xauth {
         junos:cli-feature "oneliner";
         description "Use extended authentication";
         leaf access-profile {
           description "Access profile that contains authentication information";
           junos:must "(\"access profile $$\")";
           junos:must-message "profile needs to be configured";
           type string;
         }
       }
       leaf general-ikeid {
         description "Accept peer IKE-ID in general";
         junos:must "(!(\".. remote-identity\"))";
         junos:must-message "general-ikeid option is not allowed when remote-identity is configured";
         junos:must "(!(\".. dynamic\"))";
         junos:must-message "general-ikd-id option is not available for dynamic peer.";
         type empty;
       }
       leaf version {
         description "Negotiate using either IKE v1 or IKE v2 protocol";
         default "v1-only";
         type enumeration {
           enum "v1-only" {
             description "The connection must be initiated using IKE version 1";
           }
           enum "v2-only" {
             description "The connection must be initiated using IKE version 2";
           }
         }
       }
     }
   }
   grouping ike-policy {
     leaf name {
       description "IKE peer address";
       junos:cli-feature "nokeyword";
       junos:must "((\"security ike policy $$ pre-shared-key\" || \"security ike policy $$ local-certificate\"))";
       junos:must-message "Either pre-shared-key or local-certificate must be configured in ike policy";
       type jt:ipv4addr;
     }
     uses apply-advanced;
     leaf mode {
       description "Define the IKE first phase mode";
       type enumeration {
         enum "main" {
           description "Main mode";
         }
         enum "aggressive" {
           description "Aggressive mode";
         }
       }
     }
     leaf description {
       description "Text description of IKE policy";
       type string {
         length "1 .. 80";
       }
     }
     leaf-list proposals {
       ordered-by user;
       description "Name of the proposal";
       junos:cli-feature "nokeyword";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     leaf local-certificate {
       description "File to read certificate from";
       junos:must "(!(\".. local-key-pair $$\"))";
       junos:must-message "Local certificate and local key pair files must be different";
       type string {
         length "1 .. 255";
       }
     }
     leaf local-key-pair {
       description "File to read key-pair from";
       type string {
         length "1 .. 255";
       }
     }
     leaf encoding {
       description "Encoding to use for certificate or CRL on disk";
       default "binary";
       type enumeration {
         enum "binary" {
           description "DER encoding";
         }
         enum "pem" {
           description "Privacy-enhanced-mail encoding, base64";
         }
       }
     }
     leaf identity {
       description "Define the remote certificate name";
       type string {
         length "1 .. 32";
       }
     }
     container pre-shared-key {
       junos:cli-feature "oneliner";
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
               junos:posix-pattern "^[[:xdigit:]]+$";
               junos:pattern-message "Must be hexadecimal digits (0-9, a-f, A-F)";
             }
           }
         }
       }
     }
   }
   grouping ike-proposal {
     leaf name {
       description "Name of the IKE proposal";
       junos:cli-feature "nokeyword";
       junos:must "(((\"services ipsec-vpn ike proposal $$\" && !(\"security ike proposal $$\")) || (\"security ike proposal $$\" && !(\"services ipsec-vpn ike proposal $$\"))))";
       junos:must-message "Referenced IKE proposal must not be defined both under [edit security ike proposal] and [edit services ipsec-vpn ike proposal]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (254 bit modulus)";
         }
         enum "ecdsa-signatures-384" {
           description "ECDSA signatures (384 bit modulus)";
         }
       }
     }
     leaf dh-group {
       description "Define Diffie-Hellman group";
       type enumeration {
         enum "group1" {
           description "Diffie-Hellman Group1";
         }
         enum "group2" {
           description "Diffie-Hellman Group2";
         }
         enum "group5" {
           description "Diffie-Hellman Group5";
         }
         enum "group14" {
           description "Diffie-Hellman Group14";
         }
         enum "group15" {
           description "Diffie-Hellman Group15";
         }
         enum "group16" {
           description "Diffie-Hellman Group16";
         }
         enum "group19" {
           description "Diffie-Hellman Group19";
         }
         enum "group20" {
           description "Diffie-Hellman Group20";
         }
         enum "group24" {
           description "Diffie-Hellman Group24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping security-ipsec-vpn {
     uses apply-advanced;
     container traceoptions {
       description "Trace options for IPSec data-plane debug";
       uses ipsec-traceoptions;
     }
     container vpn-monitor-options {
       description "Global options for VPN liveliness monitoring";
       presence "enable vpn-monitor-options";
       uses ipsec-vpn-monitor;
     }
     list proposal {
       key name;
       ordered-by user;
       description "Define an IPSec proposal";
       uses ipsec-proposal;
     }
     list policy {
       key name;
       ordered-by user;
       description "Define an IPSec policy";
       uses ipsec-policy;
     }
     list vpn {
       key name;
       ordered-by user;
       description "Define an IPSec VPN";
       uses ipsec-vpn-template;
     }
     list security-association {
       key name;
       ordered-by user;
       description "Define an IPSec security association";
       uses ipsec-sa;
     }
     container internal {
       presence "enable internal";
       description "Define an IPSec SA for internal RE-RE communication";
       uses apply-advanced;
       container security-association {
         description "Define an IPSec security association";
         presence "enable security-association";
         uses ipsec-internal-sa;
       }
     }
     container trusted-channel {
       presence "enable trusted-channel";
       junos:must "(\"security ipsec trusted-channel security-association\")";
       junos:must-message "Must configure trusted-channel security-association";
       description "Define an IPSec SA for trusted-channel communication";
       uses apply-advanced;
       container security-association {
         description "Define an IPSec security association";
         presence "enable security-association";
         uses ipsec-trusted-channel-sa;
       }
       leaf-list port-exclusion-list {
         ordered-by user;
         description "Define port exlusion list";
         junos:must "(\"security ipsec trusted-channel security-association\")";
         junos:must-message "Must configure trusted-channel security-association";
         type union {
           type string {
             pattern "<.*>|$.*";
           }
           type uint32 {
             range "1 .. 65535";
           }
         }
       }
     }
   }
   grouping ipsec-internal-sa {
     uses apply-advanced;
     leaf description {
       description "Text description of internal security association";
       type string {
         length "1 .. 80";
       }
     }
     container manual {
       description "Define a manual security association";
       uses apply-advanced;
       list direction {
         key name;
         ordered-by user;
         description "Define the direction of the security association";
         leaf name {
           junos:cli-feature "nokeyword";
           type enumeration {
             enum "inbound" {
               description "Inbound security association";
               junos:must "(\".. .. direction $$={outbound}\")";
               junos:must-message "Outbound block must be configured";
             }
             enum "outbound" {
               description "Outbound security association";
               junos:must "(\".. .. direction $$={inbound}\")";
               junos:must-message "Inbound block must be configured";
             }
             enum "bidirectional" {
               description "Bidirectional security association";
               junos:must "((!(\".. .. direction $$={inbound}\") && !(\".. .. direction $$={outbound}\")))";
               junos:must-message "Outbound or inbound blocks must not be configured";
             }
           }
         }
         uses apply-advanced;
         leaf protocol {
           description "Define an IPSec protocol for the security association";
           type enumeration {
             enum "ah" {
               description "Authentication header";
               junos:must "(!(\".. encryption\"))";
               junos:must-message "Encryption must not be defined for AH";
               junos:must "(\".. authentication\")";
               junos:must-message "Authentication must be defined for AH";
             }
             enum "esp" {
               description "Encapsulated Security Payload header";
               junos:must "((\".. authentication\" || \".. encryption\"))";
               junos:must-message "Either authentication or encryption must be defined for ESP";
             }
             enum "bundle" {
               description "Bundle (AH authentication plus ESP encryption)";
               junos:must "(\".. auxiliary-spi\")";
               junos:must-message "Auxiliary SPI must be defined for AH plus ESP bundle";
               junos:must "(\".. encryption\")";
               junos:must-message "Encryption must be defined for AH plus ESP bundle";
               junos:must "(\".. authentication\")";
               junos:must-message "Authentication must be defined for AH plus ESP bundle";
             }
           }
         }
         leaf spi {
           description "Define security parameter index";
           type union {
             type string {
               pattern "<.*>|$.*";
             }
             type uint32 {
               range "256 .. 16639";
             }
           }
         }
         leaf auxiliary-spi {
           description "ESP security parameter index for IPSec SA bundle";
           junos:must "(\".. protocol bundle\")";
           junos:must-message "Auxiliary SPI must be configured with protocol bundle only";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
           }
           container key {
             junos:cli-feature "oneliner";
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
           }
           container key {
             junos:cli-feature "oneliner";
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
       }
     }
   }
   grouping ipsec-policy {
     leaf name {
       description "Name of the IPSec policy";
       junos:cli-feature "nokeyword";
       junos:must "(((\"services ipsec-vpn ipsec policy $$\" && !(\"security ipsec policy $$\")) || (\"security ipsec policy $$\" && !(\"services ipsec-vpn ipsec policy $$\"))))";
       junos:must-message "Referenced IPSec policy must not be defined both under [edit security ipsec policy] and [edit services ipsec-vpn ipsec policy]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group1";
           }
           enum "group2" {
             description "Diffie-Hellman Group2";
           }
           enum "group5" {
             description "Diffie-Hellman Group5";
           }
           enum "group14" {
             description "Diffie-Hellman Group14";
           }
           enum "group15" {
             description "Diffie-Hellman Group15";
           }
           enum "group16" {
             description "Diffie-Hellman Group16";
           }
           enum "group19" {
             description "Diffie-Hellman Group19";
           }
           enum "group20" {
             description "Diffie-Hellman Group20";
           }
           enum "group24" {
             description "Diffie-Hellman Group24";
           }
         }
       }
     }
     leaf-list proposals {
       ordered-by user;
       description "Name of the proposal";
       junos:cli-feature "nokeyword";
       junos:must "(\".. .. .. proposal $$\")";
       junos:must-message "Referenced proposal is not defined";
       type string {
         length "1 .. 32";
         junos:posix-pattern "^[[:alnum:]][[:alnum:]_-]*$";
         junos:pattern-message "Must be a string beginning with a number or letter and consisting of letters, numbers, dashes and underscores.";
       }
     }
     leaf proposal-set {
       description "Types of default IPSEC proposal-set";
       type enumeration {
         enum "basic" {
           description "IPSEC basic proposal-set";
           junos:must "(!(\".. proposals\"))";
           junos:must-message "IPSec policy must not have both proposals and proposal-set configured";
         }
         enum "compatible" {
           description "IPSEC compatible proposal-set";
           junos:must "(!(\".. proposals\"))";
           junos:must-message "IPSec policy must not have both proposals and proposal-set configured";
         }
         enum "standard" {
           description "IPSEC standard proposal-set";
           junos:must "(!(\".. proposals\"))";
           junos:must-message "IPSec policy must not have both proposals and proposal-set configured";
         }
       }
     }
   }
   grouping ipsec-proposal {
     leaf name {
       description "Name of the IPSec proposal";
       junos:cli-feature "nokeyword";
       junos:must "(((\"services ipsec-vpn ipsec proposal $$\" && !(\"security ipsec proposal $$\")) || (\"security ipsec proposal $$\" && !(\"services ipsec-vpn ipsec proposal $$\"))))";
       junos:must-message "Referenced IPSec proposal must not be defined both under [edit security ipsec proposal] and [edit services ipsec-vpn ipsec proposal]";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of IPSec proposal";
       type string {
         length "1 .. 80";
       }
     }
     leaf protocol {
       description "Define an IPSec protocol for the proposal";
       type enumeration {
         enum "ah" {
           description "Authentication header";
           junos:must "(!(\".. encryption-algorithm\"))";
           junos:must-message "Encryption algorithm must not be defined for AH";
         }
         enum "esp" {
           description "Encapsulated Security Payload header";
         }
         enum "bundle" {
           description "Bundle (AH authentication plus ESP encryption)";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
           junos:must "(\".. .. .. .. ipsec-vpn\")";
           junos:must-message "hmac-sha-256-128 algorithm is not supported for IKE and IPSec configuration in security hierarchy";
         }
         enum "hmac-sha-256-96" {
           description "HMAC-SHA-256-96 authentication algorithm (non-RFC compliant)";
         }
         enum "hmac-sha2-256" {
           description "HMAC-SHA2-256 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm with 16 octet ICV";
           junos:must "(!(\".. authentication-algorithm\"))";
           junos:must-message "HMAC Authentication is not compatible with AES-GCM";
         }
         enum "aes-192-gcm" {
           description "AES-GCM 192-bit encryption algorithm with 16 octet ICV";
           junos:must "(!(\".. authentication-algorithm\"))";
           junos:must-message "HMAC Authentication is not compatible with AES-GCM";
         }
         enum "aes-256-gcm" {
           description "AES-GCM 256-bit encryption algorithm with 16 octet ICV";
           junos:must "(!(\".. authentication-algorithm\"))";
           junos:must-message "HMAC Authentication is not compatible with AES-GCM";
         }
       }
     }
     leaf lifetime-seconds {
       description "Lifetime, in seconds";
       units "seconds";
       type union {
         type string {
           pattern "<.*>|$.*";
         }
         type uint32 {
           range "180 .. 86400";
         }
       }
     }
   }
   grouping ipsec-sa {
     leaf name {
       description "Name of IPSec security association";
       junos:cli-feature "nokeyword";
       type string {
         length "1 .. 32";
         junos:posix-pattern "^[[:alnum:]][[:alnum:]_-]*$";
         junos:pattern-message "Must be a string beginning with a number or letter and consisting of letters, numbers, dashes and underscores.";
       }
     }
     uses apply-advanced;
     leaf description {
       description "Text description of security association";
       type string {
         length "1 .. 80";
       }
     }
     leaf mode {
       description "Define security association mode";
       default "tunnel";
       type enumeration {
         enum "transport" {
           description "Transport mode";
           junos:must "(!(\".. dynamic\"))";
           junos:must-message "Dynamic security associations are not supported in transport mode";
           junos:must "(\".. manual\")";
           junos:must-message "Manual block must be configured for transport mode security association";
         }
         enum "tunnel" {
           description "Tunnel mode";
         }
       }
     }
     choice sa_choice {
       case case_1 {
         container manual {
           description "Define a manual security association";
           uses apply-advanced;
           list direction {
             key name;
             ordered-by user;
             description "Define the direction of the security association";
             leaf name {
               junos:cli-feature "nokeyword";
               type enumeration {
                 enum "inbound" {
                   description "Inbound security association";
                   junos:must "(\".. .. direction $$={outbound}\")";
                   junos:must-message "Outbound block must be configured";
                 }
                 enum "outbound" {
                   description "Outbound security association";
                   junos:must "(\".. .. direction $$={inbound}\")";
                   junos:must-message "Inbound block must be configured";
                 }
                 enum "bidirectional" {
                   description "Bidirectional security association";
                   junos:must "((!(\".. .. direction $$={inbound}\") && !(\".. .. direction $$={outbound}\")))";
                   junos:must-message "Outbound or inbound blocks must not be configured";
                 }
               }
             }
             uses apply-advanced;
             leaf protocol {
               description "Define an IPSec protocol for the security association";
               type enumeration {
                 enum "ah" {
                   description "Authentication header";
                   junos:must "(!(\".. encryption\"))";
                   junos:must-message "Encryption must not be defined for AH";
                   junos:must "(\".. authentication\")";
                   junos:must-message "Authentication must be defined for AH";
                 }
                 enum "esp" {
                   description "Encapsulated Security Payload header";
                   junos:must "((\".. authentication\" || \".. encryption\"))";
                   junos:must-message "Either authentication or encryption must be defined for ESP";
                 }
                 enum "bundle" {
                   description "Bundle (AH authentication plus ESP encryption)";
                   junos:must "(\".. auxiliary-spi\")";
                   junos:must-message "Auxiliary SPI must be defined for AH plus ESP bundle";
                   junos:must "(\".. encryption\")";
                   junos:must-message "Encryption must be defined for AH plus ESP bundle";
                   junos:must "(\".. authentication\")";
                   junos:must-message "Authentication must be defined for AH plus ESP bundle";
                 }
               }
             }
             leaf spi {
               description "Define security parameter index";
               type union {
                 type string {
                   pattern "<.*>|$.*";
                 }
                 type uint32 {
                   range "256 .. 16639";
                 }
               }
             }
             leaf auxiliary-spi {
               description "ESP security parameter index for IPSec SA bundle";
               junos:must "(\".. protocol bundle\")";
               junos:must-message "Auxiliary SPI must be configured with protocol bundle only";
               type union {
                 type string {
                   pattern "<.*>|$.*";
                 }
                 type uint32 {
                   range "256 .. 16639";
                 }
               }
             }
             container authentication {
               description "Define authentication parameters";
               uses apply-advanced;
               leaf algorithm {
                 description "Define authentication algorithm";
                 type enumeration {
                   enum "hmac-md5-96" {
                     description "HMAC-MD5-96 authentication algorithm";
                   }
                   enum "hmac-sha1-96" {
                     description "HMAC-SHA1-96 authentication algorithm";
                   }
                   enum "hmac-sha2-256" {
                     description "HMAC-SHA2-256 authentication algorithm";
                   }
                   enum "hmac-sha-256-128" {
                     description "HMAC-SHA-256-128 authentication algorithm";
                   }
                 }
               }
               container key {
                 junos:cli-feature "oneliner";
                 description "Define an authentication key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                         junos:posix-pattern "^[[:xdigit:]]+$";
                         junos:pattern-message "Must be hexadecimal digits (0-9, a-f, A-F)";
                       }
                     }
                   }
                 }
               }
             }
             container encryption {
               description "Define encryption parameters";
               uses apply-advanced;
               leaf algorithm {
                 description "Define encryption algorithm";
                 type enumeration {
                   enum "des-cbc" {
                     description "DES-CBC encryption algorithm";
                   }
                   enum "3des-cbc" {
                     description "3DES-CBC encryption algorithm";
                   }
                   enum "aes-128-cbc" {
                     description "AES-CBC 128-bit encryption algorithm";
                   }
                   enum "aes-192-cbc" {
                     description "AES-CBC 192-bit encryption algorithm";
                   }
                   enum "aes-256-cbc" {
                     description "AES-CBC 256-bit encryption algorithm";
                   }
                 }
               }
               container key {
                 junos:cli-feature "oneliner";
                 description "Define an encryption key";
                 choice key-choice {
                   case case_1 {
                     leaf ascii-text {
                       description "Format as text";
                       type string {
                         length "1 .. 255";
                       }
                     }
                   }
                   case case_2 {
                     leaf hexadecimal {
                       description "Format as hexadecimal";
                       type string {
                         length "1 .. 255";
                         junos:posix-pattern "^[[:xdigit:]]+$";
                         junos:pattern-message "Must be hexadecimal digits (0-9, a-f, A-F)";
                       }
                     }
                   }
                 }
               }
             }
           }
         }
       }
       case case_2 {
         container dynamic {
           description "Define a dynamic security association";
           uses apply-advanced;
           leaf replay-window-size {
             description "Define replay protection window size";
             type enumeration {
               enum "32" {
                 description "32-packet window size";
               }
               enum "64" {
                 description "64-packet window size";
               }
             }
           }
           leaf ipsec-policy {
             description "Name of the IPSec policy";
             junos:must "(\"security ipsec policy $$\")";
             junos:must-message "Referenced IPSec policy must be defined under [edit security ipsec policy]";
             type string {
               length "1 .. 32";
               junos:posix-pattern "^[[:alnum:]][[:alnum:]_-]*$";
               junos:pattern-message "Must be a string beginning with a number or letter and consisting of letters, numbers, dashes and underscores.";
             }
           }
         }
       }
     }
   }
   grouping ipsec-traceoptions {
     description "Data-plane IPSec tracing options";
     uses apply-advanced;
     list flag {
       key name;
       ordered-by user;
       junos:cli-feature "oneliner";
       description "Events to include in data-plane IPSec trace output";
       leaf name {
         junos:cli-feature "nokeyword";
         type enumeration {
           enum "packet-processing" {
             description "Trace data packet processing events";
           }
           enum "packet-drops" {
             description "Trace packet drops";
           }
           enum "security-associations" {
             description "Trace security association management events";
           }
           enum "next-hop-tunnel-binding" {
             description "Trace next-hop tunnel binding events";
           }
           enum "all" {
             description "Trace with all flags enabled";
           }
         }
       }
     }
   }
   grouping ipsec-trusted-channel-sa {
     uses apply-advanced;
     leaf description {
       description "Text description of trusted channel security association";
       type string {
         length "1 .. 80";
       }
     }
     container manual {
       description "Define a manual security association";
       uses apply-advanced;
       list direction {
         key name;
         ordered-by user;
         description "Define the direction of the security association";
         leaf name {
           junos:cli-feature "nokeyword";
           type enumeration {
             enum "inbound" {
               description "Inbound security association";
               junos:must "(\".. .. direction $$={outbound}\")";
               junos:must-message "Outbound block must be configured";
             }
             enum "outbound" {
               description "Outbound security association";
               junos:must "(\".. .. direction $$={inbound}\")";
               junos:must-message "Inbound block must be configured";
             }
             enum "bidirectional" {
               description "Bidirectional security association";
               junos:must "((!(\".. .. direction $$={inbound}\") && !(\".. .. direction $$={outbound}\")))";
               junos:must-message "Outbound or inbound blocks must not be configured";
             }
           }
         }
         uses apply-advanced;
         leaf protocol {
           description "Define an IPSec protocol for the security association";
           type enumeration {
             enum "ah" {
               description "Authentication header";
               junos:must "(!(\".. encryption\"))";
               junos:must-message "Encryption must not be defined for AH";
               junos:must "(\".. authentication\")";
               junos:must-message "Authentication must be defined for AH";
             }
             enum "esp" {
               description "Encapsulated Security Payload header";
               junos:must "((\".. authentication\" || \".. encryption\"))";
               junos:must-message "Either authentication or encryption must be defined for ESP";
             }
             enum "bundle" {
               description "Bundle (AH authentication plus ESP encryption)";
               junos:must "(\".. auxiliary-spi\")";
               junos:must-message "Auxiliary SPI must be defined for AH plus ESP bundle";
               junos:must "(\".. encryption\")";
               junos:must-message "Encryption must be defined for AH plus ESP bundle";
               junos:must "(\".. authentication\")";
               junos:must-message "Authentication must be defined for AH plus ESP bundle";
             }
           }
         }
         leaf spi {
           description "Define security parameter index";
           type union {
             type string {
               pattern "<.*>|$.*";
             }
             type uint32 {
               range "256 .. 16639";
             }
           }
         }
         leaf auxiliary-spi {
           description "ESP security parameter index for IPSec SA bundle";
           junos:must "(\".. protocol bundle\")";
           junos:must-message "Auxiliary SPI must be configured with protocol bundle only";
           type union {
             type string {
               pattern "<.*>|$.*";
             }
             type uint32 {
               range "256 .. 16639";
             }
           }
         }
         container authentication {
           description "Define authentication parameters";
           uses apply-advanced;
           leaf algorithm {
             description "Define authentication algorithm";
             type enumeration {
               enum "hmac-md5-96" {
                 description "HMAC-MD5-96 authentication algorithm";
               }
               enum "hmac-sha1-96" {
                 description "HMAC-SHA1-96 authentication algorithm";
               }
               enum "hmac-sha2-256" {
                 description "HMAC-SHA2-256 authentication algorithm";
               }
               enum "hmac-sha-256-128" {
                 description "HMAC-SHA-256-128 authentication algorithm";
               }
             }
           }
           container key {
             junos:cli-feature "oneliner";
             description "Define an authentication key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
         container encryption {
           description "Define encryption parameters";
           uses apply-advanced;
           leaf algorithm {
             description "Define encryption algorithm";
             type enumeration {
               enum "des-cbc" {
                 description "DES-CBC encryption algorithm";
               }
               enum "3des-cbc" {
                 description "3DES-CBC encryption algorithm";
               }
               enum "aes-128-cbc" {
                 description "AES-CBC 128-bit encryption algorithm";
               }
               enum "aes-192-cbc" {
                 description "AES-CBC 192-bit encryption algorithm";
               }
               enum "aes-256-cbc" {
                 description "AES-CBC 256-bit encryption algorithm";
               }
             }
           }
           container key {
             junos:cli-feature "oneliner";
             description "Define an encryption key";
             choice key-choice {
               case case_1 {
                 leaf ascii-text {
                   description "Format as text";
                   type string {
                     length "1 .. 255";
                   }
                 }
               }
               case case_2 {
                 leaf hexadecimal {
                   description "Format as hexadecimal";
                   type string {
                     length "1 .. 255";
                     junos:posix-pattern "^[[:xdigit:]]+$";
                     junos:pattern-message "Must be hexadecimal digits (0-9, a-f, A-F)";
                   }
                 }
               }
             }
           }
         }
       }
     }
   }
   grouping ipsec-vpn-monitor {
     description "Configure VPN monitoring";
     uses apply-advanced;
     leaf interval {
       description "Monitor interval in seconds";
       default "10";
       units "seconds";
       type union {
         type string {
           pattern "<.*>|$.*";
         }
         type uint32 {
           range "2 .. 3600";
         }
       }
     }
     leaf threshold {
       description "Number of consecutive failures to determine connectivity";
       default "10";
       type union {
         type string {
           pattern "<.*>|$.*";
         }
         type uint32 {
           range "1 .. 65536";
         }
       }
     }
   }
   grouping ipsec-vpn-template {
     description "Configure an IPSec VPN";
     leaf name {
       description "Name of the VPN";
       junos:cli-feature "nokeyword";
       type string {
         length "1 .. 32";
       }
     }
     uses apply-advanced;
     leaf bind-interface {
       description "Bind to tunnel interface (route-based VPN)";
       junos:must "((\"interfaces $$\" || any \"logical-systems <*> interfaces $$\"))";
       junos:must-message "Referenced interface must be configured under [edit interfaces] hierarchy";
       type union {
         type jt:interface-name;
         type string {
           pattern "<.*>|$.*";
         }
       }
     }
     leaf df-bit {
       description "Specifies how to handle the Don't Fragment bit";
       type enumeration {
         enum "clear" {
           description "Clear DF bit of outer header";
         }
         enum "set" {
           description "Set DF bit of outer header";
         }
         enum "copy" {
           description "Copy DF bit from inner header";
         }
       }
     }
     container vpn-monitor {
       description "Monitor VPN liveliness";
       presence "enable vpn-monitor";
       uses ipsec-template-monitor;
     }
     choice negotiation {
       case case_1 {
         container manual {
           description "Define a manual security association";
           uses apply-advanced;
           leaf gateway {
             description "Define the IPSec peer";
             type jt:hostname;
           }
           leaf external-interface {
             description "External interface for the security association";
             junos:must "(!(\"interfaces $$ family bridge\"))";
             junos:must-message "Bridge interface is not allowed as external-interface";
             junos:must "(\"interfaces $$-IFL\")";
             junos:must-message "Referenced interface must be configured under [edit interfaces] hierarchy";
             type union {
               type jt:interface-unit;
               type string {
                 pattern "<.*>|$.*";
               }
             }
           }
           leaf protocol {
             description "Define an IPSec protocol for the security association";
             type enumeration {
               enum "ah" {
                 description "Authentication header";
                 junos:must "(!(\".. encryption\"))";
                 junos:must-message "Encryption must not be defined for AH";
                 junos:must "(\".. authentication\")";
                 junos:must-message "Authentication must be defined for AH";
               }
               enum "esp" {
                 description "Encapsulated Security Payload header";
                 junos:must "((\".. authentication\" || \".. encryption\"))";
                 junos:must-message "Either authentication or encryption must be defined for ESP";
               }
             }
           }
           leaf spi {
             description "Define security parameter index";
             type union {
               type string {
                 pattern "<.*>|$.*";
               }
               type uint32 {
                 range "256 .. 16639";
               }
             }
           }
           container authentication {
             description "Define authentication parameters";
             uses apply-advanced;
             leaf algorithm {
               description "Define authentication algorithm";
               type enumeration {
                 enum "hmac-md5-96" {
                   description "HMAC-MD5-96 authentication algorithm";
                 }
                 enum "hmac-sha1-96" {
                   description "HMAC-SHA1-96 authentication algorithm";
                 }
                 enum "hmac-sha-256-128" {
                   description "HMAC-SHA-256-128 authentication algorithm";
                 }
                 enum "hmac-sha-256-96" {
                   description "HMAC-SHA-256-96 authentication algorithm (non-RFC compliant)";
                 }
               }
             }
             container key {
               junos:cli-feature "oneliner";
               description "Define an authentication key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
           container encryption {
             description "Define encryption parameters";
             uses apply-advanced;
             leaf algorithm {
               description "Define encryption algorithm";
               type enumeration {
                 enum "des-cbc" {
                   description "DES-CBC encryption algorithm";
                 }
                 enum "3des-cbc" {
                   description "3DES-CBC encryption algorithm";
                 }
                 enum "aes-128-cbc" {
                   description "AES-CBC 128-bit encryption algorithm";
                 }
                 enum "aes-192-cbc" {
                   description "AES-CBC 192-bit encryption algorithm";
                 }
                 enum "aes-256-cbc" {
                   description "AES-CBC 256-bit encryption algorithm";
                 }
               }
             }
             container key {
               junos:cli-feature "oneliner";
               description "Define an encryption key";
               choice key-choice {
                 case case_1 {
                   leaf ascii-text {
                     description "Format as text";
                     type string {
                       length "1 .. 255";
                     }
                   }
                 }
                 case case_2 {
                   leaf hexadecimal {
                     description "Format as hexadecimal";
                     type string {
                       length "1 .. 255";
                       junos:posix-pattern "^[[:xdigit:]]+$";
                       junos:pattern-message "Must be hexadecimal digits (0-9, a-f, A-F)";
                     }
                   }
                 }
               }
             }
           }
         }
       }
       case case_2 {
         container ike {
           description "Define an IKE-keyed IPSec vpn";
           uses apply-advanced;
           leaf gateway {
             description "Name of remote gateway";
             junos:must "(!((\"security ike gateway $$ dynamic ike-user-type\" && \".. .. vpn-monitor destination-ip\")))";
             junos:must-message "No destination ip support for vpn-monitor in vpn using shared or group ike";
             junos:must "(!((\".. .. bind-interface\" && (\"security ike gateway $$ dynamic ike-user-type\" && \"security ike gateway $$ version v2-only\"))))";
             junos:must-message "No IKEv2 support for shared or group ike in route-based vpn";
             junos:must "(\"security ike gateway $$\")";
             junos:must-message "Referenced IKE gateway must be defined under [edit security ike gateway]";
             type string {
               length "1 .. 32";
               junos:posix-pattern "^[[:alnum:]][[:alnum:]_-]*$";
               junos:pattern-message "Must be a string beginning with a number or letter and consisting of letters, numbers, dashes and underscores.";
             }
           }
           leaf idle-time {
             description "Idle time to delete SA";
             units "seconds";
             type union {
               type string {
                 pattern "<.*>|$.*";
               }
               type uint32 {
                 range "60 .. 999999";
               }
             }
           }
           leaf no-anti-replay {
             description "Disable the anti-replay check";
             type empty;
           }
           container proxy-identity {
             description "IPSec proxy-id to use in IKE negotiations";
             presence "enable proxy-identity";
             uses ipsec-template-proxy-id;
           }
           leaf ipsec-policy {
             description "Name of the IPSec policy";
             junos:must "(\"security ipsec policy $$\")";
             junos:must-message "Referenced IPSec policy must be defined under [edit security ipsec policy]";
             type string {
               length "1 .. 32";
               junos:posix-pattern "^[[:alnum:]][[:alnum:]_-]*$";
               junos:pattern-message "Must be a string beginning with a number or letter and consisting of letters, numbers, dashes and underscores.";
             }
           }
           leaf install-interval {
             description "Delay installation of rekeyed outbound SAs on initiator";
             default "1";
             units "seconds";
             type union {
               type string {
                 pattern "<.*>|$.*";
               }
               type uint32 {
                 range "0 .. 10";
               }
             }
           }
         }
       }
     }
     leaf establish-tunnels {
       description "Define the criteria to establish tunnels";
       default "on-traffic";
       junos:must "(\".. ike\")";
       junos:must-message "VPN must be IKE-keyed to define establish-tunnel method";
       type enumeration {
         enum "immediately" {
           description "Establish tunnels immediately";
         }
         enum "on-traffic" {
           description "Establish tunnels on traffic";
         }
       }
     }
   }
   grouping ipsec-template-monitor {
     description "Configure VPN monitoring";
     uses apply-advanced;
     leaf optimized {
       description "Optimize for scalability";
       type empty;
     }
     leaf source-interface {
       description "Source interface for monitor message";
       type union {
         type jt:interface-unit;
         type string {
           pattern "<.*>|$.*";
         }
       }
     }
     leaf destination-ip {
       description "Destination IP addres for monitor message";
       type jt:ipaddr;
     }
   }
   grouping ipsec-template-proxy-id {
     description "Proxy identity settings";
     uses apply-advanced;
     leaf local {
       description "Local IP address/prefix length";
       type jt:ipprefix-mandatory;
     }
     leaf remote {
       description "Remote IP address/prefix length";
       type jt:ipprefix-mandatory;
     }
     leaf service {
       description "Name of serivce that passes through, any enables all services";
       type string {
         length "1 .. 32";
       }
     }
   }
   grouping security-macsec {
     uses apply-advanced;
     container traceoptions {
       description "Tracing options for debugging protocol operation";
       presence "enable traceoptions";
       uses macsec-trace-options;
     }
     list connectivity-association {
       key name;
       ordered-by user;
       description "Configure connectivity association properties";
       leaf name {
         description "Connectivity association name";
         junos:cli-feature "nokeyword";
         type string {
           length "1 .. 32";
         }
       }
       uses apply-advanced;
       leaf security-mode {
         description "Connectivity association mode";
         type enumeration {
           enum "dynamic" {
             description "Dynamic connectivity and secure association mode (MKA and dot1x)";
           }
           enum "static-sak" {
             description "Static secure association key mode (no MKA)";
           }
           enum "static-cak" {
             description "Static connectivity association key mode (MKA and Pre-shared key)";
           }
         }
       }
       leaf sak-hash-128 {
         description "Configure to generate 128bit SAK hash to program HW";
         junos:must "((\".. cipher-suite gcm-aes-256\" || \".. cipher-suite gcm-aes-xpn-256\"))";
         junos:must-message "Allowed only for cipher-suite gcm-aes-256 or gcm-aes-xpn-256";
         type empty;
       }
       list secure-channel {
         key name;
         ordered-by user;
         description "Configure secure channel properties";
         junos:must "(\".. security-mode static-sak\")";
         junos:must-message "Secure-channel configuration allowed only for static-sak mode";
         leaf name {
           description "Secure channel name";
           junos:cli-feature "nokeyword";
           type string;
         }
         uses apply-advanced;
         container id {
           description "Secure channel identifier";
           uses apply-advanced;
           leaf mac-address {
             description "MAC addresses";
             type jt:mac-addr;
           }
           leaf port-id {
             description "Port identifier";
             type union {
               type string {
                 pattern "<.*>|$.*";
               }
               type uint32 {
                 range "1 .. 65535";
               }
             }
           }
         }
         leaf direction {
           description "Secure channel direction";
           type enumeration {
             enum "inbound" {
             }
             enum "outbound" {
             }
           }
         }
         leaf encryption {
           description "Enable Encryption";
           type empty;
         }
         leaf offset {
           description "Confidentiality offset";
           type enumeration {
             enum "0" {
               description "Confidentiality protected for all octets of MACSec PDU data";
             }
             enum "30" {
               description "Confidentiality not protected for initial 30 octets of MACSec PDU data";
             }
             enum "50" {
               description "Confidentiality not protected for initial 50 octets of MACSec PDU data";
             }
           }
         }
         leaf include-sci {
           description "Include secure channel identifier in MAC Security PDU";
           type empty;
         }
         list security-association {
           key name;
           ordered-by user;
           description "Security association";
           leaf name {
             description "Security association number";
             junos:cli-feature "nokeyword";
             type union {
               type string {
                 pattern "<.*>|$.*";
               }
               type uint32 {
                 range "0 .. 3";
               }
             }
           }
           uses apply-advanced;
           leaf key {
             description "Security association key in hexadecimal format of length 32";
             type string {
               length 32;
               junos:posix-pattern "^[[:xdigit:]]+$";
               junos:pattern-message "Must be hexadecimal digits (0-9, a-f, A-F) of length 32";
             }
           }
         }
       }
       container mka {
         presence "enable mka";
         junos:must "((\".. security-mode static-cak\" || \".. security-mode dynamic\"))";
         junos:must-message "MKA configuration can be set only for dynamic/static-cak modes";
         description "Configure MAC Security Key Agreement protocol properties";
         uses apply-advanced;
         leaf transmit-interval {
           description "Configure MKA periodic transmit interval";
           default "2000";
           units "milliseconds";
           junos:must "(!(\".. bounded-delay\"))";
           junos:must-message "Might not be configured with bounded-delay";
           type union {
             type string {
               pattern "<.*>|$.*";
             }
             type uint32 {
               range "2000 .. 6000";
             }
           }
         }
         leaf sak-rekey-interval {
           description "Configure SAK rekeying interval";
           units "seconds";
           type union {
             type string {
               pattern "<.*>|$.*";
             }
             type uint32 {
               range "60 .. 86400";
             }
           }
         }
         leaf bounded-delay {
           description "Configure Bounded Hello Time";
           type empty;
         }
         leaf key-server-priority {
           description "Configure MKA key server priority";
           default "16";
           junos:must "(\".. .. security-mode static-cak\")";
           junos:must-message "Allowed only for static-cak mode";
           type union {
             type string {
               pattern "<.*>|$.*";
             }
             type uint32 {
               range "0 .. 255";
             }
           }
         }
         leaf should-secure {
           description "Allows non-secure traffic if MKA session fails";
           junos:must "(!(\".. must-secure\"))";
           junos:must-message "Must-secure and Should-secure cannot be configured together";
           type empty;
         }
         leaf eapol-address {
           description "Configure EAPOL destination group address";
           default "pae";
           junos:must "(\".. .. security-mode static-cak\")";
           junos:must-message "Allowed only for static-cak mode";
           type string;
         }
       }
       container replay-protect {
         junos:must "((\".. security-mode static-cak\" || \".. security-mode dynamic\"))";
         junos:must-message "Not allowed for static-sak mode";
         description "Configure replay protection";
         uses apply-advanced;
         leaf replay-window-size {
           description "Configure replay protection window size";
           units "packets";
           type union {
             type string {
               pattern "<.*>|$.*";
             }
             type uint32 {
               range "0 .. 65535";
             }
           }
         }
       }
       leaf no-encryption {
         description "Disable encryption";
         junos:must "(!(\".. offset\"))";
         junos:must-message "Offset can be configured only with encryption";
         junos:must "((\".. security-mode static-cak\" || \".. security-mode dynamic\"))";
         junos:must-message "Encryption for static-sak mode should be configured under secure-channel";
         type empty;
       }
       leaf disable-preceding-key {
         description "Disable CA preceding key duing key switch-over";
         junos:must "(\".. security-mode static-cak\")";
         junos:must-message "Enabling configuration allowed only in static-cak mode";
         type empty;
       }
       leaf offset {
         description "Confidentiality offset";
         default "0";
         junos:must "((\".. security-mode static-cak\" || \".. security-mode dynamic\"))";
         junos:must-message "Offset for static-sak mode should be configured under secure-channel";
         type enumeration {
           enum "0" {
             description "Confidentiality provided for all octets of data";
           }
           enum "30" {
             description "Confidentiality not provided for initial 30 octets of data";
             junos:must "((!(\".. cipher-suite gcm-aes-xpn-128\") && !(\".. cipher-suite gcm-aes-xpn-256\")))";
             junos:must-message "XPN cipher-suite does not support non-zero offset";
           }
           enum "50" {
             description "Confidentiality not provided for initial 50 octets of data";
             junos:must "((!(\".. cipher-suite gcm-aes-xpn-128\") && !(\".. cipher-suite gcm-aes-xpn-256\")))";
             junos:must-message "XPN cipher-suite does not support non-zero offset";
           }
         }
       }
       leaf include-sci {
         description "Include secure channel identifier in MAC Security PDU";
         junos:must "((\".. security-mode static-cak\" || \".. security-mode dynamic\"))";
         junos:must-message "Not allowed for static-sak mode";
         type empty;
       }
       container pre-shared-key {
         presence "enable pre-shared-key";
         junos:must "(\".. security-mode static-cak\")";
         junos:must-message "Pre-shared key configuration allowed only in static-cak mode";
         description "Configure pre-shared connectivity association key";
         uses apply-advanced;
         leaf ckn {
           description "Connectivity association key name in hexadecimal format";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association key in hexadecimal format";
           type string {
             length "1 .. 64";
             junos:posix-pattern "^[[:xdigit:]]+$";
             junos:pattern-message "Must be hexadecimal digits (0-9, a-f, A-F)";
           }
         }
       }
       container fallback-key {
         presence "enable fallback-key";
         junos:must "(\".. security-mode static-cak\")";
         junos:must-message "Fallback key configuration allowed only in static-cak mode";
         description "Configure fallback key for connectivity association";
         uses apply-advanced;
         leaf ckn {
           description "Connectivity association fallback key name in hexadecimal format";
           junos:must "(!(\".. .. pre-shared-key ckn $$\"))";
           junos:must-message "fallback-key CKN cannot be same as pre-shared-key CKN";
           type string {
             length "2 .. 64";
             junos:posix-pattern "^([0-9a-fA-F][0-9a-fA-F]){1,32}$";
             junos:pattern-message "Must be an even-length string up to 64 hexadecimal digits (0-9, a-f, A-F)";
           }
         }
         leaf cak {
           description "Connectivity association fallback key secret in hexadecimal format";
           type string {
             length "1 .. 64";
             junos:posix-pattern "^[[:xdigit:]]+$";
             junos:pattern-message "Must be hexadecimal digits (0-9, a-f, A-F)";
           }
         }
       }
       leaf pre-shared-key-chain {
         description "Pre-shared key chain name for connectivity association";
         junos:must "(!(\".. pre-shared-key\"))";
         junos:must-message "May not be configured with pre-shared-key";
         junos:must "(\"security authentication-key-chains key-chain $$\")";
         junos:must-message "authentication-key-chains not defined !!";
         junos:must "(\".. security-mode static-cak\")";
         junos:must-message "key-chain configuration is allowed only in static-cak mode";
         type string {
           junos:posix-pattern "^.{1,32}$";
           junos:pattern-message "Must be string of 32 characters or less";
         }
       }
       list exclude-protocol {
         key name;
         ordered-by user;
         junos:cli-feature "oneliner";
         description "Configure protocols to exclude from MAC Security";
         junos:must "((\".. security-mode static-cak\" || \".. security-mode dynamic\"))";
         junos:must-message "Not allowed for static-sak mode";
         leaf name {
           junos:cli-feature "nokeyword";
           type enumeration {
             enum "cdp" {
               description "Cisco Discovery Protocol";
             }
             enum "lldp" {
               description "Link Level Discovery Protocol";
             }
             enum "lacp" {
               description "Link Aggregation Control Protocol";
             }
           }
         }
       }
     }
     list interfaces {
       key name;
       junos:cli-feature "homogeneous";
       description "Interfaces on which macsec configuration is applied";
       leaf name {
         junos:cli-feature "nokeyword";
         type union {
           type jt:interface-device;
           type string {
             pattern "<.*>|$.*";
           }
         }
       }
       uses apply-advanced;
       leaf connectivity-association {
         description "Connectivity association name";
         junos:must "(\"security macsec connectivity-association $$\")";
         junos:must-message "Connectivity association not defined";
         type string;
       }
       leaf pre-shared-key-chain {
         description "Pre-shared key chain name for connectivity association";
         junos:must "(\"security authentication-key-chains key-chain $$\")";
         junos:must-message "authentication-key-chains not defined !!";
         type string {
           junos:posix-pattern "^.{1,32}$";
           junos:pattern-message "Must be string of 32 characters or less";
         }
       }
       container replay-protect {
         description "Configure replay protection";
         uses apply-advanced;
         leaf replay-window-size {
           description "Configure replay protection window size";
           units "packets";
           type union {
             type string {
               pattern "<.*>|$.*";
             }
             type uint32 {
               range "0 .. 65535";
             }
           }
         }
       }
       container traceoptions {
         description "Tracing options of MKA protocol";
         presence "enable traceoptions";
         junos:must "(\".. connectivity-association\")";
         junos:must-message "Connectivity association should be configured on interface to enable traceoptions";
         uses mka-trace-options;
       }
     }
   }
   grouping macsec-trace-options {
     description "Trace options for MACSec Protocol";
     uses apply-advanced;
     container file {
       junos:cli-feature "oneliner";
       description "Trace file options";
       leaf filename {
         description "Name of file in which to write trace information";
         junos:cli-feature "nokeyword";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       junos:cli-feature "oneliner";
       description "Tracing parameters";
       junos:must "(\".. file\")";
       junos:must-message "Trace file name required to enable tracing";
       leaf name {
         junos:cli-feature "nokeyword";
         type enumeration {
           enum "config" {
             description "Trace configuration messages";
           }
           enum "debug" {
             description "Trace debug messages";
           }
           enum "telemetry" {
             description "Trace telemetry messages";
           }
           enum "normal" {
             description "Trace normal messages";
           }
           enum "all" {
             description "Trace all";
           }
         }
       }
     }
   }
   grouping mka-trace-options {
     description "Trace options for MKA protocol";
     uses apply-advanced;
     container file {
       junos:cli-feature "oneliner";
       description "Trace file options";
       leaf filename {
         description "Name of file in which to write trace information";
         junos:cli-feature "nokeyword";
         type string {
           length "1 .. 1024";
           junos:posix-pattern "![/ %]";
           junos:pattern-message "Must not contain '/', % or a space";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     list flag {
       key name;
       ordered-by user;
       junos:cli-feature "oneliner";
       description "Tracing parameters";
       junos:must "(\".. file\")";
       junos:must-message "Trace file name required to enable tracing";
       leaf name {
         junos:cli-feature "nokeyword";
         type enumeration {
           enum "mka-packets" {
             description "Trace MKA input and output packets";
           }
           enum "state" {
             description "Trace MKA state information";
           }
           enum "to-secy" {
             description "Trace MKA to SecY state changes";
           }
           enum "keys" {
             description "Trace key creation/generation information";
           }
           enum "normal" {
             description "Trace normal events";
           }
           enum "all" {
             description "Trace all";
           }
         }
       }
     }
   }
   grouping security-pki {
     uses apply-advanced;
     list ca-profile {
       key name;
       ordered-by user;
       description "Certificate authority profile configuration";
       leaf name {
         description "Name of certificate authority profile";
         junos:cli-feature "nokeyword";
         type string {
           length "1 .. 32";
           junos:posix-pattern "![/%. ]";
           junos:pattern-message "Must not contain '/', %, '.' or a space";
         }
       }
       uses apply-advanced;
       leaf ca-identity {
         description "Certificate authority identifier";
         type string;
       }
       leaf source-address {
         description "Use specified address as source address";
         type jt:ipaddr;
       }
       leaf proxy-profile {
         description "Use specified proxy server";
         junos:must "(\"services proxy profile $$\")";
         junos:must-message "Referenced Proxy profile must be defined under [edit services proxy profile]";
         type string;
       }
       leaf routing-instance {
         description "Use specified routing instance";
         junos:must "((\"routing-instances $$\" || any \"tenants <*> routing-instances $$\"))";
         junos:must-message "referenced routing-instance must be defined";
         type string;
       }
       container enrollment {
         description "Enrollment parameters for certificate authority";
         uses apply-advanced;
         leaf url {
           description "Enrollment URL of certificate authority";
           type string;
         }
         leaf retry {
           description "Number of enrollment retry attempts before aborting";
           default "1000";
           type union {
             type string {
               pattern "<.*>|$.*";
             }
             type uint32 {
               range "0 .. 1080";
             }
           }
         }
         leaf retry-interval {
           description "Interval in seconds between the enrollment retries";
           default "600";
           type union {
             type string {
               pattern "<.*>|$.*";
             }
             type uint32 {
               range "0 .. 3600";
             }
           }
         }
       }
       container revocation-check {
         description "Method for checking certificate revocations";
         uses apply-advanced;
         choice revocation-check-options {
           case case_1 {
             leaf use-crl {
               description "Use CRL for revocation check";
               type empty;
             }
           }
           case case_2 {
             leaf use-ocsp {
               description "Use OCSP for revocation check";
               type empty;
             }
           }
           case case_3 {
             leaf disable {
               description "Disable revocation check";
               type empty;
             }
           }
         }
         container ocsp {
           presence "enable ocsp";
           description "Online Certificate Status Protocol (OCSP) configuration";
           uses apply-advanced;
           list url {
             key name;
             ordered-by user;
             leaf name {
               description "HTTP URL for OCSP access location";
               junos:cli-feature "nokeyword";
               type string {
                 length "1 .. 500";
               }
             }
             uses apply-advanced;
           }
           leaf nonce-payload {
             description "Include nonce payload in OCSP requests";
             type enumeration {
               enum "enable" {
                 description "Send nonce paylod in OCSP request";
               }
               enum "disable" {
                 description "Do not send nonce payload in OCSP request";
               }
             }
           }
           leaf disable-responder-revocation-check {
             description "Disable OCSP responder certificate revocation check";
             type empty;
           }
           leaf accept-unknown-status {
             description "Accept certificates with unknown status";
             type empty;
           }
           container connection-failure {
             presence "enable connection-failure";
             description "Actions on failure to connect to OCSP Responder";
             uses apply-advanced;
             choice connection-failure-options {
               case case_1 {
                 leaf fallback-crl {
                   description "Use CRL for revocation check";
                   type empty;
                 }
               }
               case case_2 {
                 leaf disable {
                   description "Disable OCSP check on connection failure";
                   type empty;
                 }
               }
             }
           }
         }
         container crl {
           description "Certificate revocation list configuration";
           uses apply-advanced;
           container disable {
             junos:cli-feature "oneliner";
             leaf on-download-failure {
               description "Check revocation status with existing CRL file if present, otherwise skip. This feature must be enabled for manual CRL download.";
               type empty;
             }
           }
           list url {
             key name;
             ordered-by user;
             leaf name {
               description "URL of CRL distribution point for certificate authority";
               junos:cli-feature "nokeyword";
               type string {
                 length "1 .. 500";
               }
             }
             uses apply-advanced;
             leaf password {
               description "Password for authentication with the server";
               type jt:unreadable;
             }
           }
           leaf refresh-interval {
             description "CRL refresh interval";
             units "hours";
             type union {
               type string {
                 pattern "<.*>|$.*";
               }
               type uint32 {
                 range "0 .. 8784";
               }
             }
           }
         }
       }
       container administrator {
         description "Administrator information";
         uses apply-advanced;
         leaf email-address {
           description "Administrator e-mail to which to send certificate requests";
           type string;
         }
       }
     }
     list trusted-ca-group {
       key name;
       ordered-by user;
       description "Trusted Certificate Authority group configuration";
       leaf name {
         description "Name of the trusted CA group";
         junos:cli-feature "nokeyword";
         type string {
           length "1 .. 63";
         }
       }
       uses apply-advanced;
       leaf-list ca-profiles {
         ordered-by user;
         description "Name of the CA profiles (maximum 20)";
         type string {
           length "1 .. 63";
         }
         max-elements 20;
       }
     }
     container trap {
       presence "enable trap";
       description "Trap options for PKI certificates";
       uses apply-advanced;
       list certificate-id {
         key name;
         ordered-by user;
         description "Local certificate identifier";
         leaf name {
           description "Local cert id";
           junos:cli-feature "nokeyword";
           type string;
         }
         uses apply-advanced;
         leaf days {
           description "Number of days to generate trap (default 60)";
           junos:cli-feature "nokeyword";
           default "60";
           type union {
             type string {
               pattern "<.*>|$.*";
             }
             type uint32 {
               range "1 .. 100";
             }
           }
         }
       }
       list ca-identity {
         key name;
         ordered-by user;
         description "CA identity";
         leaf name {
           description "CA profile";
           junos:cli-feature "nokeyword";
           junos:must "(\"security pki ca-profile $$\")";
           junos:must-message "Referenced ca-profile must be defined under [edit security pki ca-profile]";
           type string;
         }
         uses apply-advanced;
         leaf days {
           description "Number of days to generate trap (default 60)";
           junos:cli-feature "nokeyword";
           default "60";
           type union {
             type string {
               pattern "<.*>|$.*";
             }
             type uint32 {
               range "1 .. 100";
             }
           }
         }
       }
       container all-certificates {
         presence "enable all-certificates";
         description "Trap config for all certificates";
         uses apply-advanced;
         leaf days {
           description "Number of days to generate trap (default 60)";
           junos:cli-feature "nokeyword";
           default "60";
           type union {
             type string {
               pattern "<.*>|$.*";
             }
             type uint32 {
               range "1 .. 100";
             }
           }
         }
       }
     }
     container auto-re-enrollment {
       description "Auto re-enroll of certificate";
       uses apply-advanced;
       container acme {
         presence "enable acme";
         description "ACME auto re-enrollment configuration";
         uses apply-advanced;
         list certificate-id {
           key name;
           ordered-by user;
           description "Acme auto re-enrollment configuration for certificate-id";
           leaf name {
             description "Certificate identifier that needs auto re-enrollment";
             junos:cli-feature "nokeyword";
             type string {
               junos:posix-pattern "^.{1,32}$";
               junos:pattern-message "Must be string of 32 characters or less";
             }
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf acme-key-id {
             description "Acme account key identifier";
             type string {
               junos:posix-pattern "^.{1,32}$";
               junos:pattern-message "Must be string of 32 characters or less";
             }
           }
           leaf ca-profile-name {
             description "Name of certificate authority profile";
             junos:must "((\".. re-enroll-time\" || \".. re-enroll-trigger-time-percentage\"))";
             junos:must-message "Re-enroll must configure the re-enroll-trigger-time-percentage or a re-enroll-time value";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container cmpv2 {
         presence "enable cmpv2";
         description "CMPv2 auto re-enrollment configuration";
         uses apply-advanced;
         list certificate-id {
           key name;
           ordered-by user;
           description "CMPv2 auto re-enrollment configuration for certificate-id";
           leaf name {
             description "Certificate identifier that needs auto re-enrollment";
             junos:cli-feature "nokeyword";
             type string {
               junos:posix-pattern "^.{1,32}$";
               junos:pattern-message "Must be string of 32 characters or less";
             }
           }
           uses apply-advanced;
           container re-enroll-time {
             presence "enable re-enroll-time";
             description "Re-enroll trigger time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             junos:must "((\".. re-enroll-time\" || \".. re-enroll-trigger-time-percentage\"))";
             junos:must-message "Re-enroll must configure the re-enroll-trigger-time-percentage or a re-enroll-time value";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-enroll-trigger-time-percentage {
             description "Re-enrollment trigger time before expiration as percentage";
             type union {
               type string {
                 pattern "<.*>|$.*";
               }
               type uint32 {
                 range "1 .. 99";
               }
             }
           }
           leaf re-generate-keypair {
             description "Generate new key-pair for auto-re-enrollment";
             type empty;
           }
         }
       }
       container scep {
         presence "enable scep";
         description "SCEP auto re-enrollment configuration";
         uses apply-advanced;
         list certificate-id {
           key name;
           ordered-by user;
           description "SCEP auto re-enrollment configuration for certificate-id";
           leaf name {
             description "Certificate identifier that needs auto re-enrollment";
             junos:cli-feature "nokeyword";
             type string {
               junos:posix-pattern "^.{1,32}$";
               junos:pattern-message "Must be string of 32 characters or less";
             }
           }
           uses apply-advanced;
           container re-enroll-time {
             presence "enable re-enroll-time";
             description "Re-enroll time in days <value> | hours <value> | percentage <value>";
             uses apply-advanced;
             choice re-enroll-time-options {
               case case_1 {
                 leaf days {
                   description "Re-enrollment trigger time in days ahead of expiration";
                   type union {
                     type uint32;
                     type string {
                       pattern "<.*>|$.*";
                     }
                   }
                 }
               }
               case case_2 {
                 leaf hours {
                   description "Re-enrollment trigger time in hours ahead of expiration";
                   type union {
                     type uint32;
                     type string {
                       pattern "<.*>|$.*";
                     }
                   }
                 }
               }
               case case_3 {
                 leaf percent {
                   description "Re-enrollment trigger time before expiration as percentage";
                   type union {
                     type string {
                       pattern "<.*>|$.*";
                     }
                     type uint32 {
                       range "1 .. 99";
                     }
                   }
                 }
               }
             }
           }
           leaf ca-profile-name {
             description "Name of certificate authority profile";
             junos:must "((\".. re-enroll-time\" || \".. re-enroll-trigger-time-percentage\"))";
             junos:must-message "Re-enroll must configure the re-enroll-trigger-time-percentage or a re-enroll-time value";
             junos:must "(\"security pki ca-profile $$ enrollment url\")";
             junos:must-message "Referenced ca-profile must have enrollment url configured under [edit security pki ca-profile <ca-profile-name> enrollment url]";
             junos:must "(\"security pki ca-profile $$\")";
             junos:must-message "Referenced ca-profile must be defined under [edit security pki ca-profile]";
             type string {
               junos:posix-pattern "^.{1,32}$";
               junos:pattern-message "Must be string of 32 characters or less";
             }
           }
           leaf re-generate-keypair {
             description "Generate new key-pair for auto-re-enrollment";
             type empty;
           }
           leaf re-enroll-trigger-time-percentage {
             description "Re-enrollment trigger time before expiration as percentage";
             type union {
               type string {
                 pattern "<.*>|$.*";
               }
               type uint32 {
                 range "1 .. 99";
               }
             }
           }
           leaf challenge-password {
             description "Password used by CA for enrollment and revocation";
             type jt:unreadable;
           }
           container scep-encryption-algorithm {
             presence "enable scep-encryption-algorithm";
             description "SCEP encryption algorithm";
             uses apply-advanced;
             choice scep-encryption-algorithm-options {
               case case_1 {
                 leaf des {
                   description "Use DES as SCEP encryption algorithm";
                   type empty;
                 }
               }
               case case_2 {
                 leaf des3 {
                   description "Use DES3 as SCEP encryption algorithm";
                   type empty;
                 }
               }
             }
           }
           container scep-digest-algorithm {
             presence "enable scep-digest-algorithm";
             description "SCEP digest algorithm";
             uses apply-advanced;
             choice scep-digest-algorithm-options {
               case case_1 {
                 leaf md5 {
                   description "Use MD5 as SCEP digest algorithm";
                   type empty;
                 }
               }
               case case_2 {
                 leaf sha1 {
                   description "Use SHA1 as SCEP digest algorithm";
                   type empty;
                 }
               }
             }
           }
         }
       }
       list certificate-id {
         key name;
         ordered-by user;
         description "Auto re-enrollment configuration for certificate-id";
         status deprecated;
         leaf name {
           description "Certificate identifier that needs auto re-enrollment";
           junos:cli-feature "nokeyword";
           type string {
             junos:posix-pattern "^.{1,32}$";
             junos:pattern-message "Must be string of 32 characters or less";
           }
         }
         uses apply-advanced;
         container re-enroll-time {
           presence "enable re-enroll-time";
           description "Re-enroll trigger time in days <value> | hours <value> | percentage <value>";
           uses apply-advanced;
           choice re-enroll-time-options {
             case case_1 {
               leaf days {
                 description "Re-enrollment trigger time in days ahead of expiration";
                 type union {
                   type uint32;
                   type string {
                     pattern "<.*>|$.*";
                   }
                 }
               }
             }
             case case_2 {
               leaf hours {
                 description "Re-enrollment trigger time in hours ahead of expiration";
                 type union {
                   type uint32;
                   type string {
                     pattern "<.*>|$.*";
                   }
                 }
               }
             }
             case case_3 {
               leaf percent {
                 description "Re-enrollment trigger time before expiration as percentage";
                 type union {
                   type string {
                     pattern "<.*>|$.*";
                   }
                   type uint32 {
                     range "1 .. 99";
                   }
                 }
               }
             }
           }
         }
         leaf ca-profile-name {
           description "Name of certificate authority profile";
           junos:must "((\".. re-enroll-time\" || \".. re-enroll-trigger-time-percentage\"))";
           junos:must-message "Re-enroll must configure the re-enroll-trigger-time-percentage or a re-enroll-time value";
           junos:must "(\"security pki ca-profile $$ enrollment url\")";
           junos:must-message "Referenced ca-profile must have enrollment url configured under [edit security pki ca-profile <ca-profile-name> enrollment url]";
           junos:must "(\"security pki ca-profile $$\")";
           junos:must-message "Referenced ca-profile must be defined under [edit security pki ca-profile]";
           type string {
             junos:posix-pattern "^.{1,32}$";
             junos:pattern-message "Must be string of 32 characters or less";
           }
         }
         leaf re-generate-keypair {
           description "Generate new key-pair for auto-re-enrollment";
           type empty;
         }
         leaf re-enroll-trigger-time-percentage {
           description "Re-enrollment trigger time before expiration as percentage";
           type union {
             type string {
               pattern "<.*>|$.*";
             }
             type uint32 {
               range "1 .. 99";
             }
           }
         }
         leaf challenge-password {
           description "Password used by CA for enrollment and revocation";
           type jt:unreadable;
         }
         container scep-encryption-algorithm {
           presence "enable scep-encryption-algorithm";
           description "SCEP encryption algorithm";
           uses apply-advanced;
           choice scep-encryption-algorithm-options {
             case case_1 {
               leaf des {
                 description "Use DES as SCEP encryption algorithm";
                 type empty;
               }
             }
             case case_2 {
               leaf des3 {
                 description "Use DES3 as SCEP encryption algorithm";
                 type empty;
               }
             }
           }
         }
         container scep-digest-algorithm {
           presence "enable scep-digest-algorithm";
           description "SCEP digest algorithm";
           uses apply-advanced;
           choice scep-digest-algorithm-options {
             case case_1 {
               leaf md5 {
                 description "Use MD5 as SCEP digest algorithm";
                 type empty;
               }
             }
             case case_2 {
               leaf sha1 {
                 description "Use SHA1 as SCEP digest algorithm";
                 type empty;
               }
             }
           }
         }
       }
     }
     container traceoptions {
       description "PKI trace options";
       uses apply-advanced;
       leaf no-remote-trace {
         description "Disable remote tracing";
         junos:must "(\"system tracing\")";
         junos:must-message "'no-remote-trace' is valid only when [system tracing] is configured";
         type empty;
       }
       container file {
         junos:cli-feature "oneliner";
         description "Trace file information";
         leaf filename {
           description "Name of file in which to write trace information";
           junos:cli-feature "nokeyword";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         junos:cli-feature "oneliner";
         description "Tracing parameters";
         leaf name {
           junos:cli-feature "nokeyword";
           type enumeration {
             enum "certificate-verification" {
               description "PKI certificate verification tracing";
             }
             enum "online-crl-check" {
               description "PKI online crl tracing";
             }
             enum "enrollment" {
               description "PKI certificate enrollment tracing";
             }
             enum "acme-enrollment" {
               description "PKI acme based certificate enrollment tracing";
             }
             enum "all" {
               description "Trace with all flags enabled";
             }
           }
         }
       }
     }
     container acme-account-key {
       description "ACME account key";
       uses apply-advanced;
       list acme-key-id {
         key name;
         ordered-by user;
         description "ACME account key identifier";
         leaf name {
           description "ACME key identifier which is used as account key";
           junos:cli-feature "nokeyword";
           type string;
         }
         uses apply-advanced;
       }
     }
   }
   grouping security-traceoptions {
     description "Trace options for key management process";
     uses apply-advanced;
     leaf no-remote-trace {
       description "Disable remote tracing";
       junos:must "(\"system tracing\")";
       junos:must-message "'no-remote-trace' is valid only when [system tracing] is configured";
       type empty;
     }
     container file {
       junos:cli-feature "oneliner";
       description "Trace file information";
       leaf filename {
         description "Name of file in which to write trace information";
         junos:cli-feature "nokeyword";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf rate-limit {
       description "Limit the incoming rate of trace messages";
       default "0";
       type union {
         type string {
           pattern "<.*>|$.*";
         }
         type uint32 {
           range "0 .. 4294967295";
         }
       }
     }
     container filter {
       description "Filter parameters for IKE traceoptions";
       uses apply-advanced;
     }
     list flag {
       key name;
       ordered-by user;
       junos:cli-feature "oneliner";
       description "Tracing parameters";
       leaf name {
         junos:cli-feature "nokeyword";
         type enumeration {
           enum "timer" {
             description "Trace internal timer events";
           }
           enum "routing-socket" {
             description "Trace routing socket messages";
           }
           enum "parse" {
             description "Trace configuration processing";
           }
           enum "config" {
             description "Trace configuration download processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "thread" {
             description "Trace thread processing";
           }
           enum "high-availability" {
             description "Trace high-availability operations";
           }
           enum "next-hop-tunnels" {
             description "Trace next-hop-tunnels operations";
           }
           enum "all" {
             description "Trace everything";
           }
           enum "ams" {
             description "Trace AMS events";
           }
           enum "lic" {
             description "Trace License events";
           }
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
   }
 }
