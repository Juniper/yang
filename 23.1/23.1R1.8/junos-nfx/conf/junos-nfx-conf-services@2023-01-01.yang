/*
 * Copyright (c) 2023 Juniper Networks, Inc.
 * All rights reserved.
 */
 module junos-nfx-conf-services {
   namespace "http://yang.juniper.net/junos-nfx/conf/services";

   prefix jc-services;

   import junos-common-types {
     prefix jt;
     revision-date 2023-01-01;
   }

   import junos-nfx-conf-root {
     prefix jc;
     revision-date 2023-01-01;
   }

   organization "Juniper Networks, Inc.";

   contact "yang-support@juniper.net";

   description "Junos services configuration module";

   revision 2023-01-01 {
     description "Junos: 23.1R1.8";
   }

   augment /jc:configuration {
     uses services-group;
   }
   augment /jc:configuration/jc:groups {
     uses services-group;
   }
   grouping services-group {
     container services {
       description "System services";
       uses apply-advanced;
       container jinsightd {
         presence "enable jinsightd";
         description "Health Monitoring services";
         uses apply-advanced;
         container traceoptions {
           description "Jinsight trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace all events";
                 }
                 enum "rule-engine" {
                   description "Log configuration rule engine";
                 }
                 enum "core" {
                   description "Trace core message events";
                 }
                 enum "database" {
                   description "Trace database events";
                 }
                 enum "timer" {
                   description "Trace timer events";
                 }
               }
             }
           }
         }
         container subscribe {
           presence "enable subscribe";
           description "Subscription";
           uses apply-advanced;
           leaf health-monitor {
             description "Health-monitor parameters";
             type empty;
           }
         }
       }
       container fixed-wireless-access {
         description "Configuration for fixed wireless access service";
         uses apply-advanced;
         list control-plane {
           key name;
           ordered-by user;
           description "S11 configuration";
           max-elements 16;
           leaf name {
             description "S11 connection name";
             type string {
               length "1 .. 63";
             }
           }
           uses apply-advanced;
           container s11 {
             description "S11 IP address";
             uses apply-advanced;
             leaf v4-address {
               description "IPv4 address configured on interface";
               type jt:ipv4addr;
             }
             leaf path-management {
               description "Enable/disable path management";
               default "enable";
               type enumeration {
                 enum "enable" {
                   description "Enable parameter";
                 }
                 enum "disable" {
                   description "Disable parameter";
                 }
               }
             }
           }
         }
         list apn {
           key name;
           ordered-by user;
           description "Configure access point names for fixed wireless connections";
           leaf name {
             description "Access point name";
             type string {
             }
           }
           uses apply-advanced;
           leaf description {
             description "Text description of APN";
             type string {
             }
           }
           leaf apn-data-type {
             description "Specify APN data type";
             default "ipv4";
             type enumeration {
               enum "ipv4" {
                 description "IPv4 Data type";
               }
             }
           }
           leaf aaa-profile {
             description "Specify AAA profile for Authorization and Accounting";
             type string {
               length "1 .. 80";
             }
           }
           leaf dynamic-profile {
             description "Dynamic profile for the apn";
             type string {
               length "1 .. 80";
             }
           }
           leaf ipv4-address-pool {
             description "IPv4 address pool for the apn";
             type string {
               length "1 .. 80";
             }
           }
           leaf routing-instance {
             description "Routing instance used for redirect";
             type union {
               type string {
                 pattern "default";
               }
               type string {
               }
             }
           }
           container authentication {
             description "FWA tunnel authentication";
             uses fwa-authentication-type;
           }
         }
         list data-plane {
           key name;
           ordered-by user;
           description "S1-U configuration";
           max-elements 1;
           leaf name {
             description "S1-U connection name";
             type string {
               length "1 .. 63";
             }
           }
           uses apply-advanced;
           container s1-u {
             description "S1-U IP address";
             uses apply-advanced;
             leaf v4-address {
               description "IPv4 address configured on interface";
               type jt:ipv4addr;
             }
           }
         }
         leaf-list anchor-point {
           ordered-by user;
           description "Interface used for GTP-U tunnel termination";
           type string {
             length "1 .. 64";
           }
         }
         container traceoptions {
           description "Fixed wirelss access service trace options";
           uses bbefwa-trace-options-type;
         }
       }
       container captive-portal-content-delivery {
         description "Configuration for captive portal and content delivery service";
         uses apply-advanced;
         leaf auto-deactivate {
           description "Deactivate content delivery service";
           type string;
         }
         list rule {
           key name;
           ordered-by user;
           description "Define a captive portal content delivery rule";
           uses cpcd-rule-object-type;
         }
         list rule-set {
           key name;
           ordered-by user;
           description "Define a set of captive portal content delivery rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list profile {
           key name;
           ordered-by user;
           description "One or more rule/rule set in the profile";
           leaf name {
             description "Profile name";
             type string {
               length "1 .. 63";
             }
           }
           uses apply-advanced;
           choice cpcd_rules_choice {
             case case_1 {
               leaf dynamic {
                 description "Dynamic profile flag";
                 type empty;
               }
             }
             case case_2 {
               list cpcd-rules {
                 key name;
                 ordered-by user;
                 description "List of captive portal content delivery rules";
                 leaf name {
                   type string {
                     length "1 .. 63";
                   }
                 }
                 uses apply-advanced;
               }
             }
             case case_3 {
               list cpcd-rule-sets {
                 key name;
                 ordered-by user;
                 description "List of captive portal content delivery rule sets";
                 leaf name {
                   type string {
                     length "1 .. 63";
                   }
                 }
                 uses apply-advanced;
               }
             }
           }
           container ipda-rewrite-options {
             description "Ipda rewrite options";
             uses apply-advanced;
             leaf destination-address {
               description "Default ipda rewrite IP address";
               type jt:ipaddr;
             }
             leaf destination-port {
               description "Default ipda rewrite port";
               type union {
                 type string {
                   pattern "<.*>|$.*";
                 }
                 type uint16 {
                   range "1 .. 65535";
                 }
               }
             }
           }
           container http-redirect-options {
             description "Http redirect options";
             uses apply-advanced;
             leaf url {
               description "URL of the captive portal file";
               type string {
               }
             }
           }
           leaf auto-deactivate {
             description "Deactivate content delivery service";
             type enumeration {
               enum "never" {
                 description "Deactivate never";
               }
               enum "initial-get" {
                 description "Deactivate on initial http-get";
               }
             }
           }
         }
         container traceoptions {
           description "Captive portal and content delivery trace options";
           uses cpcd-trace-options-type;
         }
       }
       container dynamic-flow-capture {
         description "Configure Dynamic Flow Capture parameters";
         uses apply-advanced;
         leaf g-max-duplicates {
           description "Maximum content destinations for the capture group";
           default "3";
           type union {
             type string {
               pattern "<.*>|$.*";
             }
             type uint32 {
               range "1 .. 64";
             }
           }
         }
         leaf g-duplicates-dropped-periodicity {
           description "Periodicity of DuplicatesDropped notification in secs";
           default "30";
           type union {
             type string {
               pattern "<.*>|$.*";
             }
             type uint32 {
               range "1 .. 255";
             }
           }
         }
         list capture-group {
           key name;
           ordered-by user;
           description "Configure DFC group parameters";
           max-elements 16;
           uses dfc_group_type;
         }
         container traceoptions {
           presence "enable traceoptions";
           description "Trace options for dynamic-flow-capture service";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
       }
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           type union {
             type jt:interface-name;
             type string {
               pattern "<.*>|$.*";
             }
           }
         }
         leaf tunnel-interface {
           description "Tunnel interface through which flow-tap would communicate with MD";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               type string;
             }
           }
           case case_2 {
             list logical-system {
               key name;
               ordered-by user;
               description "Logical system to be used for radius flow tap";
               max-elements 1;
               leaf name {
                 description "Logical system name";
                 type string;
               }
               uses apply-advanced;
               leaf routing-instance {
                 description "Routing instance to be used for radius flow tap";
                 type string;
               }
             }
           }
         }
         list policy {
           key name;
           ordered-by user;
           description "Policy";
           leaf name {
             description "Policy Name";
             type string {
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container mobile-flow-tap {
         description "Configure mobile triggered flow-tap parameters";
         uses apply-advanced;
         container source-interface {
           presence "enable source-interface";
           description "Source interface from which IRI packets will be sent";
           leaf interface-name {
             description "Interface name";
             type union {
               type jt:interface-name;
               type string {
                 pattern "<.*>|$.*";
               }
             }
           }
           leaf ipv4-address {
             description "Source IPv4 address to be used";
             type jt:ipv4addr;
           }
         }
       }
       container flow-monitoring {
         presence "enable flow-monitoring";
         description "Configure flow monitoring";
         uses apply-advanced;
         container version9 {
           description "Version 9 configuration";
           uses apply-advanced;
           list template {
             key name;
             ordered-by user;
             description "One or more version 9 templates";
             max-elements 10;
             uses version9-template;
           }
         }
         container version-ipfix {
           description "Version IP-Fix configuration";
           uses apply-advanced;
           list template {
             key name;
             ordered-by user;
             description "One or more version ip-fix templates";
             max-elements 10;
             uses version-ipfix-template;
           }
         }
       }
       container jdaf {
         description "Juniper distributed application framework (JDAF)";
         uses apply-advanced;
         leaf-list routing-instances {
           ordered-by user;
           description "List of routing-instance name for JDAF clients";
           type string {
             length "1 .. 128";
           }
         }
       }
       container rpm {
         presence "enable rpm";
         description "Real-time performance monitoring";
         uses apply-advanced;
         container traceoptions {
           description "RMOPD trace options";
           uses rmopd-traceoptions;
         }
         container bgp {
           description "BGP options for real-time performance monitoring";
           uses apply-advanced;
           leaf probe-type {
             description "RPM-BGP probe request type";
             default "icmp-ping";
             type enumeration {
               enum "icmp-ping" {
                 description "Send ICMP echo request to target address";
               }
               enum "icmp-ping-timestamp" {
                 description "Send ICMP timestamp request to target address";
               }
               enum "icmp6-ping" {
                 description "Send ICMP6 echo request to target address";
               }
               enum "tcp-ping" {
                 description "Send TCP packets to target";
               }
               enum "udp-ping" {
                 description "Send UDP packets to target";
               }
               enum "udp-ping-timestamp" {
                 description "Send UDP packets with timestamp to target";
               }
             }
           }
           leaf probe-count {
             description "Total number of probes per test";
             default "1";
             type union {
               type string {
                 pattern "<.*>|$.*";
               }
               type uint32 {
                 range "1 .. 15";
               }
             }
           }
           leaf probe-interval {
             description "Delay between probes";
             default "3";
             units "seconds";
             type union {
               type string {
                 pattern "<.*>|$.*";
               }
               type uint32 {
                 range "1 .. 255";
               }
             }
           }
           leaf test-interval {
             description "Delay between tests";
             default "1";
             units "seconds";
             type union {
               type string {
                 pattern "<.*>|$.*";
               }
               type uint32 {
                 range "0 .. 86400";
               }
             }
           }
           leaf destination-port {
             description "TCP/UDP port number";
             type union {
               type string {
                 pattern "<.*>|$.*";
               }
               type uint16 {
                 range "7 .. 65535";
               }
             }
           }
           leaf history-size {
             description "Number of stored history entries";
             default "50";
             type union {
               type string {
                 pattern "<.*>|$.*";
               }
               type uint32 {
                 range "0 .. 512";
               }
             }
           }
           leaf moving-average-size {
             description "Number of samples used for moving average";
             default "0";
             type union {
               type string {
                 pattern "<.*>|$.*";
               }
               type uint32 {
                 range "0 .. 512";
               }
             }
           }
           leaf data-size {
             description "Size of the data portion of the probes";
             default "0";
             type union {
               type string {
                 pattern "<.*>|$.*";
               }
               type uint32 {
                 range "0 .. 65400";
               }
             }
           }
           leaf data-fill {
             description "Define contents of the data portion of the probes";
             type string {
               length "1 .. 2048";
             }
           }
           leaf ttl {
             description "Time to Live (hop-limit) value for an RPM IPv4(IPv6) packet";
             default "64";
             type union {
               type string {
                 pattern "<.*>|$.*";
               }
               type uint32 {
                 range "1 .. 254";
               }
             }
           }
           list logical-system {
             key name;
             description "Logical systems";
             uses bgp-logical-system;
           }
           list routing-instances {
             key name;
             description "Routing instances";
             uses bgp-routing-instances;
           }
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
               }
               choice target-type {
                 case case_1 {
                   container target {
                     presence "enable target";
                     description "Target address generation for scale test config";
                     uses apply-advanced;
                     leaf address-base {
                       description "Base address of target host in a.b.c.d format";
                       type jt:ipv4addr;
                     }
                     leaf step {
                       description "Steps to increment target address in a.b.c.d format";
                       type jt:ipv4addr;
                     }
                     leaf count {
                       description "Target address count";
                       type union {
                         type string {
                           pattern "<.*>|$.*";
                         }
                         type uint32 {
                           range "1 .. 500000";
                         }
                       }
                     }
                   }
                 }
                 case case_2 {
                   container target-inet6 {
                     presence "enable target-inet6";
                     description "IPv6 target address generation for scale test config";
                     uses apply-advanced;
                     leaf address-base {
                       description "Base address of target host in a:b:c:d:e:f:g:h format";
                       type jt:ipv6addr;
                     }
                     leaf step {
                       description "Steps to increment target address in a:b:c:d:e:f:g:h format";
                       type jt:ipv6addr;
                     }
                     leaf count {
                       description "Target address count";
                       type union {
                         type string {
                           pattern "<.*>|$.*";
                         }
                         type uint32 {
                           range "1 .. 500000";
                         }
                       }
                     }
                   }
                 }
               }
               choice source-type {
                 case case_1 {
                   container source {
                     presence "enable source";
                     description "Source address generation in scale tests";
                     uses apply-advanced;
                     leaf address-base {
                       description "Base address of host in a.b.c.d format";
                       type jt:ipv4addr;
                     }
                     leaf step {
                       description "Steps to increment src address in a.b.c.d format";
                       type jt:ipv4addr;
                     }
                     leaf count {
                       description "Source-address count";
                       type union {
                         type string {
                           pattern "<.*>|$.*";
                         }
                         type uint32 {
                           range "1 .. 500000";
                         }
                       }
                     }
                   }
                 }
                 case case_2 {
                   container source-inet6 {
                     presence "enable source-inet6";
                     description "IPv6 source address generation in scale tests";
                     uses apply-advanced;
                     leaf address-base {
                       description "Base address of host in a:b:c:d:e:f:g:h format";
                       type jt:ipv6addr;
                     }
                     leaf step {
                       description "Steps to increment src address in a:b:c:d:e:f:g:h format";
                       type jt:ipv6addr;
                     }
                     leaf count {
                       description "Source-address count";
                       type union {
                         type string {
                           pattern "<.*>|$.*";
                         }
                         type uint32 {
                           range "1 .. 500000";
                         }
                       }
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                 }
                 leaf subunit-cnt {
                   description "Subunit count for destination interface for scale test";
                   type union {
                     type string {
                       pattern "<.*>|$.*";
                     }
                     type uint32 {
                       range "1 .. 500000";
                     }
                   }
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     type jt:ipv4addr;
                   }
                 }
                 case case_2 {
                   leaf inet6-address {
                     description "Inet6 Address of target host";
                     type jt:ipv6addr;
                   }
                 }
                 case case_3 {
                   leaf url {
                     description "Fully formed target URL";
                     type string;
                   }
                 }
                 case case_4 {
                   leaf inet6-url {
                     description "Fully formed target IPV6 URL";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               type jt:ipv4addr;
             }
             leaf routing-instance {
               description "Routing instance used by probes";
               type string {
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 512";
                 }
               }
             }
             leaf dscp-code-points {
               description "Differentiated Services code point bits or alias";
               default "000000";
               type string {
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf hardware-timestamp {
               description "Packet Forwarding Engine updates timestamps";
               type empty;
             }
             leaf one-way-hardware-timestamp {
               description "Enable hardware timestamps for one-way measurements";
               type empty;
             }
             leaf next-hop {
               description "Next-hop to which probe should be sent";
               type jt:ipv4addr;
             }
           }
         }
         container probe-server {
           description "ICMP/TCP/UDP probe server";
           uses apply-advanced;
           container icmp {
             description "ICMP probe server";
             uses apply-advanced;
             leaf destination-interface {
               description "Name of output interface for probes";
               type union {
                 type jt:interface-name;
                 type string {
                   pattern "<.*>|$.*";
                 }
               }
             }
           }
           container tcp {
             description "TCP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
           container udp {
             description "UDP probe server";
             uses apply-advanced;
             leaf port {
               description "Port number 7 through 65535";
               type union {
                 type uint16;
                 type string {
                   pattern "<.*>|$.*";
                 }
               }
             }
             leaf destination-interface {
               description "Name of output interface for probes";
               type union {
                 type jt:interface-name;
                 type string {
                   pattern "<.*>|$.*";
                 }
               }
             }
           }
         }
         leaf probe-limit {
           description "Maximum number of concurrent probes allowed";
           default "100";
           type union {
             type string {
               pattern "<.*>|$.*";
             }
             type uint32 {
               range "1 .. 500";
             }
           }
         }
         container rfc2544-benchmarking {
           presence "enable rfc2544-benchmarking";
           description "Rfc2544 benchmarking tests";
           uses apply-advanced;
           container profiles {
             description "Rfc2544 test profiles";
             uses apply-advanced;
             list test-profile {
               key name;
               ordered-by user;
               description "Test-profile definition";
               leaf name {
                 description "Test name";
                 type string {
                   length "1 .. 32";
                 }
               }
               uses apply-advanced;
               leaf test-type {
                 description "Rfc2544 test type";
                 default "throughput";
                 type enumeration {
                   enum "throughput" {
                     description "Rfc2544 throughput test";
                   }
                   enum "latency" {
                     description "Rfc2544 latency test";
                   }
                   enum "frame-loss" {
                     description "Rfc2544 frame-loss test";
                   }
                   enum "back-back-frames" {
                     description "Rfc2544 back to back frames test";
                   }
                 }
               }
               leaf-list packet-size {
                 ordered-by user;
                 description "Size of the test packet";
                 type union {
                   type string {
                     pattern "<.*>|$.*";
                   }
                   type uint32 {
                     range "64 .. 9216";
                   }
                 }
               }
               leaf bandwidth-kbps {
                 description "Theoretical max service bandwidth in kbps";
                 default "10000";
                 type union {
                   type string {
                     pattern "<.*>|$.*";
                   }
                   type uint32;
                 }
               }
               leaf step-percent {
                 description "Step percent for test";
                 default "10";
                 type union {
                   type string {
                     pattern "<.*>|$.*";
                   }
                   type uint32 {
                     range "1 .. 100";
                   }
                 }
               }
             }
           }
           container tests {
             presence "enable tests";
             description "Rfc2544 test configuration";
             uses apply-advanced;
             list test-name {
               key name;
               ordered-by user;
               description "Test definition";
               leaf name {
                 description "Test name";
                 type string {
                   length "1 .. 32";
                 }
               }
               uses apply-advanced;
               leaf test-profile {
                 description "Name of the test profile";
                 type string;
               }
               leaf source-mac-address {
                 description "MAC address of source host in xx:xx:xx:xx:xx:xx format -Generator MAC";
                 type jt:mac-unicast;
               }
               leaf destination-mac-address {
                 description "MAC address of destination host in xx:xx:xx:xx:xx:xx format -Reflector MAC";
                 type jt:mac-unicast;
               }
               leaf ovlan-id {
                 description "Outer vlan id";
                 type union {
                   type string {
                     pattern "<.*>|$.*";
                   }
                   type int32 {
                     range "0 .. 4094";
                   }
                 }
               }
               leaf ovlan-priority {
                 description "Outer vlan priority";
                 type union {
                   type string {
                     pattern "<.*>|$.*";
                   }
                   type int32 {
                     range "0 .. 7";
                   }
                 }
               }
               leaf ovlan-cfi {
                 description "Outer vlan CFI bit";
                 type union {
                   type string {
                     pattern "<.*>|$.*";
                   }
                   type int32 {
                     range "0 .. 1";
                   }
                 }
               }
               leaf outer-tag-protocol-id {
                 description "Outer tag protocol id";
                 default "0x8100";
                 type string {
                 }
               }
               leaf ivlan-id {
                 description "Inner vlan id";
                 type union {
                   type string {
                     pattern "<.*>|$.*";
                   }
                   type int32 {
                     range "0 .. 4094";
                   }
                 }
               }
               leaf ivlan-priority {
                 description "Inner vlan priority";
                 type union {
                   type string {
                     pattern "<.*>|$.*";
                   }
                   type int32 {
                     range "0 .. 7";
                   }
                 }
               }
               leaf ivlan-cfi {
                 description "Inner vlan CFI bit";
                 type union {
                   type string {
                     pattern "<.*>|$.*";
                   }
                   type int32 {
                     range "0 .. 1";
                   }
                 }
               }
               leaf vlan-id {
                 description "VLAN identifier";
                 type union {
                   type string {
                     pattern "<.*>|$.*";
                   }
                   type int32 {
                     range "0 .. 4094";
                   }
                 }
               }
               leaf vlan-priority {
                 description "VLAN priority";
                 type union {
                   type string {
                     pattern "<.*>|$.*";
                   }
                   type int32 {
                     range "0 .. 7";
                   }
                 }
               }
               leaf vlan-cfi {
                 description "VLAN CFI bit";
                 type union {
                   type string {
                     pattern "<.*>|$.*";
                   }
                   type int32 {
                     range "0 .. 1";
                   }
                 }
               }
               leaf service-type {
                 description "Service type";
                 type enumeration {
                   enum "eline" {
                     description "Eline service";
                   }
                   enum "elan" {
                     description "Elan service";
                   }
                 }
               }
               leaf in-service {
                 description "Test executed in-service mode";
                 type empty;
               }
               leaf ip-swap {
                 description "Swap IP in the test payload";
                 type empty;
               }
               leaf udp-tcp-port-swap {
                 description "Swap UDP/TCP port in the test payload";
                 type empty;
               }
               leaf ignore-test-interface-state {
                 description "Ignore interface state to run the test";
                 type empty;
               }
               leaf check-test-interface-mtu {
                 description "Check interface MTU to run the test";
                 type empty;
               }
               leaf disable-signature-check {
                 description "Signature check disable";
                 type empty;
               }
               leaf forwarding-class {
                 description "Forwarding class assigned to the frames";
                 type string {
                 }
               }
               leaf packet-loss-priority {
                 description "Packet loss priority assigned to the frames";
                 type enumeration {
                   enum "low" {
                     description "Packet loss priority is low";
                   }
                   enum "high" {
                     description "Packet loss priority is high";
                   }
                   enum "medium-high" {
                     description "Packet loss priority is medium-high";
                   }
                 }
               }
               leaf dscp-code-points {
                 description "Differentiated Services code point bits or alias";
                 default "000000";
                 type string {
                 }
               }
               leaf mode {
                 description "Test mode";
                 type enumeration {
                   enum "reflect" {
                     description "Reflector end";
                   }
                   enum "initiate-and-terminate" {
                     description "Initiate and terminator";
                   }
                   enum "ethernet-loopback" {
                     description "Ethernet loopback";
                   }
                 }
               }
               leaf reflect-mode {
                 description "Reflect mode";
                 type enumeration {
                   enum "mac-swap" {
                     description "Mac swap ";
                   }
                   enum "no-mac-swap" {
                     description "No mac-swap";
                   }
                   enum "mac-rewrite" {
                     description "Mac-rewrite";
                   }
                 }
               }
               leaf family {
                 description "Family type";
                 type enumeration {
                   enum "inet" {
                     description "Inet family";
                   }
                   enum "ccc" {
                     description "CCC family ";
                   }
                   enum "bridge" {
                     description "Bridge family ";
                   }
                   enum "vpls" {
                     description "VPLS family ";
                   }
                 }
               }
               leaf reflect-etype {
                 description "Etype to match for reflect mode";
                 type union {
                   type string {
                     pattern "<.*>|$.*";
                   }
                   type uint32 {
                     range "1 .. 65535";
                   }
                 }
               }
               leaf direction {
                 description "Direction of test";
                 type enumeration {
                   enum "ingress" {
                     description "Pseudo-wire/Bridge/Vpls Ingress direction";
                   }
                   enum "egress" {
                     description "Pseudo-wire/Bridge/Vpls Egress direction";
                   }
                 }
               }
               leaf timestamp-format {
                 description "Format of timestamp values";
                 type enumeration {
                   enum "microseconds" {
                     description "Timestamps in microseconds";
                   }
                   enum "nanoseconds" {
                     description "Timestamps in nanoseconds";
                   }
                 }
               }
               leaf source-udp-port {
                 description "Source udp port";
                 type union {
                   type string {
                     pattern "<.*>|$.*";
                   }
                   type uint32 {
                     range "1 .. 65535";
                   }
                 }
               }
               leaf destination-udp-port {
                 description "Destination udp port";
                 type union {
                   type string {
                     pattern "<.*>|$.*";
                   }
                   type uint32 {
                     range "1 .. 65535";
                   }
                 }
               }
               leaf test-duration {
                 description "Test duration in minutes";
                 status deprecated;
                 default "10";
                 type union {
                   type string {
                     pattern "<.*>|$.*";
                   }
                   type uint32 {
                     range "1 .. 5000";
                   }
                 }
               }
               leaf test-iterator-duration {
                 description "Duration of each iteration in seconds";
                 type union {
                   type string {
                     pattern "<.*>|$.*";
                   }
                   type uint32 {
                     range "10 .. 1728000";
                   }
                 }
               }
               leaf test-finish-wait-duration {
                 description "Number of seconds to wait after test completes before stopping the test";
                 default "1";
                 type union {
                   type string {
                     pattern "<.*>|$.*";
                   }
                   type uint32 {
                     range "1 .. 60";
                   }
                 }
               }
               leaf transmit-failure-threshold {
                 description "Transmit failure-threshold (default 0.5%)";
                 default "0.5";
                 type decimal64 {
                   fraction-digits 9;
                   range "0 .. 100";
                 }
               }
               leaf receive-failure-threshold {
                 description "Receive failure-threshold (default 0%)";
                 default "0";
                 type decimal64 {
                   fraction-digits 9;
                   range "0 .. 100";
                 }
               }
               leaf test-iterator-pass-threshold {
                 description "Test pass-threshold (default 0.5%)";
                 default "0.5";
                 type decimal64 {
                   fraction-digits 9;
                   range "0 .. 100";
                 }
               }
               leaf halt-on-prefix-down {
                 description "Halt test on prefix down";
                 type empty;
               }
               leaf skip-arp-iteration {
                 description "Skip arp iteration in tests";
                 type empty;
               }
               leaf test-interface {
                 description "Name of interface(ifl) for test";
                 type union {
                   type jt:interface-name;
                   type string {
                     pattern "<.*>|$.*";
                   }
                 }
               }
               leaf reflector-port {
                 description "Front panel port number - ACX5048: [16-53], ACX5096: [64-95, 100-103]";
                 type union {
                   type uint32;
                   type string {
                     pattern "<.*>|$.*";
                   }
                 }
               }
               leaf destination-ipv4-address {
                 description "Destination address for test";
                 type jt:ipv4addr;
               }
               leaf source-ipv4-address {
                 description "Source address for test";
                 type jt:ipv4addr;
               }
             }
           }
         }
         container twamp {
           description "Two-way Active Measurement Protocol configuration";
           uses apply-advanced;
           leaf post-cli-implicit-firewall {
             description "Enable post cli implicit firewall";
             type empty;
           }
           container client {
             description "TWAMP client configuration";
             uses apply-advanced;
             list control-connection {
               key name;
               ordered-by user;
               description "TWAMP control session configuration";
               leaf name {
                 description "Client name";
                 type string {
                   length "1 .. 32";
                 }
               }
               uses apply-advanced;
               container authentication-mode {
                 description "Authentication modes";
                 uses apply-advanced;
                 leaf none {
                   description "No authentication or encryption";
                   type empty;
                 }
               }
               leaf destination-interface {
                 description "Name of output interface for all test sessions";
                 type union {
                   type jt:interface-name;
                   type string {
                     pattern "<.*>|$.*";
                   }
                 }
               }
               leaf persistent-results {
                 description "Displays the old results along with present. Default disable";
                 type empty;
               }
               leaf control-type {
                 description "TWAMP control connection type";
                 default "managed";
                 type enumeration {
                   enum "light" {
                     description "No control connection to manage test sessions";
                   }
                   enum "managed" {
                     description "Control connection will negotiate test sessions";
                   }
                 }
               }
               leaf tcp-keepidle {
                 description "Time to start TCP KEEPALIVEs on control connection (default 120)";
                 default "120";
                 units "seconds";
                 type union {
                   type string {
                     pattern "<.*>|$.*";
                   }
                   type uint32 {
                     range "1 .. 600";
                   }
                 }
               }
               leaf tcp-keepintvl {
                 description "Delay between succesive TCP KEEPALIVEs (default 5)";
                 default "5";
                 units "seconds";
                 type union {
                   type string {
                     pattern "<.*>|$.*";
                   }
                   type uint32 {
                     range "1 .. 600";
                   }
                 }
               }
               leaf tcp-keepcnt {
                 description "Number of TCP KEEPALIVEs sent (default 6)";
                 default "6";
                 type union {
                   type string {
                     pattern "<.*>|$.*";
                   }
                   type uint32 {
                     range "1 .. 50";
                   }
                 }
               }
               leaf destination-port {
                 description "TCP TWAMP client listening port for the test sessions. Default 862";
                 default "862";
                 type union {
                   type string {
                     pattern "<.*>|$.*";
                   }
                   type uint16 {
                     range "862 .. 65535";
                   }
                 }
               }
               leaf history-size {
                 description "Number of stored history entries";
                 default "50";
                 type union {
                   type string {
                     pattern "<.*>|$.*";
                   }
                   type uint32 {
                     range "0 .. 512";
                   }
                 }
               }
               leaf moving-average-size {
                 description "Number of samples used for moving average";
                 default "0";
                 type union {
                   type string {
                     pattern "<.*>|$.*";
                   }
                   type uint32 {
                     range "0 .. 512";
                   }
                 }
               }
               leaf routing-instance {
                 description "Routing instance used by the test sessions";
                 type string {
                 }
               }
               leaf target-address {
                 description "Destination IPv4 address of TWAMP responder";
                 type jt:ipv4addr;
               }
               leaf test-count {
                 description "Total number of test session iterations";
                 default "0";
                 type union {
                   type string {
                     pattern "<.*>|$.*";
                   }
                   type uint32 {
                     range "0 .. 4294967290";
                   }
                 }
               }
               leaf test-interval {
                 description "Delay between test session iterations";
                 default "1";
                 units "seconds";
                 type union {
                   type string {
                     pattern "<.*>|$.*";
                   }
                   type uint16 {
                     range "1 .. 255";
                   }
                 }
               }
               container traps {
                 description "Trap to send if threshold is met or exceeded";
                 uses apply-advanced;
                 leaf test-iteration-done {
                   description "All test sessions configured under the control connection have completed an iteration";
                   type empty;
                 }
                 leaf control-connection-closed {
                   description "Control connection closed";
                   type empty;
                 }
               }
               list test-session {
                 key name;
                 ordered-by user;
                 description "Test session details";
                 leaf name {
                   description "Test session name";
                   type string {
                     length "1 .. 32";
                   }
                 }
                 uses apply-advanced;
                 leaf source-address {
                   description "Source address of TWAMP Probes";
                   type jt:ipaddr;
                 }
                 container target-address {
                   presence "enable target-address";
                   description "Destination IPv4 or IPv6 address of TWAMP responder";
                   leaf address {
                     description "Address of TWAMP session reflector";
                     type jt:ipaddr;
                   }
                   leaf local-link {
                     description "Link scope for IPv6 link-local address";
                     type union {
                       type jt:interface-name;
                       type string {
                         pattern "<.*>|$.*";
                       }
                     }
                   }
                 }
                 leaf destination-port {
                   description "Target port number for test";
                   default "862";
                   type union {
                     type string {
                       pattern "<.*>|$.*";
                     }
                     type uint16 {
                       range "862 .. 65535";
                     }
                   }
                 }
                 leaf data-fill-with-zeros {
                   description "Fill contents of test packet with zeros";
                   type empty;
                 }
                 leaf data-size {
                   description "Size of the data portion of the probes";
                   default "60";
                   type union {
                     type string {
                       pattern "<.*>|$.*";
                     }
                     type uint16 {
                       range "60 .. 1400";
                     }
                   }
                 }
                 leaf dscp-code-points {
                   description "Differentiated Services code point bits or alias used for TCP control and UDP TWAMP test packets";
                   default "000000";
                   type string {
                   }
                 }
                 leaf ttl {
                   description "Time to Live (hop-limit) value for an RPM IPv4(IPv6) packet";
                   default "64";
                   type union {
                     type string {
                       pattern "<.*>|$.*";
                     }
                     type uint32 {
                       range "1 .. 254";
                     }
                   }
                 }
                 leaf probe-count {
                   description "Total number of probes per test";
                   default "1";
                   type union {
                     type string {
                       pattern "<.*>|$.*";
                     }
                     type uint32 {
                       range "1 .. 4294967290";
                     }
                   }
                 }
                 leaf probe-interval {
                   description "Delay between two consecutive probes";
                   default "1";
                   units "seconds";
                   type union {
                     type string {
                       pattern "<.*>|$.*";
                     }
                     type uint32 {
                       range "1 .. 255";
                     }
                   }
                 }
                 container thresholds {
                   presence "enable thresholds";
                   description "TWAMP test threshold values. Set 0 to disable respective threshold";
                   uses apply-advanced;
                   leaf successive-loss {
                     description "Successive probe loss count indicating probe failure";
                     default "1";
                     type union {
                       type string {
                         pattern "<.*>|$.*";
                       }
                       type uint32 {
                         range "0 .. 15";
                       }
                     }
                   }
                   leaf total-loss {
                     description "Total probe loss count indicating test failure";
                     default "1";
                     type union {
                       type string {
                         pattern "<.*>|$.*";
                       }
                       type uint32 {
                         range "0 .. 4294967290";
                       }
                     }
                   }
                   leaf rtt {
                     description "Maximum round trip time per probe";
                     default "0";
                     units "microseconds";
                     type union {
                       type string {
                         pattern "<.*>|$.*";
                       }
                       type uint32 {
                         range "0 .. 60000000";
                       }
                     }
                   }
                   leaf max-rtt {
                     description "Maximum round trip time per test";
                     status deprecated;
                     default "0";
                     units "microseconds";
                     type union {
                       type string {
                         pattern "<.*>|$.*";
                       }
                       type uint32 {
                         range "0 .. 60000000";
                       }
                     }
                   }
                   leaf jitter-rtt {
                     description "Maximum jitter per test";
                     default "0";
                     units "microseconds";
                     type union {
                       type string {
                         pattern "<.*>|$.*";
                       }
                       type uint32 {
                         range "0 .. 60000000";
                       }
                     }
                   }
                   leaf std-dev-rtt {
                     description "Maximum standard deviation per test";
                     default "0";
                     units "microseconds";
                     type union {
                       type string {
                         pattern "<.*>|$.*";
                       }
                       type uint32 {
                         range "0 .. 60000000";
                       }
                     }
                   }
                   leaf egress-time {
                     description "Maximum source to destination time per probe";
                     default "0";
                     units "microseconds";
                     type union {
                       type string {
                         pattern "<.*>|$.*";
                       }
                       type uint32 {
                         range "0 .. 60000000";
                       }
                     }
                   }
                   leaf ingress-time {
                     description "Maximum destination to source time per probe";
                     default "0";
                     units "microseconds";
                     type union {
                       type string {
                         pattern "<.*>|$.*";
                       }
                       type uint32 {
                         range "0 .. 60000000";
                       }
                     }
                   }
                   leaf jitter-ingress {
                     description "Maximum destination to source jitter per test";
                     default "0";
                     units "microseconds";
                     type union {
                       type string {
                         pattern "<.*>|$.*";
                       }
                       type uint32 {
                         range "0 .. 60000000";
                       }
                     }
                   }
                   leaf jitter-egress {
                     description "Maximum source to destination jitter per test";
                     default "0";
                     units "microseconds";
                     type union {
                       type string {
                         pattern "<.*>|$.*";
                       }
                       type uint32 {
                         range "0 .. 60000000";
                       }
                     }
                   }
                   leaf std-dev-ingress {
                     description "Maximum destination to source standard deviation per test";
                     default "0";
                     units "microseconds";
                     type union {
                       type string {
                         pattern "<.*>|$.*";
                       }
                       type uint32 {
                         range "0 .. 60000000";
                       }
                     }
                   }
                   leaf std-dev-egress {
                     description "Maximum source to destination standard deviation per test";
                     default "0";
                     units "microseconds";
                     type union {
                       type string {
                         pattern "<.*>|$.*";
                       }
                       type uint32 {
                         range "0 .. 60000000";
                       }
                     }
                   }
                 }
                 container traps {
                   description "Trap to send if threshold is met or exceeded";
                   uses apply-advanced;
                   leaf probe-failure {
                     description "Successive probe loss threshold reached";
                     type empty;
                   }
                   leaf test-failure {
                     description "Total probe loss threshold reached";
                     type empty;
                   }
                   leaf test-completion {
                     description "Test completed";
                     type empty;
                   }
                   leaf rtt-exceeded {
                     description "Exceeded maximum round trip time threshold";
                     type empty;
                   }
                   leaf max-rtt-exceeded {
                     description "Exceeded maximum round trip time threshold at the end of per test";
                     type empty;
                   }
                   leaf std-dev-exceeded {
                     description "Exceeded round trip time standard deviation threshold";
                     type empty;
                   }
                   leaf jitter-exceeded {
                     description "Exceeded jitter in round trip time threshold";
                     type empty;
                   }
                   leaf ingress-time-exceeded {
                     description "Exceeded maximum ingress time threshold";
                     type empty;
                   }
                   leaf ingress-std-dev-exceeded {
                     description "Exceeded ingress time standard deviation threshold";
                     type empty;
                   }
                   leaf ingress-jitter-exceeded {
                     description "Exceeded jitter in ingress time threshold";
                     type empty;
                   }
                   leaf egress-time-exceeded {
                     description "Exceeded maximum egress time threshold";
                     type empty;
                   }
                   leaf egress-std-dev-exceeded {
                     description "Exceeded egress time standard deviation threshold";
                     type empty;
                   }
                   leaf egress-jitter-exceeded {
                     description "Exceeded jitter in egress time threshold";
                     type empty;
                   }
                 }
               }
             }
           }
           container server {
             description "TWAMP server configuration";
             uses apply-advanced;
             leaf tcp-keepidle {
               description "Time to start TCP KEEPALIVEs on control connection (default 120)";
               default "120";
               units "seconds";
               type union {
                 type string {
                   pattern "<.*>|$.*";
                 }
                 type uint32 {
                   range "1 .. 600";
                 }
               }
             }
             leaf tcp-keepintvl {
               description "Delay between succesive TCP KEEPALIVEs (default 5)";
               default "5";
               units "seconds";
               type union {
                 type string {
                   pattern "<.*>|$.*";
                 }
                 type uint32 {
                   range "1 .. 600";
                 }
               }
             }
             leaf tcp-keepcnt {
               description "Number of TCP KEEPALIVEs sent (default 6)";
               default "6";
               type union {
                 type string {
                   pattern "<.*>|$.*";
                 }
                 type uint32 {
                   range "1 .. 50";
                 }
               }
             }
             list routing-instance-list {
               key name;
               ordered-by user;
               description "List of allowed routing instances,not more than 100, along with ports";
               leaf name {
                 description "Name of the routing instance";
                 type string {
                 }
               }
               uses apply-advanced;
               leaf port {
                 description "Port to be used by the routing instance";
                 type union {
                   type string {
                     pattern "<.*>|$.*";
                   }
                   type uint32 {
                     range "1 .. 65535";
                   }
                 }
               }
             }
             container authentication-mode {
               description "Authentication modes";
               uses apply-advanced;
               leaf none {
                 description "No authentication or encryption";
                 type empty;
               }
               container authenticated {
                 presence "enable authenticated";
                 description "Authenticated mode";
                 leaf control-only {
                   description "Authentication mode only for TWAMP control protocol";
                   status deprecated;
                   type empty;
                 }
               }
               container encrypted {
                 presence "enable encrypted";
                 description "Encrypted mode";
                 leaf control-only {
                   description "Encryption mode only for TWAMP control protocol";
                   status deprecated;
                   type empty;
                 }
               }
               leaf control-only-encrypted {
                 description "Encrypted control and unauthenticated data mode";
                 type empty;
               }
             }
             list authentication-key-chain {
               key name;
               ordered-by user;
               description "Authentication key chain configuration";
               uses twamp-authentication-key-chain;
             }
             leaf server-inactivity-timeout {
               description "Control packet idle timeout value in minutes, 0 to disable";
               default "15";
               units "minutes";
               type union {
                 type string {
                   pattern "<.*>|$.*";
                 }
                 type uint32 {
                   range "0 .. 30";
                 }
               }
             }
             leaf max-connection-duration {
               description "Maximum Connection duration in hours, 0 to disable";
               default "0";
               units "hours";
               type union {
                 type string {
                   pattern "<.*>|$.*";
                 }
                 type uint32 {
                   range "0 .. 120";
                 }
               }
             }
             leaf maximum-sessions {
               description "Maximum number of test sessions for the server";
               default "64";
               type union {
                 type string {
                   pattern "<.*>|$.*";
                 }
                 type uint32 {
                   range "1 .. 2048";
                 }
               }
             }
             leaf maximum-sessions-per-connection {
               description "Maximum number of test sessions per client connection";
               type union {
                 type string {
                   pattern "<.*>|$.*";
                 }
                 type uint32 {
                   range "1 .. 1024";
                 }
               }
             }
             leaf maximum-connections {
               description "Maximum number of connections for the server";
               default "64";
               type union {
                 type string {
                   pattern "<.*>|$.*";
                 }
                 type uint32 {
                   range "1 .. 1000";
                 }
               }
             }
             leaf maximum-connections-per-client {
               description "Maximum number of server connections per client";
               type union {
                 type string {
                   pattern "<.*>|$.*";
                 }
                 type uint32 {
                   range "1 .. 500";
                 }
               }
             }
             leaf port {
               description "TWAMP server listening port";
               default "862";
               type union {
                 type string {
                   pattern "<.*>|$.*";
                 }
                 type uint32 {
                   range "1 .. 65535";
                 }
               }
             }
             list client-list {
               key name;
               ordered-by user;
               description "List of allowed clients";
               leaf name {
                 description "Name of client list";
                 type string {
                   length "1 .. 127";
                 }
               }
               uses apply-advanced;
               list address {
                 key name;
                 ordered-by user;
                 description "IPv4 prefix of TWAMP client";
                 leaf name {
                   description "IPv4 prefix of TWAMP client";
                   type jt:ipv4prefix;
                 }
                 uses apply-advanced;
               }
             }
             container light {
               presence "enable light";
               description "Enable TWAMP server for light control on the default port";
               uses apply-advanced;
               leaf-list port {
                 ordered-by user;
                 description "UDP ports reflecting TWAMP light test packets";
                 type union {
                   type uint16;
                   type string {
                     pattern "<.*>|$.*";
                   }
                 }
                 max-elements 1000;
               }
             }
           }
         }
       }
       container video-monitoring {
         presence "enable video-monitoring";
         description "Video monitoring service";
         uses apply-advanced;
         list templates {
           key name;
           ordered-by user;
           description "Template for MDI flows";
           leaf name {
             description "Name of template";
             type string {
               length "1 .. 32";
             }
           }
           uses apply-advanced;
           leaf interval-duration {
             description "Monitoring interval in sec";
             type union {
               type string {
                 pattern "<.*>|$.*";
               }
               type uint32 {
                 range "1 .. 50";
               }
             }
           }
           leaf inactive-timeout {
             description "Inactive timeout for idle flow in sec";
             type union {
               type string {
                 pattern "<.*>|$.*";
               }
               type uint32 {
                 range "30 .. 300";
               }
             }
           }
           container rate {
             description "Media rate or layer3 pps";
             uses apply-advanced;
             choice rate-choice {
               case case_1 {
                 leaf media {
                   description "Constant bit rate in bps";
                   type string;
                 }
               }
               case case_2 {
                 leaf layer3 {
                   description "Layer3 packet rate in pps";
                   type string;
                 }
               }
             }
           }
           container delay-factor {
             description "Delay factor related parameters";
             uses apply-advanced;
             container threshold {
               description "Threshold for delay factor alarm";
               uses apply-advanced;
               leaf info {
                 description "Threshold for information alarm";
                 units "milli-sec";
                 type decimal64 {
                   fraction-digits 9;
                   range "0 .. 65535";
                 }
               }
               leaf warning {
                 description "Threshold for warning alarm";
                 units "milli-sec";
                 type decimal64 {
                   fraction-digits 9;
                   range "0 .. 65535";
                 }
               }
               leaf critical {
                 description "Threshold for critical alarm";
                 units "milli-sec";
                 type decimal64 {
                   fraction-digits 9;
                   range "0 .. 65535";
                 }
               }
             }
             choice enable-disable {
               case case_1 {
                 leaf disable {
                   description "Disable DF Calculation";
                   type empty;
                 }
               }
             }
           }
           container media-loss-rate {
             description "MLR related parameters";
             uses apply-advanced;
             container threshold {
               description "Threshold for MLR alarm";
               uses apply-advanced;
               container info {
                 description "Threshold for information alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 9;
                         range "0 .. 100";
                       }
                     }
                   }
                 }
               }
               container warning {
                 description "Threshold for warning alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 9;
                         range "0 .. 100";
                       }
                     }
                   }
                 }
               }
               container critical {
                 description "Threshold for critical alarm";
                 uses apply-advanced;
                 choice mlr-threshold-choice {
                   case case_1 {
                     leaf packet-count {
                       description "MLR threshold value in packets count";
                       type jt:unsigned-float;
                     }
                   }
                   case case_2 {
                     leaf percentage {
                       description "MLR threshold value in percentage";
                       type decimal64 {
                         fraction-digits 9;
                         range "0 .. 100";
                       }
                     }
                   }
                 }
               }
             }
             choice enable-disable {
               case case_1 {
                 leaf disable {
                   description "Disable MLR Caltulation";
                   type empty;
                 }
               }
             }
           }
           container media-rate-variation {
             description "MRV related parameters";
             uses apply-advanced;
             container threshold {
               description "Threshold for MRV alarm";
               uses apply-advanced;
               leaf info {
                 description "Threshold for information alarm";
                 type decimal64 {
                   fraction-digits 9;
                   range "0 .. 100";
                 }
               }
               leaf warning {
                 description "Threshold for warning alarm";
                 type decimal64 {
                   fraction-digits 9;
                   range "0 .. 100";
                 }
               }
               leaf critical {
                 description "Threshold for critical alarm";
                 type decimal64 {
                   fraction-digits 9;
                   range "0 .. 100";
                 }
               }
             }
             choice enable-disable {
               case case_1 {
                 leaf disable {
                   description "Disable MRV Caltulation";
                   type empty;
                 }
               }
             }
           }
           leaf media-packets-count-in-layer3 {
             description "Number of media packets in a IP packet";
             type union {
               type string {
                 pattern "<.*>|$.*";
               }
               type uint32 {
                 range "1 .. 32";
               }
             }
           }
           leaf media-packet-size {
             description "Size of media packet";
             type union {
               type string {
                 pattern "<.*>|$.*";
               }
               type uint32 {
                 range "1 .. 2048";
               }
             }
           }
         }
         list interfaces {
           key name;
           ordered-by user;
           description "Interfaces to enable video monitoring";
           leaf name {
             description "Name of IFL";
             type union {
               type jt:interface-unit;
               type string {
                 pattern "<.*>|$.*";
               }
             }
           }
           uses apply-advanced;
           container family {
             description "Protocol family";
             uses apply-advanced;
             container inet {
               description "IPv4 flows";
               uses apply-advanced;
               list input-flows {
                 key name;
                 ordered-by user;
                 description "Input flows informations";
                 leaf name {
                   description "Name of flow";
                   type string {
                     length "1 .. 32";
                   }
                 }
                 uses apply-advanced;
                 leaf-list source-address {
                   ordered-by user;
                   description "Prefix to match";
                   type jt:ipv4prefix;
                   max-elements 32;
                 }
                 leaf-list destination-address {
                   ordered-by user;
                   description "Prefix to match";
                   type jt:ipv4prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf-list source-address {
                   ordered-by user;
                   description "Prefix to match";
                   type jt:ipv4prefix;
                   max-elements 32;
                 }
                 leaf-list destination-address {
                   ordered-by user;
                   description "Prefix to match";
                   type jt:ipv4prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
             }
             container inet6 {
               description "IPv6 flows";
               uses apply-advanced;
               list input-flows {
                 key name;
                 ordered-by user;
                 description "Input flows informations";
                 leaf name {
                   description "Name of flow";
                   type string {
                     length "1 .. 32";
                   }
                 }
                 uses apply-advanced;
                 leaf-list source-address {
                   ordered-by user;
                   description "Prefix to match";
                   type jt:ipv6prefix;
                   max-elements 32;
                 }
                 leaf-list destination-address {
                   ordered-by user;
                   description "Prefix to match";
                   type jt:ipv6prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf-list source-address {
                   ordered-by user;
                   description "Prefix to match";
                   type jt:ipv6prefix;
                   max-elements 32;
                 }
                 leaf-list destination-address {
                   ordered-by user;
                   description "Prefix to match";
                   type jt:ipv6prefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
             }
             container mpls {
               description "MPLS flows";
               uses apply-advanced;
               list input-flows {
                 key name;
                 ordered-by user;
                 description "Input flows informations";
                 leaf name {
                   description "Name of flow";
                   type string {
                     length "1 .. 32";
                   }
                 }
                 uses apply-advanced;
                 leaf payload-type {
                   description "Specify MPLS payload-type";
                   type enumeration {
                     enum "ipv4" {
                       description "IPv4 over MPLS";
                     }
                     enum "ipv6" {
                       description "IPv6 over MPLS";
                     }
                   }
                 }
                 leaf-list source-address {
                   ordered-by user;
                   description "Prefix to match";
                   type jt:ipprefix;
                   max-elements 32;
                 }
                 leaf-list destination-address {
                   ordered-by user;
                   description "Prefix to match";
                   type jt:ipprefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
               list output-flows {
                 key name;
                 ordered-by user;
                 description "Output flows informations";
                 leaf name {
                   description "Name of flow";
                   type string {
                     length "1 .. 32";
                   }
                 }
                 uses apply-advanced;
                 leaf payload-type {
                   description "Specify MPLS payload-type";
                   type enumeration {
                     enum "ipv4" {
                       description "IPv4 over MPLS";
                     }
                     enum "ipv6" {
                       description "IPv6 over MPLS";
                     }
                   }
                 }
                 leaf-list source-address {
                   ordered-by user;
                   description "Prefix to match";
                   type jt:ipprefix;
                   max-elements 32;
                 }
                 leaf-list destination-address {
                   ordered-by user;
                   description "Prefix to match";
                   type jt:ipprefix;
                   max-elements 32;
                 }
                 leaf-list source-port {
                   ordered-by user;
                   description "Source port number to match";
                   type string;
                   max-elements 32;
                 }
                 leaf-list destination-port {
                   ordered-by user;
                   description "Destination port number to match";
                   type string;
                   max-elements 32;
                 }
                 leaf template {
                   description "Name of template";
                   type string {
                     length "1 .. 32";
                   }
                 }
               }
             }
           }
         }
         leaf stats-cache-life-time {
           description "Lifetime of cached stats in seconds";
           default "10";
           type union {
             type string {
               pattern "<.*>|$.*";
             }
             type uint32 {
               range "1 .. 600";
             }
           }
         }
         leaf errors-cache-life-time {
           description "Lifetime of cached errors in seconds";
           default "10";
           type union {
             type string {
               pattern "<.*>|$.*";
             }
             type uint32 {
               range "1 .. 600";
             }
           }
         }
         leaf flow-cache-life-time {
           description "Lifetime of cached flows in seconds";
           default "10";
           type union {
             type string {
               pattern "<.*>|$.*";
             }
             type uint32 {
               range "1 .. 600";
             }
           }
         }
         container alarms {
           description "Alarms for Flows";
           uses apply-advanced;
           container delay-factor {
             description "DF Alarms";
             uses apply-advanced;
             leaf no-syslog-generation {
               description "Don't generate syslog when threshold exceed";
               type empty;
             }
             leaf generate-snmp-traps {
               description "Generate SNMP traps when threshold exceed";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container media-rate-variation {
             description "MLR Alarms";
             uses apply-advanced;
             leaf no-syslog-generation {
               description "Don't generate syslog when threshold exceed";
               type empty;
             }
             leaf generate-snmp-traps {
               description "Generate SNMP traps when threshold exceed";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container media-loss-rate {
             description "MRV Alarms";
             uses apply-advanced;
             leaf no-syslog-generation {
               description "Don't generate syslog when threshold exceed";
               type empty;
             }
             leaf generate-snmp-traps {
               description "Generate SNMP traps when threshold exceed";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
             container alarm-mode {
               presence "enable alarm-mode";
               description "Mode of alarm generation";
               uses apply-advanced;
               leaf mdi-records-count {
                 description "Number of MDI records to average";
                 type union {
                   type string {
                     pattern "<.*>|$.*";
                   }
                   type uint32 {
                     range "2 .. 10";
                   }
                 }
               }
               choice alarm_mode {
                 case case_1 {
                   leaf immediate {
                     description "Alarm will be triggered immediately";
                     type empty;
                   }
                 }
                 case case_2 {
                   leaf average {
                     description "Alarm will be triggered based on average";
                     type empty;
                   }
                 }
               }
             }
           }
           container flow-insert {
             description "Flow Insert Alarms";
             uses apply-advanced;
             leaf no-syslog-generation {
               description "Don't generate syslog when threshold exceed";
               type empty;
             }
             leaf generate-snmp-traps {
               description "Generate SNMP traps when threshold exceed";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
           }
           container flow-delete {
             description "Flow Delete Alarms";
             uses apply-advanced;
             leaf no-syslog-generation {
               description "Don't generate syslog when threshold exceed";
               type empty;
             }
             leaf generate-snmp-traps {
               description "Generate SNMP traps when threshold exceed";
               type empty;
             }
             container storm-control {
               presence "enable storm-control";
               description "Control frequency of alarm generation";
               uses apply-advanced;
               leaf count {
                 description "Max number of alarms in specified interval";
                 type union {
                   type string {
                     pattern "<.*>|$.*";
                   }
                   type uint32 {
                     range "1 .. 300";
                   }
                 }
               }
               leaf interval {
                 description "Interval in Seconds";
                 type union {
                   type string {
                     pattern "<.*>|$.*";
                   }
                   type uint32 {
                     range "1 .. 300";
                   }
                 }
               }
             }
           }
         }
       }
       container inline-monitoring {
         presence "enable inline-monitoring";
         description "Inline packet monitoring service";
         uses apply-advanced;
         container traceoptions {
           description "Trace options for IMOND";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         list counter-profile {
           key name;
           ordered-by user;
           description "Custom counter profiles for Inline packet monitoring";
           max-elements 8;
           leaf name {
             description "Name of counter-profile";
             type string {
               length "1 .. 32";
             }
           }
           uses apply-advanced;
           list counter {
             key name;
             ordered-by user;
             description "Inline monitoring counter";
             max-elements 6;
             leaf name {
               description "Name of counter";
               type string {
                 length "1 .. 32";
               }
             }
             uses apply-advanced;
             leaf max-value {
               description "Non-overlapping min/max range for counter-type, not exceeding packet contruct";
               type union {
                 type string {
                   pattern "<.*>|$.*";
                 }
                 type uint32 {
                   range "0 .. 65535";
                 }
               }
             }
             leaf min-value {
               description "Non-overlapping min/max range for counter-type, not exceeding packet contruct";
               type union {
                 type string {
                   pattern "<.*>|$.*";
                 }
                 type uint32 {
                   range "0 .. 65535";
                 }
               }
             }
             leaf counter-type {
               description "Counter type";
               type enumeration {
                 enum "packet-range" {
                   description "Packet range 64-9000 bytes";
                 }
                 enum "ttl-range" {
                   description "TTL range 0-255";
                 }
                 enum "tcp-window-range" {
                   description "TCP window range 0-65535";
                 }
                 enum "dos-attack" {
                   description "DoS attack counter, min/max is not required";
                 }
               }
             }
           }
         }
         list feature-profile {
           key name;
           ordered-by user;
           description "Feature profile for Inline packet monitoring";
           max-elements 1;
           leaf name {
             description "Name of feature-profile";
             type string {
               length "1 .. 32";
             }
           }
           uses apply-advanced;
           leaf-list features {
             ordered-by user;
             description "Features list";
             type enumeration {
               enum "inter-arrival-time" {
                 description "Inter arrival time";
               }
               enum "inter-departure-time" {
                 description "Inter departure time";
               }
               enum "chip-delay" {
                 description "Chip delay";
               }
               enum "shared-pool-congestion" {
                 description "Shared pool congestion level";
               }
               enum "queue-congestion-level" {
                 description "Queue congestion level";
               }
               enum "ingress-drop-reason" {
                 description "Ingress drop reason";
               }
               enum "egress-drop-reason" {
                 description "Egress drop reason";
               }
               enum "aggregate-intf-member-id" {
                 description "Aggregate interface member id";
               }
               enum "flow-start-end-time" {
                 description "Flow start and end time";
               }
               enum "security-enable" {
                 description "Enable DOS attack detection on monitored flows";
               }
             }
           }
         }
         list template {
           key name;
           ordered-by user;
           description "Templates for Inline packet monitoring";
           max-elements 16;
           leaf name {
             description "Name of template";
             type string {
               length "1 .. 32";
             }
           }
           uses apply-advanced;
           leaf template-refresh-rate {
             description "Refresh rate in seconds";
             default "600";
             type union {
               type string {
                 pattern "<.*>|$.*";
               }
               type uint16 {
                 range "10 .. 600";
               }
             }
           }
           leaf option-template-refresh-rate {
             description "Option refresh rate in seconds";
             default "600";
             type union {
               type string {
                 pattern "<.*>|$.*";
               }
               type uint16 {
                 range "10 .. 600";
               }
             }
           }
           leaf observation-domain-id {
             description "Observation domain ID";
             default "0";
             type union {
               type string {
                 pattern "<.*>|$.*";
               }
               type uint8 {
                 range "0 .. 255";
               }
             }
           }
           leaf template-id {
             description "Template ID";
             type union {
               type string {
                 pattern "<.*>|$.*";
               }
               type uint16;
             }
           }
           leaf option-template-id {
             description "Option template ID";
             type union {
               type string {
                 pattern "<.*>|$.*";
               }
               type uint16 {
                 range "1024 .. 65535";
               }
             }
           }
           leaf flow-active-timeout {
             description "Interval after which active flow is exported in seconds";
             default "60";
             type union {
               type string {
                 pattern "<.*>|$.*";
               }
               type uint16 {
                 range "10 .. 600";
               }
             }
           }
           leaf flow-inactive-timeout {
             description "Period of inactivity that marks a flow inactive in seconds";
             default "60";
             type union {
               type string {
                 pattern "<.*>|$.*";
               }
               type uint16 {
                 range "10 .. 600";
               }
             }
           }
           leaf template-type {
             description "Template IP version";
             default "ipv4-template";
             type enumeration {
               enum "ipv4-template" {
                 description "IPv4 template configuration";
               }
               enum "ipv6-template" {
                 description "IPv6 template configuration";
               }
             }
           }
           container flow-monitoring {
             presence "enable flow-monitoring";
             uses apply-advanced;
             leaf sampling-profile {
               description "Supported sampling profiles";
               type enumeration {
                 enum "first-N-Packets" {
                   description "Initial first 'N' packet samples are exported to collector";
                 }
                 enum "deterministic" {
                   description "Deterministically 'N'th packet is sampled";
                 }
                 enum "random" {
                   description "Random packets are sampled and exported";
                 }
                 enum "combo-1" {
                   description "Initial first 'N' packets followed by random packet sampling";
                 }
                 enum "combo-2" {
                   description "Initial first 'N' packets followed by deterministic sampling";
                 }
               }
             }
             leaf packet-count {
               description "Packet count for first-N-Packets/combo-1/combo-2 sampling profiles";
               default "10";
               type union {
                 type string {
                   pattern "<.*>|$.*";
                 }
                 type uint16 {
                   range "1 .. 1023";
                 }
               }
             }
             leaf sampling-rate {
               description "Sampling rate";
               default "10000";
               type union {
                 type string {
                   pattern "<.*>|$.*";
                 }
                 type uint32 {
                   range "1 .. 65535";
                 }
               }
             }
             leaf security-enable {
               description "Enable DOS attack detection on monitored flows";
               type empty;
             }
             leaf flow-rate {
               description "Flow meter rate in kbps";
               type union {
                 type string {
                   pattern "<.*>|$.*";
                 }
                 type uint32 {
                   range "8 .. 10000000";
                 }
               }
             }
             leaf burst-size {
               description "Burst size in bytes";
               type union {
                 type string {
                   pattern "<.*>|$.*";
                 }
                 type uint32 {
                   range "512 .. 256000000";
                 }
               }
             }
             leaf flow-limit {
               description "Maximum number of flows allowed";
               default "32000";
               type union {
                 type string {
                   pattern "<.*>|$.*";
                 }
                 type uint16;
               }
             }
             leaf counter-profile {
               description "Counter profiles per-flow-4-counters, per-flow-6-counters or custom profile";
               type string {
                 length "1 .. 32";
               }
             }
             leaf feature-profile {
               description "Feature profile";
               type string {
                 length "1 .. 32";
               }
             }
           }
           list primary-data-record-fields {
             key name;
             ordered-by user;
             description "Primary data record fields";
             leaf name {
               description "IPFIX Information Elements";
               type enumeration {
                 enum "datalink-frame-size" {
                   description "Datalink Frame Size";
                 }
                 enum "direction" {
                   description "Direction";
                 }
                 enum "egress-interface-snmp-id" {
                   description "Egress Interface SNMP ID";
                 }
                 enum "ingress-interface-snmp-id" {
                   description "Ingress Interface SNMP ID";
                 }
                 enum "cpid-ingress-interface-index" {
                   description "CPID Ingress Interface Index";
                 }
                 enum "cpid-underlying-ingress-interface-index" {
                   description "CPID Underlying Ingress Interface Index";
                 }
                 enum "cpid-egress-interface-index" {
                   description "CPID Egress Interface Index";
                 }
                 enum "cpid-forwarding-nexthop-id" {
                   description "CPID Forwarding Nexthop Id";
                 }
                 enum "cpid-forwarding-exception-code" {
                   description "CPID Forwarding Exception Code";
                 }
                 enum "cpid-forwarding-class-drop-priority" {
                   description "CPID Forwarding Class Drop Priority";
                 }
               }
             }
           }
         }
         list instance {
           key name;
           ordered-by user;
           description "Inline monitoring instance";
           max-elements 16;
           leaf name {
             description "Name of instance";
             type string {
               length "1 .. 32";
             }
           }
           uses apply-advanced;
           leaf template-name {
             description "Template Name";
             type string {
               length "1 .. 32";
             }
           }
           leaf maximum-clip-length {
             description "Maximum packet length";
             type union {
               type string {
                 pattern "<.*>|$.*";
               }
               type uint16 {
                 range "64 .. 126";
               }
             }
           }
           leaf controller {
             description "Controller type";
             type enumeration {
               enum "p4" {
                 description "Controller P4";
               }
               enum "re" {
                 description "Send packet to RE";
               }
             }
           }
           leaf export-by-asic {
             description "Export IPFIX packets via ASIC";
             type empty;
           }
           leaf sampling-rate {
             description "Sampling rate";
             type union {
               type string {
                 pattern "<.*>|$.*";
               }
               type uint32 {
                 range "1 .. 32000000";
               }
             }
           }
           list collector {
             key name;
             ordered-by user;
             description "Inline monitoring collector";
             max-elements 1;
             leaf name {
               description "Name of collector";
               type string {
                 length "1 .. 32";
               }
             }
             uses apply-advanced;
             leaf source-address {
               description "Source address";
               type jt:ipv4addr;
             }
             leaf destination-address {
               description "Destination address";
               type jt:ipv4addr;
             }
             leaf dscp {
               description "DSCP Value";
               default "0";
               type union {
                 type string {
                   pattern "<.*>|$.*";
                 }
                 type uint8 {
                   range "0 .. 63";
                 }
               }
             }
             leaf destination-port {
               description "Destination port value";
               type union {
                 type string {
                   pattern "<.*>|$.*";
                 }
                 type uint16 {
                   range "1 .. 65535";
                 }
               }
             }
             leaf forwarding-class {
               description "Forwarding class for exported frames";
               type string {
                 length "1 .. 64";
               }
             }
             leaf sampling-rate {
               description "Sampling rate";
               type union {
                 type string {
                   pattern "<.*>|$.*";
                 }
                 type uint32 {
                   range "1 .. 16000000";
                 }
               }
             }
             leaf routing-instance {
               description "Name of routing instance";
               type string;
             }
           }
         }
         leaf observation-cloud-id {
           description "Observation cloud ID";
           type union {
             type string {
               pattern "<.*>|$.*";
             }
             type uint8 {
               range "1 .. 255";
             }
           }
         }
         leaf flow-export-timer {
           description "Flow export timer";
           default "10";
           units "seconds";
           type union {
             type string {
               pattern "<.*>|$.*";
             }
             type uint16 {
               range "1 .. 600";
             }
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             description "Management address connected to compute cluster";
             uses apply-advanced;
             list routing-instance {
               key routing-instance-name;
               ordered-by user;
               description "Packets are restriction to specified routing instance";
               max-elements 1;
               leaf routing-instance-name {
                 description "Name of routing instance";
                 type string {
                 }
               }
               uses apply-advanced;
               container family {
                 description "Protocol family";
                 container inet {
                   description "IPv4 parameters";
                   uses apply-advanced;
                   leaf address {
                     description "Interface address";
                     type jt:ipv4addr;
                   }
                 }
               }
             }
             container family {
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   type jt:mac-addr;
                 }
               }
               case case_2 {
                 leaf fpc {
                   description "FPC slot number";
                   type union {
                     type string {
                       pattern "<.*>|$.*";
                     }
                     type uint32;
                   }
                 }
               }
               case case_3 {
                 leaf hypervisor {
                   description "Compute node is hypervisor";
                   type empty;
                 }
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   type string {
                     length "1 .. 15";
                   }
                 }
                 uses apply-advanced;
                 leaf management {
                   description "Use this as management interface";
                   type empty;
                 }
                 container family {
                   description "Protocol family";
                   uses family;
                 }
                 leaf enable-passthrough {
                   description "Enable passthrough on this interface";
                   type empty;
                 }
                 leaf mtu {
                   description "Maximum transmit packet size";
                   type union {
                     type string {
                       pattern "<.*>|$.*";
                     }
                     type uint16 {
                       range "256 .. 9192";
                     }
                   }
                 }
                 container ether-options {
                   uses apply-advanced;
                   choice agg-intf {
                     case case_1 {
                       leaf ieee-802-3ad {
                         description "Aggregated interface name";
                         type string {
                           length "1 .. 15";
                         }
                       }
                     }
                   }
                 }
               }
               list bridge {
                 key name;
                 ordered-by user;
                 description "Bridge configuration";
                 leaf name {
                   description "Bridge name";
                   type string {
                     length "1 .. 15";
                   }
                 }
                 uses apply-advanced;
                 leaf management {
                   description "Use this as management bridge";
                   type empty;
                 }
                 container family {
                   description "Protocol family";
                   uses family;
                 }
                 leaf-list interface {
                   ordered-by user;
                   description "Bridge interface list";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   type string {
                     length "1 .. 15";
                   }
                 }
                 uses apply-advanced;
                 leaf management {
                   description "Use this as management aggregate";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf management-interface {
               description "Virtual-machine management interface name";
               type string {
                 length "1 .. 31";
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 max-elements 1;
                 leaf routing-instance-name {
                   description "Name of routing instance";
                   type string {
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 type string {
                   length "1 .. 15";
                 }
               }
               uses apply-advanced;
               leaf compute-node {
                 description "Compute node on which the virtual-machine runs";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container unified-access-control {
         description "Configure Unified Access Control";
         uses apply-advanced;
         list infranet-controller {
           key name;
           ordered-by user;
           description "Configure infranet controller";
           leaf name {
             description "Infranet controller name";
             type string {
               length "1 .. 31";
             }
           }
           uses apply-advanced;
           leaf address {
             description "Infranet controller IP address";
             type jt:ipv4addr;
           }
           leaf port {
             description "Infranet controller port";
             default "11123";
             type union {
               type string {
                 pattern "<.*>|$.*";
               }
               type uint32 {
                 range "1 .. 65535";
               }
             }
           }
           leaf interface {
             description "Outgoing interface";
             type union {
               type jt:interface-name;
               type string {
                 pattern "<.*>|$.*";
               }
             }
           }
           leaf password {
             description "Infranet controller server password";
             type string {
               length "1 .. 255";
             }
           }
           leaf-list ca-profile {
             ordered-by user;
             description "Define a list of certificate authority";
             type string;
           }
           leaf server-certificate-subject {
             description "Subject name of infranet controller certificate to match";
             type string {
               length "1 .. 255";
             }
           }
         }
         leaf certificate-verification {
           description "Specify certificate verification requirement";
           default "warning";
           type enumeration {
             enum "warning" {
               description "Warn if certificate is not being verified";
             }
             enum "required" {
               description "Require certificate verification. Most secure";
             }
             enum "optional" {
               description "Make verification optional, no warnings. Least secure";
             }
           }
         }
         leaf timeout {
           description "Timeout for idle infranet controller link in seconds";
           default "300";
           type union {
             type string {
               pattern "<.*>|$.*";
             }
             type uint32 {
               range "2 .. 10000";
             }
           }
         }
         leaf interval {
           description "Heartbeat interval from infranet controller in seconds";
           default "30";
           type union {
             type string {
               pattern "<.*>|$.*";
             }
             type uint32 {
               range "1 .. 9999";
             }
           }
         }
         leaf timeout-action {
           description "Specify action when infranet controller timeout occurs";
           default "close";
           type enumeration {
             enum "close" {
               description "Remove existing sessions and block further traffic";
             }
             enum "no-change" {
               description "Preserve existing connections; block new sessions";
             }
             enum "open" {
               description "Allow traffic for new and existing sessions to go through";
             }
           }
         }
         leaf test-only-mode {
           description "Allow all traffic and only log enforcement result";
           type empty;
         }
         leaf event-entry-lifetime {
           description "Interval between successive NO-AUTH msgs for same src ip in seconds";
           default "60";
           type union {
             type string {
               pattern "<.*>|$.*";
             }
             type uint32 {
               range "1 .. 60";
             }
           }
         }
         container traceoptions {
           description "UAC trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace with all flags enabled";
                 }
                 enum "ipc" {
                   description "IPC tracing";
                 }
                 enum "config" {
                   description "Configuration tracing";
                 }
                 enum "connect" {
                   description "Communication with infranet controller tracing";
                 }
               }
             }
           }
         }
         list captive-portal {
           key name;
           ordered-by user;
           description "Unauthenticated HTTP redirect";
           leaf name {
             description "Redirect policy name";
             type string {
               length "1 .. 128";
             }
           }
           uses apply-advanced;
           leaf redirect-traffic {
             description "Traffic to redirect";
             type enumeration {
               enum "unauthenticated" {
                 description "Redirect unauthenticated traffic";
               }
               enum "all" {
                 description "Redirect all traffic";
               }
             }
           }
           leaf redirect-url {
             description "Redirect URL for unauthenticated users";
             type string {
               length "1 .. 512";
             }
           }
         }
       }
       container inband-flow-telemetry {
         presence "enable inband-flow-telemetry";
         description "Inband telemetry services";
         uses apply-advanced;
         container traceoptions {
           presence "enable traceoptions";
           description "Inband telemetry trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container device-id {
           description "Inband telemetry global unique identifier";
           uses apply-advanced;
           choice device_id_choice {
             case case_1 {
               leaf auto {
                 description "Device router-id will be considered";
                 type empty;
               }
             }
             case case_2 {
               leaf id {
                 description "Specify unique device identifier";
                 type union {
                   type string {
                     pattern "<.*>|$.*";
                   }
                   type uint32 {
                     range "1 .. 1048575";
                   }
                 }
               }
             }
           }
         }
         leaf meta-data-stack-length {
           description "Maximum length for meta data";
           default "240";
           type union {
             type string {
               pattern "<.*>|$.*";
             }
             type uint32 {
               range "8 .. 255";
             }
           }
         }
         leaf hop-limit {
           description "Maximum hop limits allowed";
           default "250";
           type union {
             type string {
               pattern "<.*>|$.*";
             }
             type uint32 {
               range "1 .. 250";
             }
           }
         }
         leaf flow-type {
           description "Configure IFA traffic type";
           type enumeration {
             enum "l3" {
               description "L3 traffic type";
             }
             enum "vxlan" {
               description "Vxlan traffic type";
             }
           }
         }
         leaf no-ipv6-address-match {
           description "Configure if no ipv6 address match is used";
           type empty;
         }
         leaf clock-source {
           description "Configure clock source for timestamping";
           type enumeration {
             enum "ntp" {
               description "Use Network Time Protocol";
             }
             enum "ptp" {
               description "Use Precision Time Protocol";
             }
           }
         }
         list profile {
           key name;
           description "Profile options";
           max-elements 32;
           uses inband-telemetry-profile-type;
         }
       }
       container agf {
         description "Configuration for access gateway function";
         uses apply-advanced;
         leaf node-name {
           description "AGF node name";
           type string {
             length "1 .. 150";
           }
         }
         leaf node-id {
           description "AGF node identifier";
           type union {
             type string {
               pattern "<.*>|$.*";
             }
             type uint32 {
               range "0 .. 255";
             }
           }
         }
         leaf ip-address {
           description "AGF ip address";
           status deprecated;
           type jt:ipv4addr;
         }
         list fiveqi-map {
           key name;
           ordered-by user;
           uses fiveqi;
         }
         container n2-proxy {
           presence "enable n2-proxy";
           description "N2 proxy settings";
           status deprecated;
           uses apply-advanced;
           leaf ip-address {
             description "N2 proxy ip address";
             type jt:ipv4addr;
           }
           leaf port {
             description "N2 proxy port number";
             default "65454";
             type union {
               type string {
                 pattern "<.*>|$.*";
               }
               type uint16 {
                 range "0 .. 65535";
               }
             }
           }
         }
         list plmn {
           key name;
           ordered-by user;
           description "AGF public land mobile network";
           leaf name {
             description "Public land mobile network name";
             type string {
               length "1 .. 80";
             }
           }
           uses apply-advanced;
           leaf mcc {
             description "Mobile country code";
             type string {
             }
           }
           leaf mnc {
             description "Mobile network code";
             type string {
             }
           }
         }
         list tracking-area {
           key name;
           ordered-by user;
           description "Tracking area";
           leaf name {
             description "Tracking area code";
             type union {
               type string {
                 pattern "<.*>|$.*";
               }
               type uint32 {
                 range "0 .. 16777215";
               }
             }
           }
           uses apply-advanced;
           list plmn {
             key name;
             ordered-by user;
             description "Public land mobile network";
             max-elements 1;
             leaf name {
               description "Public land mobile network name";
               type string {
                 length "1 .. 80";
               }
             }
             uses apply-advanced;
             list s-nssai {
               key name;
               ordered-by user;
               description "Single network slice selection assistance information";
               leaf name {
                 description "Single network slice selection assistance information identifier";
                 type union {
                   type string {
                     pattern "<.*>|$.*";
                   }
                   type uint16 {
                     range "0 .. 128";
                   }
                 }
               }
               uses apply-advanced;
               leaf sst {
                 description "Slice service type";
                 type enumeration {
                   enum "embb" {
                     description "Enhanced mobile broadband slice";
                   }
                   enum "urllc" {
                     description "Ultra-reliable, low latency communications";
                   }
                   enum "miot" {
                     description "Massive IoT";
                   }
                   enum "v2x" {
                     description "V2X services";
                   }
                 }
               }
               leaf sd {
                 description "Selection differentiator";
                 default "0";
                 type union {
                   type string {
                     pattern "<.*>|$.*";
                   }
                   type uint32 {
                     range "0 .. 16777215";
                   }
                 }
               }
             }
           }
         }
         list amf {
           key name;
           ordered-by user;
           description "AGF access and mobility management function";
           max-elements 256;
           leaf name {
             description "AMF name";
             type string {
               length "1 .. 80";
             }
           }
           uses apply-advanced;
           leaf node-id {
             description "AMF node identifier";
             type union {
               type string {
                 pattern "<.*>|$.*";
               }
               type uint32 {
                 range "0 .. 255";
               }
             }
           }
           leaf ip-address {
             description "AMF ip address";
             type jt:ipv4addr;
           }
           leaf port {
             description "AMF port number";
             default "38412";
             type union {
               type string {
                 pattern "<.*>|$.*";
               }
               type uint16 {
                 range "0 .. 65535";
               }
             }
           }
           container local-endpoint {
             description "AMF local endpoint";
             uses apply-advanced;
             list ip-address {
               key name;
               ordered-by user;
               description "AMF local endpoint ip address";
               leaf name {
                 description "AMF local endpoint ip address";
                 type jt:ipv4addr;
               }
               uses apply-advanced;
               leaf primary {
                 description "Set primary AMF local endpoint ip address";
                 type empty;
               }
             }
             leaf initial-tnla-weight-factor {
               description "The weight factor assigned to the initial SCTP association";
               default "128";
               type union {
                 type string {
                   pattern "<.*>|$.*";
                 }
                 type uint32 {
                   range "1 .. 255";
                 }
               }
             }
           }
           leaf routing-instance {
             description "Routing instance for AMF connectivity";
             type string {
             }
           }
           list tracking-area {
             key name;
             ordered-by user;
             description "AMF tracking areas";
             leaf name {
               description "Tracking area code";
               type union {
                 type uint32;
                 type string {
                   pattern "<.*>|$.*";
                 }
               }
             }
             uses apply-advanced;
           }
           leaf default-amf {
             description "Configure a default AMF";
             type empty;
           }
           leaf offline {
             description "Offline the AMF";
             type empty;
           }
         }
         list user-planes {
           key name;
           ordered-by user;
           uses user-plane-object;
         }
       }
       container flow-collector {
         description "Configure options to control flow collector";
         uses apply-advanced;
         leaf analyzer-address {
           description "Analyzer IP address field override value";
           type jt:ipv4addr;
         }
         leaf analyzer-id {
           description "Analyzer ID field override value";
           type string {
             length "1 .. 64";
           }
         }
         leaf retry {
           description "Transfer retry attempt count";
           default "0";
           type union {
             type string {
               pattern "<.*>|$.*";
             }
             type uint32 {
               range "0 .. 10";
             }
           }
         }
         leaf retry-delay {
           description "Delay between transfer retry attempts";
           default "0";
           units "seconds";
           type union {
             type string {
               pattern "<.*>|$.*";
             }
             type uint32 {
               range "0 .. 60";
             }
           }
         }
         list destinations {
           key name;
           ordered-by user;
           description "Configure destination for files";
           uses collector_destinations_type;
         }
         list file-specification {
           key name;
           description "File format specification";
           uses file_specification_type;
         }
         container interface-map {
           description "Input interface to Collector PIC mapping";
           presence "enable interface-map";
           uses interface_map_type;
         }
         container transfer-log-archive {
           description "Transfer log archive specification";
           presence "enable transfer-log-archive";
           uses collector_transfer_log_archive_type;
         }
       }
       container captive-portal {
         description "Captive Portal options";
         uses juniper-services-captive-portal;
       }
       container advanced-anti-malware {
         uses apply-advanced;
         container dynamic-filter {
           description "Dynamic Filtering configuration";
           uses apply-advanced;
           container traceoptions {
             description "Dynamic Filtering traceoptions";
             uses dyn-filterd-traceoptions;
           }
         }
         container connection {
           presence "enable connection";
           description "Cloud service RE connection, only for master logical domain";
           uses apply-advanced;
           leaf url {
             description "The url of the cloud server [https://<ip or hostname>:<port>]";
             type string;
           }
           container authentication {
             description "The authentication profile for using cloud services";
             uses apply-advanced;
             leaf tls-profile {
               description "TLS profile";
               type string;
             }
           }
           leaf proxy-profile {
             description "Proxy profile";
             type string {
               length "1 .. 63";
             }
           }
           leaf source-address {
             description "The source ip for connecting to the cloud server.";
             type jt:ipaddr;
           }
           leaf source-interface {
             description "The source interface for connecting to the cloud server";
             type union {
               type jt:interface-name;
               type string {
                 pattern "<.*>|$.*";
               }
             }
           }
         }
         container default-policy {
           presence "enable default-policy";
           description "Advanced Anti-malware default policy";
           uses apply-advanced;
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         list policy {
           key name;
           description "Advanced Anti-malware policy";
           leaf name {
             description "Policy name, default policy must name (default-policy)";
             type string {
               length "1 .. 63";
             }
           }
           uses apply-advanced;
           container match {
             description "Policy match conditions";
             status deprecated;
             uses apply-advanced;
             leaf application {
               description "Application";
               type enumeration {
                 enum "HTTP" {
                   description "HTTP Traffic";
                 }
               }
             }
             leaf verdict-threshold {
               description "Verdict threshold";
               type enumeration {
                 enum "1" {
                   description "Verdict-threshold level 1";
                 }
                 enum "2" {
                   description "Verdict-threshold level 2";
                 }
                 enum "3" {
                   description "Verdict-threshold level 3";
                 }
                 enum "4" {
                   description "Verdict-threshold level 4";
                 }
                 enum "5" {
                   description "Verdict-threshold level 5";
                 }
                 enum "6" {
                   description "Verdict-threshold level 6";
                 }
                 enum "7" {
                   description "Verdict-threshold level 7";
                 }
                 enum "8" {
                   description "Verdict-threshold level 8";
                 }
                 enum "9" {
                   description "Verdict-threshold level 9";
                 }
                 enum "10" {
                   description "Verdict-threshold level 10";
                 }
                 enum "recommended" {
                   description "Recommended verdict-threshold";
                 }
               }
             }
           }
           container then {
             status deprecated;
             uses apply-advanced;
             leaf action {
               description "Action taken for contents with verdict meet threshold";
               type enumeration {
                 enum "permit" {
                   description "Allow contents";
                 }
                 enum "block" {
                   description "Disallow contents";
                 }
               }
             }
             container notification {
               description "Notification action taken for contents with verdict meet threshold";
               uses apply-advanced;
               leaf log {
                 description "Logging option for Advanced Anti-malware actions";
                 type empty;
               }
             }
           }
           container http {
             description "Configure HTTP options";
             uses apply-advanced;
             leaf inspection-profile {
               description "Advanced Anti-malware inspection-profile name (default:default_profile)";
               type string {
                 length "1 .. 63";
               }
             }
             leaf file-verdict-unknown {
               description "Action taken for contents with verdict unknown";
               type enumeration {
                 enum "permit" {
                   description "Allow contents";
                 }
                 enum "block" {
                   description "Disallow contents";
                 }
               }
             }
             leaf action {
               description "Action taken for contents with verdict meet threshold";
               type enumeration {
                 enum "permit" {
                   description "Allow contents";
                 }
                 enum "block" {
                   description "Disallow contents";
                 }
               }
             }
             container client-notify {
               description "Notification action taken for contents with verdict meet threshold";
               uses apply-advanced;
               choice http-choice {
                 case case_1 {
                   leaf file {
                     description "File name for http response to client";
                     type string {
                       length "1 .. 255";
                     }
                   }
                 }
                 case case_2 {
                   leaf message {
                     description "Block message to client";
                     type string {
                       length "1 .. 1023";
                     }
                   }
                 }
                 case case_3 {
                   leaf redirect-url {
                     description "Redirect url to client";
                     type string {
                       length "1 .. 1023";
                     }
                   }
                 }
               }
             }
             container notification {
               description "Notification action taken for contents with verdict meet threshold";
               uses apply-advanced;
               leaf log {
                 description "Logging option for Advanced Anti-malware actions";
                 type empty;
               }
             }
           }
           container smtp {
             description "Configure SMTP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container imap {
             description "Configure IMAP options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
           }
           container smb {
             description "Configure SMB options";
             uses apply-advanced;
             leaf inspection-profile {
               description "Advanced Anti-malware inspection-profile name (default:default_profile)";
               type string {
                 length "1 .. 63";
               }
             }
             container notification {
               description "Notification action taken for contents with verdict meet threshold";
               uses apply-advanced;
               leaf log {
                 description "Logging option for Advanced Anti-malware actions";
                 type empty;
               }
             }
             leaf action {
               description "Action taken for contents with verdict meet threshold";
               type enumeration {
                 enum "permit" {
                   description "Allow contents";
                 }
                 enum "block" {
                   description "Disallow contents";
                 }
               }
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
               enum "recommended" {
                 description "Recommended verdict-threshold";
               }
             }
           }
           leaf inspection-profile {
             description "Advanced Anti-malware inspection-profile name";
             status deprecated;
             type string {
               length "1 .. 63";
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container service-not-ready {
               description "Service not ready yet";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Service out of resources";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container verdict-timeout {
               description "Verdict timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container submission-timeout {
               description "Submission timed out";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container unknown-file {
               description "File type unknown";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container default-notification {
             description "Notification action taken for action";
             uses apply-advanced;
             leaf log {
               description "Logging option for Advanced Anti-malware action";
               type empty;
             }
           }
           container whitelist-notification {
             description "Whitelist notification logging option";
             uses apply-advanced;
             leaf log {
               description "Logging option for Advanced Anti-malware whitelist hit";
               type empty;
             }
           }
           container blacklist-notification {
             description "Blacklist notification logging option";
             uses apply-advanced;
             leaf log {
               description "Logging option for Advanced Anti-malware blacklist hit";
               type empty;
             }
           }
         }
         container traceoptions {
           description "Advanced Anti-malware trace options";
           uses aamwd-traceoptions;
         }
       }
       container logging {
         description "Bulk logging configuration";
         uses juniper-pic-services-logging-options;
       }
       container application-identification {
         presence "enable application-identification";
         description "Application identification configuration";
         uses apply-advanced;
         leaf enable-heuristics {
           description "Enable heuristic application identification";
           status deprecated;
           type empty;
         }
         container enable-performance-mode {
           presence "enable enable-performance-mode";
           description "Enable performance mode knobs for best DPI performance";
           status deprecated;
           uses apply-advanced;
           leaf max-packet-threshold {
             description "Max packet inspection threshold including both c2s ans s2c direction packets. Default value is 2 if not configured";
             status deprecated;
             default "2";
             type union {
               type string {
                 pattern "<.*>|$.*";
               }
               type uint32 {
                 range "1 .. 100";
               }
             }
           }
         }
         leaf imap-cache-timeout {
           description "IMAP cache entry timeout in seconds";
           type union {
             type string {
               pattern "<.*>|$.*";
             }
             type uint32 {
               range "1 .. 86400";
             }
           }
         }
         leaf imap-cache-size {
           description "IMAP cache size, it will be effective only after next appid sigpack install";
           type union {
             type string {
               pattern "<.*>|$.*";
             }
             type uint32 {
               range "60 .. 512000";
             }
           }
         }
         container download {
           uses apply-advanced;
           leaf url {
             description "URL for application package download";
             type string {
             }
           }
           leaf ignore-server-validation {
             description "Disable server authentication for Applicaton Signature download";
             type empty;
           }
           container automatic {
             description "Scheduled download and update";
             uses apply-advanced;
             leaf start-time {
               description "Start time(MM-DD.hh:mm / YYYY-MM-DD.hh:mm:ss)";
               type string {
               }
             }
             leaf interval {
               description "Attempt to download new application package";
               default "24";
               units "hours";
               type union {
                 type string {
                   pattern "<.*>|$.*";
                 }
                 type uint32 {
                   range "6 .. 720";
                 }
               }
             }
           }
           leaf proxy-profile {
             description "Configure web proxy for Application signature download";
             type string {
               length "1 .. 128";
             }
           }
         }
         container statistics {
           description "Configure application statistics information";
           leaf interval {
             description "Application statistics collection interval";
             default "1";
             units "minutes";
             type union {
               type string {
                 pattern "<.*>|$.*";
               }
               type uint32 {
                 range "1 .. 1440";
               }
             }
           }
         }
         container nested-application-settings {
           presence "enable nested-application-settings";
           description "Nested application settings";
           status deprecated;
           uses apply-advanced;
           leaf no-nested-application {
             description "Disable nested application identification";
             type empty;
           }
           leaf no-application-system-cache {
             description "Not to save nested AI match in application system cache";
             type empty;
           }
         }
         leaf no-application-identification {
           description "Disable all application identification methods";
           status deprecated;
           type empty;
         }
         leaf no-signature-based {
           description "Disable signature based method";
           status deprecated;
           type empty;
         }
         leaf no-protocol-based {
           description "Disable protocol based method";
           status deprecated;
           type empty;
         }
         leaf signature-method-all-ports {
           description "Use signature-method on all(including well-known) ports";
           status deprecated;
           type empty;
         }
         leaf no-clear-application-system-cache {
           description "Disable clearing application system cache";
           status deprecated;
           type empty;
         }
         leaf no-application-system-cache {
           description "Disable storing AI result in application system cache";
           type empty;
         }
         leaf no-application-statistics {
           description "Disable application statistics";
           type empty;
         }
         leaf max-sessions {
           description "Max sessions that can run AI at the same time";
           status deprecated;
           type union {
             type string {
               pattern "<.*>|$.*";
             }
             type uint32 {
               range "0 .. 500000";
             }
           }
         }
         leaf application-system-cache-timeout {
           description "Application system cache entry lifetime";
           type union {
             type string {
               pattern "<.*>|$.*";
             }
             type uint32 {
               range "0 .. 1000000";
             }
           }
         }
         container application-system-cache {
           presence "enable application-system-cache";
           description "Enable or Disable application system cache";
           uses apply-advanced;
           leaf security-services {
             description "Enable ASC for security services (appfw, appqos, idp, skyatp..)";
             type empty;
           }
           leaf no-miscellaneous-services {
             description "Disable ASC for miscellaneous services APBR,...";
             type empty;
           }
         }
         leaf micro-apps {
           description "Enable Micro Apps identifcation";
           type empty;
         }
         leaf max-transactions {
           description "Number of transaction finals to terminate application classification";
           type union {
             type string {
               pattern "<.*>|$.*";
             }
             type uint16 {
               range "0 .. 25";
             }
           }
         }
         leaf custom-application-byte-limit {
           description "Max bytes to be scanned for identification of custom application";
           type union {
             type string {
               pattern "<.*>|$.*";
             }
             type uint32 {
               range "1 .. 100000";
             }
           }
         }
         leaf max-memory {
           description "Maximum amount of object cache memory JDPI can use (in MB)";
           type union {
             type string {
               pattern "<.*>|$.*";
             }
             type uint32 {
               range "1 .. 200000";
             }
           }
         }
         leaf max-checked-bytes {
           description "Inspect the maximal number of bytes";
           status deprecated;
           type union {
             type string {
               pattern "<.*>|$.*";
             }
             type uint32 {
               range "0 .. 100000";
             }
           }
         }
         list application {
           key name;
           description "Configure application definition";
           leaf name {
             description "A unique application identifier";
             type string {
               length "1 .. 63";
             }
           }
           uses apply-advanced;
           leaf type {
             description "Well-known application such as HTTP and FTP";
             type string {
               length "1 .. 63";
             }
           }
           leaf index {
             description "Custom index (32768..65534). Application index";
             status deprecated;
             type union {
               type string {
                 pattern "<.*>|$.*";
               }
               type uint16 {
                 range "1 .. 65534";
               }
             }
           }
           list tags {
             key name;
             ordered-by user;
             description "Application tags eg. risk factors, technology, traffic type";
             max-elements 3;
             leaf name {
               description "General information about the application type";
               type string;
             }
             uses apply-advanced;
             leaf value {
               description "Value";
               type string;
             }
           }
           leaf session-timeout {
             description "Lifetime of a session";
             status deprecated;
             default "86400";
             type enumeration {
               enum "0" {
                 description "No session timeout";
                 status deprecated;
               }
               enum "30" {
                 description "30 seconds";
                 status deprecated;
               }
               enum "60" {
                 description "60 seconds";
                 status deprecated;
               }
               enum "1800" {
                 description "1800 seconds";
                 status deprecated;
               }
               enum "3600" {
                 description "3600 seconds";
                 status deprecated;
               }
               enum "43200" {
                 description "43200 seconds (12 hours)";
                 status deprecated;
               }
               enum "86400" {
                 description "86400 seconds (1 day)";
                 status deprecated;
               }
               enum "2592000" {
                 description "2592000 seconds (30 days)";
                 status deprecated;
               }
             }
           }
           leaf idle-timeout {
             description "Remove the session if no packets";
             status deprecated;
             default "30";
             type enumeration {
               enum "0" {
                 description "No idle timeout";
                 status deprecated;
               }
               enum "5" {
                 description "5 seconds";
                 status deprecated;
               }
               enum "15" {
                 description "15 seconds";
                 status deprecated;
               }
               enum "30" {
                 description "30 seconds";
                 status deprecated;
               }
               enum "60" {
                 description "60 seconds";
                 status deprecated;
               }
               enum "1800" {
                 description "1800 seconds";
                 status deprecated;
               }
               enum "3600" {
                 description "3600 seconds";
                 status deprecated;
               }
             }
           }
           container type-of-service {
             description "Type of service";
             status deprecated;
             uses apply-advanced;
             leaf minimize-delay {
               description "Requires minimal delay in packet transmission";
               type empty;
             }
             leaf maximize-throughput {
               description "Requires maximal throughput in packet transmission";
               type empty;
             }
             leaf maximize-reliability {
               description "Requires maximal reliability in packet transmission";
               type empty;
             }
             leaf minimize-monetary-cost {
               description "Requires minimal monetary cost in packet transmission";
               type empty;
             }
           }
           leaf disable {
             description "Disable this application definition in AI";
             status deprecated;
             type empty;
           }
           leaf cacheable {
             description "Cacheable";
             type empty;
           }
           leaf risk {
             description "Risk/Hotness of application";
             type union {
               type string {
                 pattern "<.*>|$.*";
               }
               type uint32 {
                 range "1 .. 5";
               }
             }
           }
           leaf description {
             description "Text description of application";
             type string {
             }
           }
           leaf priority {
             description "Application matching priority";
             default "low";
             type enumeration {
               enum "high" {
                 description "Highest priority over all other signatures";
               }
               enum "low" {
                 description "Lowest priority over all other signatures";
               }
             }
           }
           leaf order {
             description "The order value, lower the value higher the priority";
             type union {
               type string {
                 pattern "<.*>|$.*";
               }
               type uint16 {
                 range "1 .. 50000";
               }
             }
           }
           leaf maximum-transactions {
             description "Maximum number of transactions matched by AI";
             status deprecated;
             type union {
               type uint16;
               type string {
                 pattern "<.*>|$.*";
               }
             }
           }
           leaf alt-name {
             description "Alt name for the application";
             type string {
             }
           }
           leaf compatibility {
             description "Juniper compatibility version";
             type string {
             }
           }
           container port-mapping {
             status deprecated;
             uses apply-advanced;
             container icmp {
               description "Match ICMP message";
               uses apply-advanced;
               leaf type {
                 description "Numeric type value (0 .. 254)";
                 type union {
                   type string {
                     pattern "<.*>|$.*";
                   }
                   type uint16 {
                     range "0 .. 254";
                   }
                 }
               }
               leaf code {
                 description "Numeric code value (0 .. 254)";
                 type union {
                   type string {
                     pattern "<.*>|$.*";
                   }
                   type uint16 {
                     range "0 .. 254";
                   }
                 }
               }
             }
             leaf protocol {
               description "Numeric protocol value (0 .. 254)";
               type union {
                 type string {
                   pattern "<.*>|$.*";
                 }
                 type uint16 {
                   range "0 .. 254";
                 }
               }
             }
             container port-range {
               description "Used by port-based AI method";
               uses apply-advanced;
               leaf-list tcp {
                 ordered-by user;
                 description "TCP port range";
                 type string;
                 max-elements 64;
               }
               leaf-list udp {
                 ordered-by user;
                 description "UDP port range";
                 type string;
                 max-elements 64;
               }
             }
             leaf disable {
               description "Disable port-based method for this application";
               type empty;
             }
           }
           container icmp-mapping {
             description "Match ICMP message";
             uses apply-advanced;
             leaf type {
               description "Numeric type value";
               type union {
                 type string {
                   pattern "<.*>|$.*";
                 }
                 type uint16 {
                   range "0 .. 254";
                 }
               }
             }
             leaf code {
               description "Numeric code value";
               type union {
                 type string {
                   pattern "<.*>|$.*";
                 }
                 type uint16 {
                   range "0 .. 254";
                 }
               }
             }
             leaf order {
               description "The Order value";
               status deprecated;
               type union {
                 type string {
                   pattern "<.*>|$.*";
                 }
                 type uint16 {
                   range "0 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           container ip-protocol-mapping {
             description "Match IP protocol";
             uses apply-advanced;
             leaf protocol {
               description "Numeric protocol value";
               type union {
                 type string {
                   pattern "<.*>|$.*";
                 }
                 type uint16 {
                   range "0 .. 254";
                 }
               }
             }
             leaf order {
               description "The Order value";
               status deprecated;
               type union {
                 type string {
                   pattern "<.*>|$.*";
                 }
                 type uint16 {
                   range "0 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           list address-mapping {
             key name;
             ordered-by user;
             description "Match IP address";
             leaf name {
               description "Address name";
               type string {
                 length "1 .. 63";
               }
             }
             uses apply-advanced;
             container filter {
               description "Match IP/port";
               uses apply-advanced;
               leaf ip {
                 description "IP address and prefix-length";
                 type jt:ipprefix;
               }
               container port-range {
                 description "Port ranges";
                 uses apply-advanced;
                 leaf-list tcp {
                   ordered-by user;
                   description "TCP port range";
                   type string;
                   max-elements 20;
                 }
                 leaf-list udp {
                   ordered-by user;
                   description "UDP port range";
                   type string;
                   max-elements 20;
                 }
               }
             }
             container source {
               description "Match IP source address";
               uses apply-advanced;
               leaf ip {
                 description "IP address and prefix-length";
                 type jt:ipprefix;
               }
               container wildcard-address {
                 description "IP wildcard address and mask";
                 leaf address {
                   description "IP wildcard address";
                   type jt:ipaddr;
                 }
                 leaf wildcard-mask {
                   description "IP wildcard address mask";
                   type jt:ipaddr;
                 }
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             container destination {
               description "Match IP destination address";
               uses apply-advanced;
               leaf ip {
                 description "IP address and prefix-length";
                 type jt:ipprefix;
               }
               container wildcard-address {
                 description "IP wildcard address and mask";
                 leaf address {
                   description "IP wildcard address";
                   type jt:ipaddr;
                 }
                 leaf wildcard-mask {
                   description "IP wildcard address mask";
                   type jt:ipaddr;
                 }
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             leaf order {
               description "Application matching priority";
               status deprecated;
               type union {
                 type string {
                   pattern "<.*>|$.*";
                 }
                 type uint16 {
                   range "1 .. 65535";
                 }
               }
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
           }
           list over {
             key name;
             description "Set of L4/L7 application that carries given application";
             max-elements 8;
             leaf name {
               description "A unique application and protocol identifier";
               type string {
                 length "1 .. 63";
               }
             }
             uses apply-advanced;
             leaf protocol {
               description "Application protocol";
               status deprecated;
               type enumeration {
                 enum "http" {
                   description "Application over http protocol";
                   status deprecated;
                 }
                 enum "ssl" {
                   description "Application over ssl protocol";
                   status deprecated;
                 }
                 enum "udp" {
                   description "Application over over udp protocol";
                   status deprecated;
                 }
                 enum "tcp" {
                   description "Application over tcp protocol";
                   status deprecated;
                 }
               }
             }
             leaf chain-order {
               description "The order of members is used to match the pattern";
               type empty;
             }
             leaf order-priority {
               description "Application matching priority";
               status deprecated;
               default "high";
               type enumeration {
                 enum "high" {
                   description "Highest priority over all other signatures";
                   status deprecated;
                 }
                 enum "low" {
                   description "Lowest priority over all other signatures";
                   status deprecated;
                 }
               }
             }
             leaf order {
               description "The order value";
               status deprecated;
               type union {
                 type string {
                   pattern "<.*>|$.*";
                 }
                 type uint16 {
                   range "0 .. 65535";
                 }
               }
             }
             container port-range {
               description "Apply signature to packets sent to this port range";
               status deprecated;
               uses apply-advanced;
               leaf-list tcp {
                 ordered-by user;
                 description "TCP port range";
                 type string;
                 max-elements 64;
               }
               leaf-list udp {
                 ordered-by user;
                 description "UDP port range";
                 type string;
                 max-elements 64;
               }
             }
             list member {
               key name;
               description "Pattern matched on client-to-server packets";
               status deprecated;
               max-elements 4;
               leaf name {
                 description "A unique application signature member identifier. Must be m01 ..m16";
                 type string {
                   length "1 .. 63";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             list signature {
               key name;
               description "Application signature for pattern matching";
               leaf name {
                 description "A unique application signature identifier";
                 type string {
                   length "1 .. 63";
                 }
               }
               uses apply-advanced;
               leaf-list port-range {
                 ordered-by user;
                 description "Port range";
                 type string;
                 max-elements 64;
               }
               list member {
                 key name;
                 description "Application signature member";
                 leaf name {
                   description "Application signature member identifier in range m01 - m15";
                   type string {
                     length "1 .. 63";
                   }
                 }
                 uses apply-advanced;
                 leaf depth {
                   description "Maximum number of bytes to check for context match";
                   type union {
                     type string {
                       pattern "<.*>|$.*";
                     }
                     type uint32 {
                       range "1 .. 8000";
                     }
                   }
                 }
                 leaf context {
                   description "Context to be matched on";
                   type string;
                 }
                 leaf pattern {
                   description "DFA pattern matched on context";
                   type string {
                   }
                 }
                 leaf direction {
                   description "Connection direction of the packets to apply pattern matching";
                   type enumeration {
                     enum "client-to-server" {
                       description "Client to server";
                     }
                     enum "server-to-client" {
                       description "Server to client";
                     }
                     enum "any" {
                       description "Any direction";
                     }
                   }
                 }
               }
             }
           }
         }
         list nested-application {
           key name;
           description "Configure nested application definition";
           status deprecated;
           leaf name {
             description "A unique application identifier";
             type string {
               length "1 .. 63";
             }
           }
           uses apply-advanced;
           leaf type {
             description "Well-known application such as FACEBOOK and KAZZA";
             type string {
               length "1 .. 63";
             }
           }
           leaf index {
             description "Custom index (32768..65534). Application index";
             status deprecated;
             type union {
               type string {
                 pattern "<.*>|$.*";
               }
               type uint16 {
                 range "1 .. 65534";
               }
             }
           }
           leaf protocol {
             description "Name of layer 7 application that carries nested application";
             type string {
               length "1 .. 63";
             }
           }
           list signature {
             key name;
             description "Nested application signature for pattern matching";
             leaf name {
               description "A unique nested application signature identifier";
               type string {
                 length "1 .. 63";
               }
             }
             uses apply-advanced;
             list member {
               key name;
               description "Pattern matched on client-to-server packets";
               leaf name {
                 description "A unique nested application signature member identifier";
                 type string {
                   length "1 .. 63";
                 }
               }
               uses apply-advanced;
               leaf context {
                 description "Context to be matched on";
                 type string;
               }
               leaf pattern {
                 description "Pattern matched on context";
                 type string;
               }
               leaf direction {
                 description "Connection direction of the packets to apply pattern matching";
                 type enumeration {
                   enum "client-to-server" {
                     description "Client to server";
                   }
                   enum "server-to-client" {
                     description "Server to client";
                   }
                   enum "any" {
                     description "Any direction";
                   }
                 }
               }
               leaf check-bytes {
                 description "Maximum number of bytes to check for stream context ";
                 default "1000";
                 type union {
                   type string {
                     pattern "<.*>|$.*";
                   }
                   type uint32 {
                     range "1 .. 5000";
                   }
                 }
               }
             }
             leaf chain-order {
               description "The order of members is used to match the pattern";
               type empty;
             }
             leaf maximum-transactions {
               description "Maximum number of transactions matched by AI";
               type union {
                 type uint16;
                 type string {
                   pattern "<.*>|$.*";
                 }
               }
             }
             leaf order {
               description "Application matching priority";
               status deprecated;
               type union {
                 type string {
                   pattern "<.*>|$.*";
                 }
                 type uint16 {
                   range "1 .. 65535";
                 }
               }
             }
             container insert-before {
               description "Insert before another signature";
               uses apply-advanced;
               leaf insert-before-name {
                 description "An application name";
                 type string;
               }
             }
           }
         }
         list application-group {
           key name;
           description "Define application group";
           leaf name {
             description "A unique application group identifier";
             type string {
               length "1 .. 63";
             }
           }
           uses apply-advanced;
           list tag-group {
             key name;
             description "Configure application tag group that belong to this application group";
             leaf name {
               description "A unique tag group identifier";
               type string {
                 length "1 .. 63";
               }
             }
             uses apply-advanced;
             leaf-list application-tags {
               ordered-by user;
               description "Name of application tag to configure";
               type string;
               max-elements 128;
             }
           }
           list application-groups {
             key name;
             description "Configure child application group(s)";
             leaf name {
               description "Name of the child application group";
               type string {
                 length "1 .. 63";
               }
             }
             uses apply-advanced;
           }
           list applications {
             key name;
             description "Configure applications that belong to this application group";
             leaf name {
               description "Configure application name";
               type string {
                 length "1 .. 63";
               }
             }
             uses apply-advanced;
           }
           leaf disable {
             description "Disable this application group definition in AI";
             status deprecated;
             type empty;
           }
         }
         list rule {
           key name;
           ordered-by user;
           description "One or more application rules for address-based method AI";
           status deprecated;
           leaf name {
             description "Rule name";
             type string {
               length "1 .. 63";
             }
           }
           uses apply-advanced;
           leaf application-name {
             description "Name of application that is target of this rule";
             type string {
               length "1 .. 63";
             }
           }
           list address {
             key name;
             ordered-by user;
             description "Configure one of more addresses";
             leaf name {
               description "Address name";
               type string;
             }
             uses apply-advanced;
             container source {
               description "Match IP source address";
               uses apply-advanced;
               leaf ip {
                 description "IP address and prefix-length";
                 type jt:ipv4prefix;
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             container destination {
               description "Match IP destination address";
               uses apply-advanced;
               leaf ip {
                 description "IP address and prefix-length";
                 type jt:ipv4prefix;
               }
               container port-range {
                 description "IP port ranges";
                 uses apply-advanced;
                 leaf-list tcp {
                   ordered-by user;
                   description "TCP port range";
                   type string;
                   max-elements 64;
                 }
                 leaf-list udp {
                   ordered-by user;
                   description "UDP port range";
                   type string;
                   max-elements 64;
                 }
               }
             }
             leaf order {
               description "Application matching priority";
               type union {
                 type string {
                   pattern "<.*>|$.*";
                 }
                 type uint16 {
                   range "1 .. 65535";
                 }
               }
             }
           }
         }
         list rule-set {
           key name;
           ordered-by user;
           description "One or more application rules";
           status deprecated;
           leaf name {
             description "Name of the rule set";
             type string {
               length "1 .. 63";
             }
           }
           uses apply-advanced;
           list rule {
             key name;
             ordered-by user;
             description "Rule to be included in this rule set";
             leaf name {
               description "Rule name";
               type string {
               }
             }
             uses apply-advanced;
           }
         }
         list profile {
           key name;
           ordered-by user;
           description "One or more application rule-sets";
           leaf name {
             description "Profile name";
             type string {
               length "1 .. 63";
             }
           }
           uses apply-advanced;
           list rule-set {
             key name;
             ordered-by user;
             description "One or more rule-sets in the profile";
             status deprecated;
             leaf name {
               description "Rule-set name";
               type string {
                 length "1 .. 63";
               }
             }
             uses apply-advanced;
           }
         }
         container traceoptions {
           description "Trace options for application identification";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Events and other information to include in trace output";
             leaf name {
               description "Flag name to include in trace output";
               type enumeration {
                 enum "all" {
                   description "All events";
                 }
               }
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
         }
         container inspection-limit {
           description "Bytes and packets limit for AppID inspection.";
           uses apply-advanced;
           container tcp {
             presence "enable tcp";
             description "TCP byte/packet inspection limit.";
             uses apply-advanced;
             leaf byte-limit {
               description "TCP byte inspection limit. (Default 6000)";
               default "6000";
               type union {
                 type uint32;
                 type string {
                   pattern "<.*>|$.*";
                 }
               }
             }
             leaf packet-limit {
               description "TCP packet inspection limit.";
               type union {
                 type uint32;
                 type string {
                   pattern "<.*>|$.*";
                 }
               }
             }
           }
           container udp {
             presence "enable udp";
             description "UDP byte/packet inspection limit.";
             uses apply-advanced;
             leaf byte-limit {
               description "UDP byte inspection limit.";
               type union {
                 type uint32;
                 type string {
                   pattern "<.*>|$.*";
                 }
               }
             }
             leaf packet-limit {
               description "UDP packet inspection limit. (Default 10)";
               default "10";
               type union {
                 type uint32;
                 type string {
                   pattern "<.*>|$.*";
                 }
               }
             }
           }
         }
         leaf global-offload-byte-limit {
           description "Global byte limit to offload AppID inspection. (Default 10000)";
           default "10000";
           type union {
             type uint32;
             type string {
               pattern "<.*>|$.*";
             }
           }
         }
         container packet-capture {
           description "To capture the unknown application traffic";
           uses apply-advanced;
           leaf global {
             description "Enable global capturing of application traffic";
             type empty;
           }
           leaf aggressive-mode {
             description "This mode captures all traffic prior to AppID classification";
             type empty;
           }
           leaf max-packets {
             description "Maximum number of UDP packets per session";
             type union {
               type string {
                 pattern "<.*>|$.*";
               }
               type uint32 {
                 range "1 .. 1000";
               }
             }
           }
           leaf max-bytes {
             description "Maximum number of TCP bytes per session";
             units "bytes";
             type union {
               type string {
                 pattern "<.*>|$.*";
               }
               type uint32 {
                 range "40 .. 1073741824";
               }
             }
           }
           leaf max-files {
             description "Maximum number of unique pcap files";
             type union {
               type string {
                 pattern "<.*>|$.*";
               }
               type uint32 {
                 range "1 .. 2500";
               }
             }
           }
           leaf no-inconclusive {
             description "Disable capturing of inconclusive traffic";
             type empty;
           }
           leaf storage-limit {
             description "Maximum disk space";
             units "bytes";
             type string;
           }
           leaf buffer-packets-limit {
             description "Maximum memory to buffer packets";
             units "bytes";
             type union {
               type uint64;
               type string {
                 pattern "<.*>|$.*";
               }
             }
           }
           leaf capture-interval {
             description "Timeout to avoid repetitive capture of same traffic (minutes)";
             type union {
               type string {
                 pattern "<.*>|$.*";
               }
               type uint32 {
                 range "1 .. 525600";
               }
             }
           }
           leaf capture-limit {
             description "Number of repetitive captures of same traffic";
             type union {
               type string {
                 pattern "<.*>|$.*";
               }
               type uint32 {
                 range "1 .. 1000";
               }
             }
           }
           leaf ssl-unknown {
             description "This mode captures all SSL unknown traffic";
             type empty;
           }
         }
         leaf l3l4-app-reclassification {
           description "Enable l3l4 custom app to be reclassified by jdpi ignoring results from other plugins";
           type empty;
         }
         leaf nb-flows-limit {
           description "Maximum number of nb flows";
           type union {
             type uint32;
             type string {
               pattern "<.*>|$.*";
             }
           }
         }
       }
       list service-set {
         key name;
         ordered-by user;
         description "Define a service set";
         leaf name {
           description "Service set name";
           type string {
             length "1 .. 52";
           }
         }
         uses apply-advanced;
         container syslog {
           description "Define system logging parameters";
           uses log-object;
         }
         leaf max-flows {
           description "Maximum number of flows allowed for a service set";
           type string;
         }
         leaf hosted-service-identifier {
           description "Service Set to Hosted service Map";
           type union {
             type string {
               pattern "<.*>|$.*";
             }
             type int32 {
               range "1 .. 63";
             }
           }
         }
         leaf max-session-setup-rate {
           description "Maximum number of session creations allowed per second";
           type string;
         }
         container max-drop-flows {
           description "Maximum number of drop flows allowed for a service-set";
           uses apply-advanced;
           leaf ingress {
             description "Maximum number of ingress drop flows allowed";
             type union {
               type string {
                 pattern "<.*>|$.*";
               }
               type int32 {
                 range "0 .. 8500000";
               }
             }
           }
           leaf egress {
             description "Maximum number of egress drop flows allowed";
             type union {
               type string {
                 pattern "<.*>|$.*";
               }
               type int32 {
                 range "0 .. 8500000";
               }
             }
           }
         }
         container snmp-trap-thresholds {
           presence "enable snmp-trap-thresholds";
           description "Define snmp traps for service sets";
           uses apply-advanced;
           container flow {
             presence "enable flow";
             description "Flow Threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
           container nat-address-port {
             presence "enable nat-address-port";
             description "Nat Address and port usage trap threshold range";
             leaf low {
               description "Lower limit of trap threshold";
               units "percent";
               type union {
                 type string {
                   pattern "<.*>|$.*";
                 }
                 type uint16 {
                   range "0 .. 100";
                 }
               }
             }
             leaf high {
               description "Upper limit of trap threshold";
               units "percent";
               type union {
                 type string {
                   pattern "<.*>|$.*";
                 }
                 type uint16 {
                   range "0 .. 100";
                 }
               }
             }
           }
           container session {
             presence "enable session";
             description "Session threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
         }
         leaf tcp-mss {
           description "Enable the limit on TCP Max. Seg. Size in SYN packets";
           type union {
             type string {
               pattern "<.*>|$.*";
             }
             type uint16 {
               range "536 .. 65535";
             }
           }
         }
         container cos-options {
           presence "enable cos-options";
           description "Options for COS service";
           uses apply-advanced;
           leaf match-rules-on-reverse-flow {
             description "If forward rules match fails, do it on reverse flow";
             type empty;
           }
         }
         container softwire-options {
           presence "enable softwire-options";
           description "Options for softwire";
           uses apply-advanced;
           leaf dslite-ipv6-prefix-length {
             description "The ipv6 prefix length for subscriber addresses";
             default "128";
             type enumeration {
               enum "56" {
                 description "The ipv6 prefix length of 56";
               }
               enum "64" {
                 description "The ipv6 prefix length of 64";
               }
               enum "96" {
                 description "The ipv6 prefix length of 96";
               }
               enum "128" {
                 description "The ipv6 prefix length of 128";
               }
             }
           }
         }
         container nat-options {
           description "Options for NAT";
           uses apply-advanced;
           container stateful-nat64 {
             description "Options for stateful NAT64";
             uses apply-advanced;
             leaf no-v6-frag-header {
               description "No fragmentation header in IPv6 header during IPv4 to IPv6 translation";
               type empty;
             }
             leaf clear-dont-fragment-bit {
               description "Clear DF bit in IPv4 header if IPv6 packet size is less than 1280 bytes";
               type empty;
             }
             leaf ipv6-mtu {
               description "Path MTU of IPv6 network";
               type union {
                 type string {
                   pattern "<.*>|$.*";
                 }
                 type uint16 {
                   range "1280 .. 9192";
                 }
               }
             }
             leaf disable-h323-ras {
               description "Disable H323 and RAS ALG for NAT64";
               type empty;
             }
           }
           container nptv6 {
             description "Options for NPTv6";
             uses apply-advanced;
             leaf icmpv6-error-messages {
               description "Send ICMP Error messages if NPTv6 address translation fails";
               type empty;
             }
           }
           leaf land-attack-check {
             description "Enable land attack checks";
             type enumeration {
               enum "ip-only" {
                 description "Land attack check is on IP address only";
               }
               enum "ip-port" {
                 description "Land attack check is on both IP and port";
               }
             }
           }
           leaf max-sessions-per-subscriber {
             description "Limit the number of sessions per subscriber";
             type union {
               type string {
                 pattern "<.*>|$.*";
               }
               type uint16 {
                 range "1 .. 32000";
               }
             }
           }
           leaf snmp-value-match-msmic {
             description "Match the MSMIC specific snmp values for the msdpc";
             type empty;
           }
         }
         container service-set-options {
           presence "enable service-set-options";
           description "Options for service set";
           uses apply-advanced;
           leaf tcp-non-syn {
             description "Deny session creation on receiving first non SYN pkt";
             type enumeration {
               enum "drop-flow" {
                 description "Drop tcp non SYN first packe";
               }
               enum "drop-flow-send-rst" {
                 description "Enable sending TCP RST on receiving first non SYN pkt";
               }
             }
           }
           leaf tcp-fast-open {
             description "Tcp-fast-Open enabled packets will be handled accordingly";
             type enumeration {
               enum "disabled" {
                 description "TFO option will be stripped and packet will be forwarded";
               }
               enum "drop" {
                 description "TFO enabled packets will be dropeed";
               }
             }
           }
           leaf bypass-traffic-on-pic-failure {
             description "Bypass traffic on service PIC failure";
             type empty;
           }
           leaf bypass-traffic-on-exceeding-flow-limits {
             description "Bypass traffic when exceeding the max flow limit";
             type empty;
           }
           leaf enable-asymmetric-traffic-processing {
             description "Enable service-processing for asymmetric traffic";
             type empty;
           }
           leaf subscriber-awareness {
             description "Enable subscriber awareness on the service chain";
             type empty;
           }
           leaf static-subscriber-application {
             description "Enable static subscriber on the service set";
             type empty;
           }
           container header-integrity-check {
             description "Enable/Disable header integrity checks";
             uses apply-advanced;
             leaf enable-all {
               description "Enable all header integrity checks";
               type empty;
             }
           }
           leaf enable-descriptive-session-syslog {
             description "This knob enables descriptive session syslogs for OPEN and CLOSE";
             type empty;
           }
           leaf enable-change-on-ams-redistribution {
             description "Allow NAT pool change on AMS redistribution";
             status deprecated;
             type empty;
           }
           leaf routing-engine-services {
             description "Enable service-processing at RE";
             type empty;
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           container session-limit {
             presence "enable session-limit";
             description "Session limit";
             uses apply-advanced;
             leaf maximum {
               description "Maximum number of sessions allowed simultaneously";
               type string;
             }
           }
           leaf max-sessions-per-subscriber {
             description "Limit the number of sessions per subscriber";
             type union {
               type string {
                 pattern "<.*>|$.*";
               }
               type uint16 {
                 range "1 .. 32000";
               }
             }
           }
           container tcp-session {
             presence "enable tcp-session";
             description "Transmission Control Protocol session configuration";
             uses apply-advanced;
             leaf tcp-mss {
               description "Enable the limit on TCP Max. Seg. Size in SYN packets";
               type union {
                 type string {
                   pattern "<.*>|$.*";
                 }
                 type uint16 {
                   range "536 .. 65535";
                 }
               }
             }
             leaf tcp-tickles {
               description "Number of TCP keep-alive packets to be sent for bi-directional TCP flows";
               default "4";
               type union {
                 type string {
                   pattern "<.*>|$.*";
                 }
                 type uint8 {
                   range "0 .. 30";
                 }
               }
             }
             leaf open-timeout {
               description "Timeout period for TCP session establishment";
               units "seconds";
               type union {
                 type string {
                   pattern "<.*>|$.*";
                 }
                 type uint32 {
                   range "4 .. 300";
                 }
               }
             }
             leaf inactivity-tcp-timeout {
               description "Inactivity timeout period for TCP established sessions";
               units "seconds";
               type union {
                 type string {
                   pattern "<.*>|$.*";
                 }
                 type uint32 {
                   range "4 .. 86400";
                 }
               }
             }
             leaf inactivity-asymm-tcp-timeout {
               description "Inactivity timeout period for asymmetric TCP established sessions";
               units "seconds";
               type union {
                 type string {
                   pattern "<.*>|$.*";
                 }
                 type uint32 {
                   range "4 .. 86400";
                 }
               }
             }
             container ignore-errors {
               presence "enable ignore-errors";
               description "Ignore anomalies or errors";
               leaf tcp {
                 description "TCP protocol errors";
                 type empty;
               }
             }
             leaf close-timeout {
               description "Timeout period for TCP session tear-down";
               units "seconds";
               type union {
                 type string {
                   pattern "<.*>|$.*";
                 }
                 type uint32 {
                   range "2 .. 300";
                 }
               }
             }
             leaf tcp-non-syn {
               description "Deny session creation on receiving first non SYN pkt";
               type enumeration {
                 enum "drop-flow" {
                   description "Drop tcp non SYN first packe";
                 }
                 enum "drop-flow-send-rst" {
                   description "Enable sending TCP RST on receiving first non SYN pkt";
                 }
               }
             }
             leaf tcp-fast-open {
               description "Tcp-fast-Open enabled paclets will be handled accordingly";
               type enumeration {
                 enum "disabled" {
                   description "TFO option will be stripped and packet will be forwarded";
                 }
                 enum "drop" {
                   description "TFO enabled packets will be dropeed";
                 }
               }
             }
           }
           leaf enforce-global-timeout {
             description "Enforce global inactivity or session timeout";
             type empty;
           }
           leaf unidirectional-session-refreshing {
             description "Enable unidirectional session refreshing on this service-set";
             type enumeration {
               enum "input" {
                 description "Enable unidirectional session refreshing on input";
               }
               enum "output" {
                 description "Enable unidirectional session refreshing on output";
               }
             }
           }
         }
         container replicate-services {
           description "Define services that will be replicated to peer.";
           uses apply-advanced;
           leaf replication-threshold {
             description "Duration in seconds for which flow should remain active for replication. (Min 180s)";
             default "180";
             type union {
               type string {
                 pattern "<.*>|$.*";
               }
               type uint32 {
                 range "180 .. 86400";
               }
             }
           }
           leaf disable-replication-capability {
             description "Disable replication capability for this service-set";
             type empty;
           }
         }
         container allow-multicast {
           presence "enable allow-multicast";
           description "Allow multicast packets";
           uses apply-advanced;
         }
         choice softwire_choice {
           case case_1 {
             list softwire-rules {
               key name;
               ordered-by user;
               description "List of softwire rules";
               leaf name {
                 type string {
                   length "1 .. 63";
                 }
               }
               uses apply-advanced;
             }
           }
           case case_2 {
             list softwire-rule-sets {
               key name;
               ordered-by user;
               description "List of softwire rule sets";
               leaf name {
                 type string {
                   length "1 .. 63";
                 }
               }
               uses apply-advanced;
             }
           }
         }
         list softwires-rule-set {
           key name;
           ordered-by user;
           description "List of softwire rule sets";
           leaf name {
             type string {
               length "1 .. 63";
             }
           }
           uses apply-advanced;
         }
         choice stateful_firewall_rules_choice {
           case case_1 {
             list stateful-firewall-rules {
               key name;
               ordered-by user;
               description "List of stateful firewall rules";
               leaf name {
                 type string {
                   length "1 .. 63";
                 }
               }
               uses apply-advanced;
             }
           }
           case case_2 {
             list stateful-firewall-rule-sets {
               key name;
               ordered-by user;
               description "List of stateful firewall rule sets";
               leaf name {
                 type string {
                   length "1 .. 63";
                 }
               }
               uses apply-advanced;
             }
           }
         }
         choice ids-option-choice {
           case case_1 {
             list ids-option {
               key name;
               ordered-by user;
               description "List of ids-options";
               leaf name {
                 type string {
                   length "1 .. 31";
                 }
               }
               uses apply-advanced;
             }
           }
         }
         choice pcp_rules_choice {
           case case_1 {
             list pcp-rules {
               key name;
               ordered-by user;
               description "List of PCP rules";
               leaf name {
                 type string {
                   length "1 .. 63";
                 }
               }
               uses apply-advanced;
             }
           }
           case case_2 {
             list pcp-rule-sets {
               key name;
               ordered-by user;
               description "List of PCP rule sets";
               leaf name {
                 type string {
                   length "1 .. 63";
                 }
               }
               uses apply-advanced;
             }
           }
         }
         leaf appid-profile {
           description "Define AppID profile";
           type string {
             length "1 .. 63";
           }
         }
         choice nat_rules_choice {
           case case_1 {
             list nat-rules {
               key name;
               ordered-by user;
               description "List of NAT rules";
               leaf name {
                 type string {
                   length "1 .. 63";
                 }
               }
               uses apply-advanced;
             }
           }
           case case_2 {
             list nat-rule-sets {
               key name;
               ordered-by user;
               description "List of NAT rule sets";
               leaf name {
                 type string {
                   length "1 .. 63";
                 }
               }
               uses apply-advanced;
             }
           }
         }
         choice ip_reassembly_rules_choice {
           case case_1 {
             list ip-reassembly-rules {
               key name;
               ordered-by user;
               description "List of ip-reassembly rules";
               leaf name {
                 type string {
                   length "1 .. 63";
                 }
               }
               uses apply-advanced;
             }
           }
         }
         choice ids_rules_choice {
           case case_1 {
             list ids-rules {
               key name;
               ordered-by user;
               description "List of IDS rules";
               leaf name {
                 type string {
                   length "1 .. 63";
                 }
               }
               uses apply-advanced;
             }
           }
           case case_2 {
             list ids-rule-sets {
               key name;
               ordered-by user;
               description "List of IDS rule sets";
               leaf name {
                 type string {
                   length "1 .. 63";
                 }
               }
               uses apply-advanced;
             }
           }
         }
         choice cos_rules_choice {
           case case_1 {
             list cos-rules {
               key name;
               ordered-by user;
               description "One or more CoS rules";
               leaf name {
                 description "Rule name";
                 type string {
                   length "1 .. 63";
                 }
               }
               uses apply-advanced;
             }
           }
           case case_2 {
             list cos-rule-sets {
               key name;
               ordered-by user;
               description "One or more CoS rule sets";
               leaf name {
                 description "Name of rule set";
                 type string {
                   length "1 .. 63";
                 }
               }
               uses apply-advanced;
             }
           }
         }
         choice aacl_rules_choice {
           case case_1 {
             list aacl-rules {
               key name;
               ordered-by user;
               description "One or more AACL rules";
               leaf name {
                 description "Rule name";
                 type string {
                   length "1 .. 63";
                 }
               }
               uses apply-advanced;
             }
           }
           case case_2 {
             list aacl-rule-sets {
               key name;
               ordered-by user;
               description "One or more AACL rule sets";
               leaf name {
                 description "Name of rule set";
                 type string {
                   length "1 .. 63";
                 }
               }
               uses apply-advanced;
             }
           }
         }
         list aacl-dyn-rules {
           key name;
           ordered-by user;
           description "One or more AACL rule ";
           leaf name {
             description "Name of dynamic rule set";
             type string {
               length "1 .. 63";
             }
           }
           uses apply-advanced;
         }
         choice pgcp_rules_choice {
           case case_1 {
             list pgcp-rules {
               key name;
               ordered-by user;
               description "One or more PGCP rules";
               leaf name {
                 description "Rule name";
                 type string {
                   length "1 .. 63";
                 }
               }
               uses apply-advanced;
             }
           }
           case case_2 {
             list pgcp-rule-sets {
               key name;
               ordered-by user;
               description "One or more PGCP rule sets";
               leaf name {
                 description "Name of rule set";
                 type string {
                   length "1 .. 63";
                 }
               }
               uses apply-advanced;
             }
           }
         }
         container jflow-rules {
           presence "enable jflow-rules";
           description "One or more jflow rules";
           uses apply-advanced;
           container sampling {
             presence "enable sampling";
             uses apply-advanced;
             leaf instance {
               description "Name of the instance";
               type string {
                 length "1 .. 64";
               }
             }
           }
         }
         choice appid-choice {
           case case_1 {
             leaf application-identification-profile {
               description "Define Application Identification profile";
               type string {
                 length "1 .. 63";
               }
             }
           }
         }
         leaf pcef-profile {
           description "Define PCEF profile";
           type string {
             length "1 .. 63";
           }
         }
         leaf lrf-profile {
           description "Define logging and reporting profile";
           type string {
             length "1 .. 63";
           }
         }
         leaf hcm-profile {
           description "Define HCM profile";
           type string {
             length "1 .. 63";
           }
         }
         leaf web-filter-profile {
           description "Define WEB filtering profile";
           type string {
             length "1 .. 63";
           }
         }
         choice hcm_url_rules_choice {
           case case_1 {
             list hcm-url-rules {
               key name;
               ordered-by user;
               description "One or more HCM uri rules";
               leaf name {
                 description "Rule name";
                 type string {
                   length "1 .. 63";
                 }
               }
               uses apply-advanced;
             }
           }
           case case_2 {
             list hcm-url-rule-sets {
               key name;
               ordered-by user;
               description "One or more HCM url rule sets";
               leaf name {
                 description "Name of rule set";
                 type string {
                   length "1 .. 63";
                 }
               }
               uses apply-advanced;
             }
           }
         }
         choice hcm-tag-rules-choice {
           case case_1 {
             list tag-rules {
               key name;
               ordered-by user;
               description "One or more HCM tag rules";
               leaf name {
                 description "Rule name";
                 type string {
                   length "1 .. 63";
                 }
               }
               uses apply-advanced;
             }
           }
           case case_2 {
             list tag-rule-sets {
               key name;
               ordered-by user;
               description "One or more HCM tag rule sets";
               leaf name {
                 description "Name of rule set";
                 type string {
                   length "1 .. 63";
                 }
               }
               uses apply-advanced;
             }
           }
         }
         choice idppolicy-choice {
           case case_1 {
             leaf idp-profile {
               description "IDP policy to use";
               type string {
                 length "1 .. 63";
               }
             }
           }
         }
         choice cpcdd-choice {
           case case_1 {
             leaf captive-portal-content-delivery-profile {
               description "Define captive portal and content delivery profile";
               type string {
                 length "1 .. 63";
               }
             }
           }
         }
         choice lpdf-stats-choice {
           case case_1 {
             container policy-decision-statistics-profile {
               description "Define policy decision statistics profile";
               uses apply-advanced;
               leaf profile-name {
                 description "Policy decision statistics profile name";
                 type string {
                   length "1 .. 63";
                 }
               }
             }
           }
         }
         choice service_type_choice {
           case case_1 {
             container interface-service {
               description "Define parameters for interface-specific service sets";
               uses apply-advanced;
               leaf service-interface {
                 description "Services interface to use";
                 type union {
                   type jt:interface-unit;
                   type string {
                     pattern "<.*>|$.*";
                   }
                 }
               }
               container load-balancing-options {
                 uses apply-advanced;
                 container hash-keys {
                   presence "enable hash-keys";
                   uses apply-advanced;
                   leaf resource-triggered {
                     description "Resource Triggered load balancing";
                     type empty;
                   }
                   leaf-list ingress-key {
                     ordered-by user;
                     description "Hash Key for the ingress direction";
                     type enumeration {
                       enum "source-ip" {
                         description "Source Ip Address";
                       }
                       enum "destination-ip" {
                         description "Destination Ip Address";
                       }
                       enum "protocol" {
                         description "Protocol";
                       }
                       enum "iif" {
                         description "Incoming Interface";
                       }
                     }
                   }
                   leaf-list egress-key {
                     ordered-by user;
                     description "Hash Key for the egress direction";
                     type enumeration {
                       enum "source-ip" {
                         description "Source Ip Address";
                       }
                       enum "destination-ip" {
                         description "Destination Ip Address";
                       }
                       enum "protocol" {
                         description "Protocol";
                       }
                       enum "oif" {
                         description "Outgoing Interface";
                       }
                     }
                   }
                 }
               }
             }
           }
           case case_2 {
             container sampling-service {
               description "Define parameters for sampling service sets";
               uses apply-advanced;
               leaf service-interface {
                 description "Services interface to use";
                 type union {
                   type jt:interface-unit;
                   type string {
                     pattern "<.*>|$.*";
                   }
                 }
               }
             }
           }
           case case_3 {
             container next-hop-service {
               description "Define parameters for next-hop service sets";
               uses apply-advanced;
               leaf inside-service-interface {
                 description "Service interface to inside network";
                 type union {
                   type jt:interface-unit;
                   type string {
                     pattern "<.*>|$.*";
                   }
                 }
               }
               leaf outside-service-interface {
                 description "Service interface name";
                 type union {
                   type jt:interface-unit;
                   type string {
                     pattern "<.*>|$.*";
                   }
                 }
               }
               leaf outside-service-interface-type {
                 description "Service interface type local for reassembly service";
                 type enumeration {
                   enum "local" {
                     description "Must be local for reassembly service";
                   }
                 }
               }
               leaf service-interface-pool {
                 description "Service interface pool name";
                 type string {
                   length "1 .. 63";
                 }
               }
             }
           }
         }
         list extension-service {
           key name;
           ordered-by user;
           description "Define the customer specific extensions";
           max-elements 2;
           leaf name {
             description "Customer-prefixed service name";
             type string {
               length "1 .. 63";
             }
           }
           uses apply-advanced;
         }
         container service-order {
           presence "enable service-order";
           description "Define of order of services to be applied";
           uses apply-advanced;
           leaf-list forward-flow {
             ordered-by user;
             description "Service Order for forward flow";
             type string;
           }
           leaf-list reverse-flow {
             ordered-by user;
             description "Service Order for reverse flow";
             type string;
           }
         }
         container jflow-log {
           description "Define Jflow-logging parameters.";
           uses apply-advanced;
           leaf template-profile {
             description "Allow jflow messages for applications";
             type string {
               length "1 .. 63";
             }
           }
         }
         container flow {
           description "Define flow parameters";
           uses apply-advanced;
           container traceoptions {
             description "Trace options for flow services";
             uses flow-traceoptions-object;
           }
         }
         leaf-list ipsec-vpn {
           ordered-by user;
           description "List of IPsec VPN policies";
           type string;
         }
         leaf redundancy-set-id {
           description "Redundancy set identifier";
           type union {
             type string {
               pattern "<.*>|$.*";
             }
             type uint32 {
               range "1 .. 100";
             }
           }
         }
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
         container proxy {
           description "Configuration for Secure Socket Layer proxy support service";
           uses ssl-proxy-config;
         }
       }
       container web-proxy {
         description "Configuration for Web Proxy service";
         uses apply-advanced;
         container traceoptions {
           description "Trace options for Web Proxy service";
           uses web-proxy-traceoptions;
         }
         container secure-proxy {
           description "Configuration for Secure Web Proxy profile ";
           status deprecated;
           uses web-config;
         }
         container transparent-proxy {
           description "Configuration for transparent proxy profile ";
           uses web-config;
         }
         container explicit-proxy {
           description "Configuration for explicit proxy profile ";
           uses explicit-config;
         }
       }
       container softwires {
         description "Configure softwire feature";
         uses softwires-object;
       }
       container screen {
         description "Configure screen feature";
         uses apply-advanced;
         container trap {
           presence "enable trap";
           description "Configure trap interval";
           leaf interval {
             description "Trap interval";
             default "2";
             units "seconds";
             type union {
               type string {
                 pattern "<.*>|$.*";
               }
               type uint32 {
                 range "1 .. 3600";
               }
             }
           }
         }
         container cpu-throttle {
           presence "enable cpu-throttle";
           description "Configure cpu-throttle percentage";
           uses apply-advanced;
           leaf percentage {
             description "Percentage of cpu throttle";
             units "percentage";
             type union {
               type string {
                 pattern "<.*>|$.*";
               }
               type uint32 {
                 range "1 .. 100";
               }
             }
           }
         }
         list ids-option {
           key name;
           description "Configure ids-option";
           uses ids-option-type;
         }
         container traceoptions {
           description "Trace options for Network Security Screen";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
         list whitelist {
           key name;
           description "Set of IP addresses for white list";
           max-elements 32;
           uses ids-wlist-type;
         }
       }
       container icap-redirect {
         description "Configure ICAP redirection service";
         uses apply-advanced;
         list profile {
           key name;
           ordered-by user;
           description "Congifure ICAP service profile";
           uses icap-profile-object;
         }
         container traceoptions {
           description "ICAP redirect trace options";
           uses icap-redirect-traceoptions;
         }
       }
       container security-metadata-streaming {
         uses apply-advanced;
         list policy {
           key name;
           description "Security Metadata Streaming policy";
           leaf name {
             description "Policy name";
             type string {
               length "1 .. 63";
             }
           }
           uses apply-advanced;
           container dynamic-filter {
             presence "enable dynamic-filter";
             description "Configure dynamic filtering options";
           }
           container http {
             description "Configure HTTP options";
             uses apply-advanced;
             leaf action {
               description "Action for HTTP";
               status deprecated;
               type enumeration {
                 enum "permit" {
                   description "Allow traffic";
                   status deprecated;
                 }
               }
             }
             container notification {
               description "Notification action taken for traffic";
               status deprecated;
               uses apply-advanced;
               leaf log {
                 description "Logging option for Security Metadata Streaming actions";
                 type empty;
               }
             }
             container detections {
               description "Type of Detection Methods for DNS Request";
               uses apply-advanced;
               container encryptedc2 {
                 description "Detection on the HTTPS";
                 uses apply-advanced;
                 leaf action {
                   description " Action to take on the HTTPS packet";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for encryptedc2 detection";
                   uses apply-advanced;
                   container notification {
                     description "Notification action taken for the packet";
                     uses apply-advanced;
                     leaf log {
                       description "Log HTTP Request";
                       type empty;
                     }
                   }
                 }
               }
               container all {
                 description "All Detections";
                 uses apply-advanced;
                 leaf action {
                   description "Action for HTTP";
                   type enumeration {
                     enum "permit" {
                       description "Allow traffic";
                     }
                   }
                 }
                 leaf notification {
                   description "Notification action taken for traffic";
                   type enumeration {
                     enum "log" {
                       description "Log Everything";
                     }
                     enum "log-detections" {
                       description "Log only Macilious HTTP detections";
                     }
                   }
                 }
                 container fallback-options {
                   description "Fallback options for the encryptedc2 detection";
                   uses apply-advanced;
                   container notification {
                     description "Notification action taken for the packet";
                     uses apply-advanced;
                     leaf log {
                       description "Log HTTP Request";
                       type empty;
                     }
                   }
                 }
               }
             }
           }
           container dns {
             description "Configure DNS options";
             uses apply-advanced;
             container cache {
               description "Storing DNS in Cache till TTL";
               uses apply-advanced;
               container ttl {
                 presence "enable ttl";
                 description "For setting TTL values";
                 uses apply-advanced;
                 leaf benign {
                   description "Set Benign TTL value";
                   default "86400";
                   units "seconds";
                   type union {
                     type string {
                       pattern "<.*>|$.*";
                     }
                     type uint32 {
                       range "60 .. 172800";
                     }
                   }
                 }
                 leaf c2 {
                   description "Set C2 TTL value";
                   default "86400";
                   units "seconds";
                   type union {
                     type string {
                       pattern "<.*>|$.*";
                     }
                     type uint32 {
                       range "60 .. 172800";
                     }
                   }
                 }
               }
             }
             container detections {
               description "Type of Detection Methods for DNS Request";
               uses apply-advanced;
               container dga {
                 description "Detecting DGA Algorithms on DNS Packets";
                 uses apply-advanced;
                 leaf action {
                   description "Action to take on the DNS tunneled packet";
                   type enumeration {
                     enum "permit" {
                       description "Allow the packet";
                     }
                     enum "deny" {
                       description "Drop the packet";
                     }
                     enum "sinkhole" {
                       description "Sinkhole the packet";
                     }
                   }
                 }
                 leaf verdict-timeout {
                   description "Time to wait for a verdict on DNS Packet";
                   default "100";
                   units "milliseconds";
                   type union {
                     type string {
                       pattern "<.*>|$.*";
                     }
                     type uint32 {
                       range "50 .. 500";
                     }
                   }
                 }
                 leaf notification {
                   description "Notification action taken for DNS DGA Detection";
                   type enumeration {
                     enum "log" {
                       description "Log Everything";
                     }
                     enum "log-detections" {
                       description "Only log malicious DNS activity";
                     }
                   }
                 }
                 container fallback-options {
                   description "Fallback options for DNS DGA detection";
                   uses apply-advanced;
                   container notification {
                     description "Notification action taken for the packet";
                     uses apply-advanced;
                     leaf log {
                       description "Log DNS Request";
                       type empty;
                     }
                   }
                 }
               }
               container tunneling {
                 description "Detecting DNS Tunneling";
                 uses apply-advanced;
                 leaf action {
                   description " Action to take on the DNS tunneled packet";
                   type enumeration {
                     enum "permit" {
                       description "Allow the packet";
                     }
                     enum "deny" {
                       description "Drop the packet";
                     }
                     enum "sinkhole" {
                       description "Sinkhole the packet";
                     }
                   }
                 }
                 leaf notification {
                   description "Notification action taken for DNS Tunneling Detection";
                   type enumeration {
                     enum "log" {
                       description "Log Everything";
                     }
                     enum "log-detections" {
                       description "Only log malicious DNS activity";
                     }
                   }
                 }
                 leaf inspection-depth {
                   description "Number of packets to be inspected for Tunnel Detection";
                   default "4";
                   type union {
                     type string {
                       pattern "<.*>|$.*";
                     }
                     type uint8 {
                       range "0 .. 10";
                     }
                   }
                 }
                 container fallback-options {
                   description "Fallback options for DNS Tunneling detection";
                   uses apply-advanced;
                   container notification {
                     description "Notification action taken for the packet";
                     uses apply-advanced;
                     leaf log {
                       description "Log DNS Request";
                       type empty;
                     }
                   }
                 }
               }
               container all {
                 description "All Detections";
                 uses apply-advanced;
                 leaf action {
                   description " Global Action to take on the DNS packet";
                   type enumeration {
                     enum "permit" {
                       description "Allow the packet";
                     }
                     enum "deny" {
                       description "Drop the packet";
                     }
                     enum "sinkhole" {
                       description "Sinkhole the packet";
                     }
                   }
                 }
                 leaf notification {
                   description "Global Notification action taken for DNS Detection Methods";
                   type enumeration {
                     enum "log" {
                       description "Log Everything";
                     }
                     enum "log-detections" {
                       description "Only log malicious DNS activity";
                     }
                   }
                 }
                 container fallback-options {
                   description "Fallback options for DNS detections";
                   uses apply-advanced;
                   container notification {
                     description "Notification action taken for the packet";
                     uses apply-advanced;
                     leaf log {
                       description "Log DNS Request";
                       type empty;
                     }
                   }
                 }
               }
             }
           }
         }
         container dns-cache {
           description "Storing DNS-Cache user configured lists";
           uses apply-advanced;
           container custom-list {
             description "For setting TTL values";
             uses apply-advanced;
             leaf-list benign {
               description "Set Benign Persistent domains";
               type string {
                 length "1 .. 255";
               }
               max-elements 500;
             }
             leaf-list c2 {
               description "Set C2 Persistent domains";
               type string {
                 length "1 .. 255";
               }
               max-elements 500;
             }
           }
         }
       }
       container anti-virus {
         uses apply-advanced;
         container update {
           description "Anti-virus package download and install options";
           uses apply-advanced;
           container ignore-server-validation {
             presence "enable ignore-server-validation";
             description "Don't check server certificate";
           }
           leaf url {
             description "HTTP/HTTPS URL of Anti-virus package download";
             type string;
           }
           leaf proxy-profile {
             description "Proxy profile";
             type string {
               length "1 .. 63";
             }
           }
           container automatic {
             description "Scheduled download and install";
             uses apply-advanced;
             leaf interval {
               description "Interval in minutes";
               default "5";
               type union {
                 type string {
                   pattern "<.*>|$.*";
                 }
                 type uint32 {
                   range "5 .. 60";
                 }
               }
             }
             container off {
               presence "enable off";
               description "Disable automatic Anti-virus download and install";
             }
           }
         }
         list policy {
           key name;
           description "Anti-virus policy";
           leaf name {
             description "Policy name";
             type string {
               length "1 .. 63";
             }
           }
           uses apply-advanced;
           leaf action {
             description "Action taken when file meets verdict threshold";
             type enumeration {
               enum "permit" {
                 description "Allow contents";
               }
               enum "block" {
                 description "Disallow contents";
               }
             }
           }
           container default-notification {
             description "Notification log when file not meets verdict threshold";
             uses apply-advanced;
             leaf log {
               description "Logging option for anti-virus action";
               type empty;
             }
           }
           container fallback-options {
             description "Fallback options for abnormal conditions";
             uses apply-advanced;
             leaf action {
               description "Action taken for fallback conditions";
               type enumeration {
                 enum "permit" {
                   description "Allow contents";
                 }
                 enum "block" {
                   description "Disallow contents";
                 }
               }
             }
             container notification {
               description "Notification action taken for fallback action";
               uses apply-advanced;
               leaf log {
                 description "Logging option for Advanced Anti-malware fallback action";
                 type empty;
               }
             }
             container invalid-content-size {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container out-of-resources {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
             container service-not-ready {
               description "Content size exceed supported range";
               uses apply-advanced;
               leaf action {
                 description "Action taken for fallback conditions";
                 type enumeration {
                   enum "permit" {
                     description "Allow contents";
                   }
                   enum "block" {
                     description "Disallow contents";
                   }
                 }
               }
               container notification {
                 description "Notification action taken for fallback action";
                 uses apply-advanced;
                 leaf log {
                   description "Logging option for Advanced Anti-malware fallback action";
                   type empty;
                 }
               }
             }
           }
           container http-client-notify {
             description "Notification action taken for contents with verdict meet threshold";
             uses apply-advanced;
             choice http-choice {
               case case_1 {
                 leaf file {
                   description "File name for http response to client";
                   type string {
                     length "1 .. 255";
                   }
                 }
               }
               case case_2 {
                 leaf message {
                   description "Block message to client";
                   type string {
                     length "1 .. 1023";
                   }
                 }
               }
               case case_3 {
                 leaf redirect-url {
                   description "Redirect url to client";
                   type string {
                     length "1 .. 1023";
                   }
                 }
               }
             }
           }
           container notification {
             description "Notification action taken for contents with verdict meet threshold";
             uses apply-advanced;
             leaf log {
               description "Logging option for Advanced Anti-malware actions";
               type empty;
             }
           }
           leaf verdict-threshold {
             description "Verdict threshold";
             type enumeration {
               enum "1" {
                 description "Verdict-threshold level 1";
               }
               enum "2" {
                 description "Verdict-threshold level 2";
               }
               enum "3" {
                 description "Verdict-threshold level 3";
               }
               enum "4" {
                 description "Verdict-threshold level 4";
               }
               enum "5" {
                 description "Verdict-threshold level 5";
               }
               enum "6" {
                 description "Verdict-threshold level 6";
               }
               enum "7" {
                 description "Verdict-threshold level 7";
               }
               enum "8" {
                 description "Verdict-threshold level 8";
               }
               enum "9" {
                 description "Verdict-threshold level 9";
               }
               enum "10" {
                 description "Verdict-threshold level 10";
               }
             }
           }
         }
         container traceoptions {
           description "Anti-virus trace options";
           uses antivirus-traceoptions;
         }
       }
       container user-identification {
         description "Configure user-identification";
         uses apply-advanced;
         container fwauth {
           presence "enable fwauth";
           description "Configure userid fwauth interaction options";
           uses apply-advanced;
           container traceoptions {
             description "Userid fwauth interaction tracing options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "userid-fwauth-group" {
                     description "Trace userid fwauth group opertaions";
                   }
                   enum "userid-fwauth-db" {
                     description "Trace userid fwauth db opertaions";
                   }
                   enum "userid-fwauth-config" {
                     description "Trace userid fwauth config read opertaions";
                   }
                   enum "userid-fwauth-ut" {
                     description "Trace userid fwauth unit test opertaions";
                   }
                   enum "userid-fwauth-all" {
                     description "Trace userid fwauth all opertaions";
                   }
                 }
               }
             }
           }
         }
         container active-directory-access {
           presence "enable active-directory-access";
           description "Configure active directory access";
           uses apply-advanced;
           container traceoptions {
             description "Active-directory-access Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "active-directory-authentication" {
                     description "Trace active directory auth";
                   }
                   enum "configuration" {
                     description "Trace configuration";
                   }
                   enum "db" {
                     description "Trace db";
                   }
                   enum "ip-user-mapping" {
                     description "Trace ip-user-mapping module";
                   }
                   enum "ip-user-probe" {
                     description "Trace ip-user-probe";
                   }
                   enum "ipc" {
                     description "Trace ipc";
                   }
                   enum "user-group-mapping" {
                     description "Trace user-group-mapping module";
                   }
                   enum "wmic" {
                     description "Trace wmic";
                   }
                   enum "memory" {
                     description "Trace memory";
                   }
                   enum "all" {
                     description "Trace everything";
                   }
                 }
               }
             }
           }
           list domain {
             key name;
             ordered-by user;
             description "Configure active-directory-access domain";
             max-elements 2;
             leaf name {
               description "Domain name";
               type string {
                 length "1 .. 64";
               }
             }
             uses apply-advanced;
             container user {
               description "User name";
               uses apply-advanced;
               leaf user-name {
                 description "User name";
                 type string {
                   length "1 .. 64";
                 }
               }
               leaf password {
                 description "Password string";
                 type string {
                   length "1 .. 128";
                 }
               }
             }
             list domain-controller {
               key name;
               ordered-by user;
               description "Domain controller";
               max-elements 10;
               leaf name {
                 description "Domain controller name";
                 type string {
                   length "1 .. 64";
                 }
               }
               uses apply-advanced;
               leaf address {
                 description "Address of domain controller";
                 type jt:ipaddr;
               }
             }
             container ip-user-mapping {
               description "Ip-user-mapping";
               uses apply-advanced;
               container discovery-method {
                 description "Discovery method";
                 uses apply-advanced;
                 container wmi {
                   presence "enable wmi";
                   description "WMI";
                   uses apply-advanced;
                   leaf event-log-scanning-interval {
                     description "Interval of event log scanning";
                     units "seconds";
                     type union {
                       type string {
                         pattern "<.*>|$.*";
                       }
                       type uint16 {
                         range "5 .. 60";
                       }
                     }
                   }
                   leaf initial-event-log-timespan {
                     description "Event log scanning timespan";
                     units "hours";
                     type union {
                       type string {
                         pattern "<.*>|$.*";
                       }
                       type uint16 {
                         range "1 .. 168";
                       }
                     }
                   }
                 }
               }
             }
             container user-group-mapping {
               description "User-group-mapping";
               uses user-group-mapping-type;
             }
           }
           leaf no-on-demand-probe {
             description "Disable on-demand probe";
             type empty;
           }
           leaf authentication-entry-timeout {
             description "Authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           leaf firewall-authentication-forced-timeout {
             description "Firewallauth fallback authentication entry forced timeout number (10-1440)";
             units "minutes";
             type union {
               type uint16;
               type string {
                 pattern "<.*>|$.*";
               }
             }
           }
           leaf wmi-timeout {
             description "Wmi timeout number";
             units "seconds";
             type union {
               type string {
                 pattern "<.*>|$.*";
               }
               type uint32 {
                 range "3 .. 120";
               }
             }
           }
           leaf thread {
             description "Thread to do PC probe";
             type union {
               type string {
                 pattern "<.*>|$.*";
               }
               type uint16 {
                 range "1 .. 100";
               }
             }
           }
           leaf probe-rate {
             description "PC probe rate per minute";
             type union {
               type string {
                 pattern "<.*>|$.*";
               }
               type uint32 {
                 range "100 .. 1500";
               }
             }
           }
           leaf-list event-log-identifier {
             ordered-by user;
             description "Event log identifier";
             type union {
               type uint16;
               type string {
                 pattern "<.*>|$.*";
               }
             }
           }
           leaf-list logon-type {
             ordered-by user;
             description "Logon type";
             type union {
               type uint16;
               type string {
                 pattern "<.*>|$.*";
               }
             }
           }
           container filter {
             description "Configure filter address or prefix";
             uses apply-advanced;
             list include {
               key name;
               ordered-by user;
               description "Include address";
               max-elements 20;
               leaf name {
                 description "Address or prefix";
                 type jt:ipprefix;
               }
             }
             list exclude {
               key name;
               ordered-by user;
               description "Exclude address";
               max-elements 20;
               leaf name {
                 description "Address or prefix";
                 type jt:ipprefix;
               }
             }
           }
         }
         list authentication-source {
           key name;
           ordered-by user;
           description "Configure authentication-source";
           max-elements 2;
           leaf name {
             description "Authenticaton source name";
             type enumeration {
               enum "aruba-clearpass" {
                 description "Authentication source from Aruba ClearPass";
               }
             }
           }
           uses apply-advanced;
           leaf authentication-entry-timeout {
             description "Aruba ClearPass authentication entry timeout number (0, 10-1440)";
             units "minutes";
             type union {
               type uint16;
               type string {
                 pattern "<.*>|$.*";
               }
             }
           }
           leaf invalid-authentication-entry-timeout {
             description "Invalid authentication entry timeout number (0, 10-1440)";
             units "minutes";
             type union {
               type uint16;
               type string {
                 pattern "<.*>|$.*";
               }
             }
           }
           container traceoptions {
             description "Aruba ClearPass authentication table Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace Aruba ClearPass all modules";
                   }
                   enum "clearpass-authentication" {
                     description "Trace Aruba ClearPass auth table management module";
                   }
                   enum "configuration" {
                     description "Trace Aruba ClearPass configuration";
                   }
                   enum "dispatcher" {
                     description "Trace dispatcher module";
                   }
                   enum "ipc" {
                     description "Trace ipc";
                   }
                   enum "user-query" {
                     description "Trace user-query module";
                   }
                   enum "memory" {
                     description "Trace memory";
                   }
                 }
               }
             }
           }
           container user-query {
             description "ClearPass individual user query";
             uses apply-advanced;
             container web-server {
               description "Web server for user query";
               uses apply-advanced;
               leaf server-name {
                 description "Web server name";
                 type string {
                   length "1 .. 64";
                 }
               }
               leaf connect-method {
                 description "Method of connecting to web server";
                 type enumeration {
                   enum "https" {
                     description "HTTPS connection to web server";
                   }
                   enum "http" {
                     description "HTTP connection to web server";
                   }
                 }
               }
               leaf address {
                 description "IP address or hostname of web server";
                 type string {
                   length "1 .. 128";
                 }
               }
               leaf port {
                 description "Web server port";
                 default "443";
                 type union {
                   type string {
                     pattern "<.*>|$.*";
                   }
                   type uint32 {
                     range "1 .. 65535";
                   }
                 }
               }
             }
             leaf ca-certificate {
               description "Ca-certificate file name";
               type string {
                 length "1 .. 256";
               }
             }
             leaf client-id {
               description "Client ID for OAuth2 grant";
               type string {
                 length "1 .. 64";
               }
             }
             leaf client-secret {
               description "Client secret for OAuth2 grant";
               type string {
                 length "1 .. 128";
               }
             }
             leaf token-api {
               description "API of acquiring token for OAuth2 authentication";
               type string {
                 length "1 .. 128";
               }
             }
             leaf query-api {
               description "User query API";
               type string {
                 length "4 .. 128";
               }
             }
             leaf delay-query-time {
               description "Delay time to send user query (0~60sec)";
               default "15";
               units "seconds";
               type union {
                 type string {
                   pattern "<.*>|$.*";
                 }
                 type uint8 {
                   range "0 .. 60";
                 }
               }
             }
           }
           container no-user-query {
             presence "enable no-user-query";
             description "Disable user query from ClearPass";
           }
         }
         container device-information {
           description "Device information configuration";
           uses apply-advanced;
           container authentication-source {
             description "Configure authentication-source";
             uses apply-advanced;
             leaf authentication-source-name {
               default "no-configured";
               type enumeration {
                 enum "active-directory" {
                   description "From windows active directory";
                 }
                 enum "network-access-controller" {
                   description "From network access controller such as Aruba ClearPass or JIMS";
                 }
                 enum "no-configured" {
                   description "No configuring authentication source for device entry";
                 }
               }
             }
           }
           container end-user-profile {
             description "End-user-profile configuration";
             uses apply-advanced;
             list profile-name {
               key name;
               ordered-by user;
               description "End-user-profile profile-name configuration";
               leaf name {
                 description "End-user-profile profile-name";
                 type string {
                   length "1 .. 64";
                 }
               }
               uses apply-advanced;
               leaf domain-name {
                 description "Domain name";
                 type string {
                   length "1 .. 64";
                 }
               }
               list attribute {
                 key name;
                 ordered-by user;
                 description "Attribute";
                 leaf name {
                   description "Attribute name";
                   type string;
                 }
                 uses apply-advanced;
                 choice attribute-value {
                   case case_1 {
                     leaf-list string {
                       ordered-by user;
                       description "Value type is strings";
                       type string;
                       max-elements 20;
                     }
                   }
                   case case_2 {
                     container digital {
                       presence "enable digital";
                       description "Value type is digital";
                       uses apply-advanced;
                       leaf-list value {
                         ordered-by user;
                         description "Digital value";
                         type union {
                           type uint32;
                           type string {
                             pattern "<.*>|$.*";
                           }
                         }
                       }
                       list from {
                         key name;
                         ordered-by user;
                         description "Range of digital value";
                         leaf name {
                           description "Digit range's start value";
                           type union {
                             type uint32;
                             type string {
                               pattern "<.*>|$.*";
                             }
                           }
                         }
                         uses apply-advanced;
                         leaf to {
                           description "Digit range's end value";
                           type union {
                             type uint32;
                             type string {
                               pattern "<.*>|$.*";
                             }
                           }
                         }
                       }
                     }
                   }
                 }
               }
             }
           }
           container traceoptions {
             description "Device info related Tracing Options";
             uses apply-advanced;
             leaf no-remote-trace {
               description "Disable remote tracing";
               type empty;
             }
             container file {
               description "Trace file information";
               leaf filename {
                 description "Name of file in which to write trace information";
                 type string {
                   length "1 .. 1024";
                 }
               }
               leaf size {
                 description "Maximum trace file size";
                 type string;
               }
               leaf files {
                 description "Maximum number of trace files";
                 default "3";
                 type union {
                   type string {
                     pattern "<.*>|$.*";
                   }
                   type uint32 {
                     range "2 .. 1000";
                   }
                 }
               }
               choice world-readable-choice {
                 leaf world-readable {
                   description "Allow any user to read the log file";
                   type empty;
                 }
                 leaf no-world-readable {
                   description "Don't allow any user to read the log file";
                   type empty;
                 }
               }
               leaf match {
                 description "Regular expression for lines to be logged";
                 type jt:regular-expression;
               }
             }
             leaf level {
               description "Level of debugging output";
               type enumeration {
                 enum "error" {
                   description "Match error conditions";
                 }
                 enum "warning" {
                   description "Match warning messages";
                 }
                 enum "notice" {
                   description "Match conditions that should be handled specially";
                 }
                 enum "info" {
                   description "Match informational messages";
                 }
                 enum "verbose" {
                   description "Match verbose messages";
                 }
                 enum "all" {
                   description "Match all levels";
                 }
               }
             }
             list flag {
               key name;
               ordered-by user;
               description "Tracing parameters";
               leaf name {
                 type enumeration {
                   enum "all" {
                     description "Trace device info all modules";
                   }
                   enum "auth-source" {
                     description "Trace Auth source module";
                   }
                   enum "configuration" {
                     description "Trace Device info configuration";
                   }
                   enum "device-table" {
                     description "Trace device table management module";
                   }
                   enum "ipid-all" {
                     description "Trace IPID all functions";
                   }
                   enum "ipid-db" {
                     description "Trace IPID Database function";
                   }
                   enum "ipid-entry" {
                     description "Trace IPID entry management function";
                   }
                   enum "ipid-ipc" {
                     description "Trace IPID communication processing function";
                   }
                   enum "ipid-message" {
                     description "Trace IPID message processing function";
                   }
                   enum "ipid-others" {
                     description "Trace IPID other function";
                   }
                   enum "ipid-server" {
                     description "Trace IPID server handling function";
                   }
                   enum "ipid-statistics" {
                     description "Trace IPID statistics handling function";
                   }
                   enum "ipid-task" {
                     description "Trace IPID task handling function";
                   }
                   enum "profile-lookup" {
                     description "Trace End-user-profile lookup function";
                   }
                   enum "memory" {
                     description "Trace memory";
                   }
                 }
               }
             }
           }
         }
         container identity-management {
           description "Identity management configuration";
           uses apply-advanced;
           leaf authentication-entry-timeout {
             description "Authentication entry timeout number (0, 10-1440)";
             default "60";
             units "minutes";
             type union {
               type uint16;
               type string {
                 pattern "<.*>|$.*";
               }
             }
           }
           leaf invalid-authentication-entry-timeout {
             description "Invalid authentication entry timeout number (0, 10-1440)";
             default "30";
             units "minutes";
             type union {
               type uint16;
               type string {
                 pattern "<.*>|$.*";
               }
             }
           }
           leaf preserve-valid-user {
             description "Null user will not overwrite valid user for the same ip";
             type empty;
           }
           container connection {
             description "Connection to identity management";
             uses identity-management-connection-type;
           }
           container jims-validator {
             description "Web server from JIMS for Validate or group query request";
             uses jims-validator-type;
           }
           container batch-query {
             description "Batch query parameters";
             uses batch-query-type;
           }
           container ip-query {
             description "IP query parameters";
             uses apply-advanced;
             leaf query-delay-time {
               description "Delay time to send IP query (0~60sec)";
               default "15";
               units "seconds";
               type union {
                 type string {
                   pattern "<.*>|$.*";
                 }
                 type uint8 {
                   range "0 .. 60";
                 }
               }
             }
             container no-ip-query {
               presence "enable no-ip-query";
               description "Disable IP query";
             }
             leaf max-connections {
               description "Max connection number";
               type union {
                 type string {
                   pattern "<.*>|$.*";
                 }
                 type uint32 {
                   range "1 .. 20";
                 }
               }
             }
           }
           container filter {
             description "Filter for query";
             uses apply-advanced;
             list domain {
               key name;
               ordered-by user;
               description "Domain filter";
               max-elements 20;
               leaf name {
                 description "Domain name";
                 type string {
                   length "1 .. 64";
                 }
               }
             }
             container include-ip {
               description "Include IP filter";
               uses address-filter-type;
             }
             container exclude-ip {
               description "Exclude IP filter";
               uses address-filter-type;
             }
           }
           container traceoptions {
             description "Tracing Options";
             uses ims-traceoptions-type;
           }
           container session-batch-query {
             description "Session batch query parameters";
             uses apply-advanced;
             leaf items-per-batch {
               description "Items number per batch query";
               default "200";
               type union {
                 type string {
                   pattern "<.*>|$.*";
                 }
                 type uint32 {
                   range "100 .. 1000";
                 }
               }
             }
             leaf query-interval {
               description "Query interval";
               default "5";
               units "seconds";
               type union {
                 type string {
                   pattern "<.*>|$.*";
                 }
                 type uint32 {
                   range "1 .. 60";
                 }
               }
             }
           }
           container session-query {
             description "Session query parameters";
             uses apply-advanced;
             leaf query-delay-time {
               description "Delay time to send session query (0~60sec)";
               default "15";
               units "seconds";
               type union {
                 type string {
                   pattern "<.*>|$.*";
                 }
                 type uint8 {
                   range "0 .. 60";
                 }
               }
             }
             container no-session-query {
               presence "enable no-session-query";
               description "Disable session query";
             }
             leaf max-connections {
               description "Session query configuration";
               type union {
                 type string {
                   pattern "<.*>|$.*";
                 }
                 type uint32 {
                   range "1 .. 20";
                 }
               }
             }
           }
         }
         container logical-domain-identity-management {
           description "Logical domain identity management configuration";
           uses apply-advanced;
           container active {
             description "Actve mode for logical domain identity management moudule";
             uses apply-advanced;
             leaf authentication-entry-timeout {
               description "Authentication entry timeout number (0, 10-1440)";
               default "60";
               units "minutes";
               type union {
                 type uint16;
                 type string {
                   pattern "<.*>|$.*";
                 }
               }
             }
             leaf invalid-authentication-entry-timeout {
               description "Invalid authentication entry timeout number (0, 10-1440)";
               default "30";
               units "minutes";
               type union {
                 type uint16;
                 type string {
                   pattern "<.*>|$.*";
                 }
               }
             }
             container ip-query {
               description "IP query parameters";
               uses apply-advanced;
               leaf query-delay-time {
                 description "Delay time to send IP query (0~60sec)";
                 default "15";
                 units "seconds";
                 type union {
                   type string {
                     pattern "<.*>|$.*";
                   }
                   type uint8 {
                     range "0 .. 60";
                   }
                 }
               }
             }
             container filter {
               description "Filter for query";
               uses apply-advanced;
               list domain {
                 key name;
                 ordered-by user;
                 description "Domain filter";
                 max-elements 20;
                 leaf name {
                   description "Domain name";
                   type string {
                     length "1 .. 64";
                   }
                 }
               }
               container include-ip {
                 description "Include IP filter";
                 uses address-filter-type;
               }
               container exclude-ip {
                 description "Exclude IP filter";
                 uses address-filter-type;
               }
             }
             list query-server {
               key name;
               ordered-by user;
               description "Query server";
               max-elements 1;
               leaf name {
                 description "Query server name";
                 type string {
                   length "1 .. 64";
                 }
               }
               uses apply-advanced;
               container connection {
                 description "Connection to identity management";
                 uses ims-connection-type;
               }
               container batch-query {
                 description "Batch query parameters";
                 uses batch-query-type;
               }
             }
           }
           container traceoptions {
             description "Tracing Options";
             uses ims-traceoptions-type;
           }
         }
         container captive-portal {
           description "Captive Portal configuration";
           uses apply-advanced;
           list profile {
             key name;
             ordered-by user;
             description "Captive portal profile";
             leaf name {
               description "Captive portal profile name";
               type string {
                 length "1 .. 64";
               }
             }
             uses apply-advanced;
             leaf redirect-url {
               description "Captive portal redirect url";
               type string {
                 length "1 .. 256";
               }
             }
             leaf default-profile {
               description "Enable captive portal default profile";
               type empty;
             }
           }
           container connection {
             description "Captive Portal connection";
             uses apply-advanced;
             leaf certificate-url {
               description "Captive portal certificate url";
               type string {
                 length "1 .. 256";
               }
             }
           }
         }
       }
       container ip-monitoring {
         description "IP monitoring for route action";
         uses apply-advanced;
         list policy {
           key name;
           ordered-by user;
           description "Policy for route action";
           leaf name {
             description "Policy name";
             type string {
               length "1 .. 64";
             }
           }
           uses apply-advanced;
           leaf no-preempt {
             description "No automatic failback preemption once policy failover";
             type empty;
           }
           container match {
             description "Matching probing condition";
             uses apply-advanced;
             leaf-list rpm-probe {
               ordered-by user;
               description "RPM probe name";
               type string;
             }
           }
           container then {
             description "Action to be taken";
             uses action-object-type;
           }
         }
         container traceoptions {
           description "IP-Monitoring trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "debug" {
                   description "Trace debug";
                 }
                 enum "configuration" {
                   description "Trace configuration events";
                 }
                 enum "errors" {
                   description "Trace errors";
                 }
                 enum "memory" {
                   description "Trace memory allocation or deallocation messages";
                 }
                 enum "event" {
                   description "Trace events";
                 }
                 enum "all" {
                   description "Trace events";
                 }
               }
             }
           }
         }
       }
       container wireless-wan {
         description "Wireless WAN configuration";
         uses apply-advanced;
         list adapter {
           key name;
           ordered-by user;
           description "Wireless adapter name configuration";
           leaf name {
             description "Wireless adapter name";
             type string {
               length "1 .. 16";
             }
           }
           uses apply-advanced;
           leaf ip-address {
             description "Adapter management IP address";
             type jt:ipaddr;
           }
           leaf adapter-type {
             description "Select adapter type";
             type enumeration {
               enum "cx-bridge" {
                 description "Adapter type - CX-bridge";
               }
             }
           }
           container modem {
             description "Adapter modem settings";
             uses apply-advanced;
             container usb1 {
               presence "enable usb1";
               description "Adapter USB1 modem name";
               uses apply-advanced;
               leaf description {
                 description "Text description for modem";
                 type string;
               }
             }
             container usb2 {
               presence "enable usb2";
               description "Adapter USB2 modem name";
               uses apply-advanced;
               leaf description {
                 description "Text description for modem";
                 type string;
               }
             }
             container usb3 {
               presence "enable usb3";
               description "Adapter USB3 modem name";
               uses apply-advanced;
               leaf description {
                 description "Text description for modem";
                 type string;
               }
             }
             container expresscard {
               presence "enable expresscard";
               description "Adapter Expresscard modem name";
               uses apply-advanced;
               leaf description {
                 description "Text description for modem";
                 type string;
               }
             }
           }
         }
       }
       container proxy {
         description "Proxy setting for services";
         uses apply-advanced;
         list profile {
           key name;
           ordered-by user;
           description "Proxy profile";
           uses proxy-profile-setting;
         }
       }
       container lrf {
         description "Logging and reporting service configuration";
         uses apply-advanced;
         list profile {
           key name;
           ordered-by user;
           description "One or more LRF profiles";
           max-elements 8;
           uses lrf-profile-object;
         }
       }
       container pcef {
         description "Policy and Charging Enforcement Function(PCEF) configuration";
         uses services-pcef;
       }
       container mobile-edge {
         description "Mobile edge configuration";
         uses apply-advanced;
         container gateways {
           description "Gateways";
           uses apply-advanced;
           leaf description {
             description "Description of the gateway";
             type string {
               length "1 .. 64";
             }
           }
           container resource-management {
             description "Configure resource management packet steering daemon";
             uses apply-advanced;
             container server {
               description "Configure resource management packet steering daemon";
               uses apply-advanced;
               container traceoptions {
                 description "Resource management packet steering daemon trace options";
                 uses rmpsd-traceoptions-type;
               }
             }
             container client {
               description "Configure resource management packet steering client";
               uses apply-advanced;
               container traceoptions {
                 description "Resource management packet steering client trace options";
                 uses rmps-clnt-traceoptions-type;
               }
             }
           }
           list saegw {
             key name;
             ordered-by user;
             description "SAE gateway name";
             max-elements 1;
             uses saegw-names;
           }
         }
         container pfcp {
           presence "enable pfcp";
           description "Trace options for upad pfcp";
           uses apply-advanced;
           container traceoptions {
             description "SAEGW upad pfcp trace options";
             uses pfcp-traceoptions-type;
           }
         }
         container session-manager {
           presence "enable session-manager";
           description "Trace options for upad session-manager";
           uses apply-advanced;
           container traceoptions {
             description "SAEGW upad session-manager trace options";
             uses sm-traceoptions-type;
           }
         }
         container charging-module {
           presence "enable charging-module";
           description "Trace options for upad charging-module";
           uses apply-advanced;
           container traceoptions {
             description "SAEGW upad charging-module trace options";
             uses cm-traceoptions-type;
           }
         }
       }
       container security-intelligence {
         uses apply-advanced;
         leaf url {
           description "Configure the url of feed server [https://<ip or hostname>:<port>/<uri>]";
           type string;
         }
         container authentication {
           description "Authenticate to use feed update services";
           uses apply-advanced;
           leaf auth-token {
             description "Token string for authentication";
             type string {
             }
           }
           leaf tls-profile {
             description "TLS profile";
             type string;
           }
         }
         container traceoptions {
           description "Security intelligence trace options";
           uses secintel-traceoptions;
         }
         container category {
           description "Category to be disabled";
           uses apply-advanced;
           container all {
             presence "enable all";
             description "All categories";
             uses apply-advanced;
             container disable {
               presence "enable disable";
               description "To disable all categories";
             }
           }
           list category-name {
             key name;
             ordered-by user;
             uses secintel-category-disable;
           }
         }
         leaf proxy-profile {
           description "The proxy profile name";
           type string {
             length "1 .. 64";
           }
         }
         leaf http-persist {
           description "Inspect all HTTP requests in a connection";
           type empty;
         }
         list profile {
           key name;
           ordered-by user;
           description "Configure security intelligence profile";
           uses secintel-profile-setting;
         }
         container default-policy {
           description "Configure security intelligence default policy";
           uses apply-advanced;
           list category-profiles {
             key name;
             ordered-by user;
             description "Security intelligence category profiles";
             leaf name {
               description "Name of security intelligence category";
               type enumeration {
                 enum "IPFilter" {
                   description "IPFilter";
                 }
                 enum "GeoIP" {
                   description "GeoIP";
                 }
                 enum "CC" {
                   description "Command and control";
                 }
                 enum "Infected-Hosts" {
                   description "Infected-Hosts";
                 }
                 enum "DNS" {
                   description "DNS";
                 }
               }
             }
             uses apply-advanced;
             leaf profile-name {
               description "Name of profile";
               type string;
             }
           }
         }
         list policy {
           key name;
           ordered-by user;
           description "Configure security intelligence policy";
           uses secintel-policy-setting;
         }
         container global-disable-feed {
           presence "enable global-disable-feed";
           description "Security intelligence global feed disabling setting";
           uses apply-advanced;
           list feed-name {
             key name;
             ordered-by user;
             max-elements 32;
             leaf name {
               description "Name of security intelligence global Command and control feed";
               type string {
                 length "1 .. 63";
               }
             }
             uses apply-advanced;
           }
           container all {
             presence "enable all";
             description "All of security intelligence global Command and control feed";
           }
         }
       }
       container stateful-firewall {
         description "Configure stateful firewall services";
         uses apply-advanced;
         list rule {
           key name;
           ordered-by user;
           description "Define a stateful firewall rule";
           uses sfw_rule_object;
         }
         list rule-set {
           key name;
           ordered-by user;
           description "Define a set of stateful firewall rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container ip-reassembly {
         description "Configure ip-reassembly services";
         uses apply-advanced;
         list profile {
           key name;
           description "Define a ip reassembly profile";
           uses ipr_profile_object;
         }
         list rule {
           key name;
           ordered-by user;
           description "Define a ip reassembly rule";
           uses ipr_rule_object;
         }
         list rule-set {
           key name;
           ordered-by user;
           description "Define a set of ip reassembly rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container softwire {
         description "Configure softwire services";
         uses apply-advanced;
         list ipv6-multicast-interfaces {
           key name;
           ordered-by user;
           description "Enable IPv6 multicast filter";
           leaf name {
             description "Interface name";
             type string;
           }
           uses apply-advanced;
         }
         container softwire-concentrator {
           description "Configure softwire concentrators";
           uses apply-advanced;
           list ds-lite {
             key name;
             ordered-by user;
             description "Configure DS-Lite concentrator";
             uses dslite_object;
           }
           list v6rd {
             key name;
             ordered-by user;
             description "Configure 6rd concentrator";
             uses v6rd_object;
           }
           list map-e {
             key name;
             ordered-by user;
             description "Configure MAP-E concentrator";
             uses mape_object;
           }
           list map-t {
             key name;
             ordered-by user;
             description "Configure MAP-T concentrator";
             uses mapt_object;
           }
         }
         list rule {
           key name;
           ordered-by user;
           description "Define a softwire rule";
           uses sw_rule_object;
         }
         list rule-set {
           key name;
           ordered-by user;
           description "Define a set of softwire rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container aacl {
         description "Application Aware Access List services configuration";
         uses apply-advanced;
         list rule {
           key name;
           ordered-by user;
           description "One or more AACL rules";
           uses aacl_rule_object;
         }
         list rule-set {
           key name;
           ordered-by user;
           description "Define a Set of AACL rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list aacl-dyn-rule-set {
           key name;
           ordered-by user;
           description "Define a set of AACL dynamic rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container hcm {
         description "Http Content Management services configuration";
         uses apply-advanced;
         list url-rule {
           key name;
           ordered-by user;
           description "One or more url HCM rules";
           uses hcm_url_rule_object;
         }
         list tag-rule {
           key name;
           ordered-by user;
           description "One or more  HCM tag rules";
           uses hcm_tag_rule_object;
         }
         list url-list {
           key name;
           ordered-by user;
           description "List of URL's";
           uses hcm_url_list_object;
         }
         leaf-list tag-attribute {
           ordered-by user;
           description "Tag Attributes (Subscriber Aware Attrs: imsi,msisdn,ipv4addr,imei,ipv6addr,apn,ggsnipv4,ggsnipv6)";
           type enumeration {
             enum "ipv4addr" {
             }
             enum "ipv6addr" {
             }
           }
         }
         list url-rule-set {
           key name;
           ordered-by user;
           description "Define a Set of HCM url rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list tag-rule-set {
           key name;
           ordered-by user;
           description "Define a Set of HCM tag rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list profile {
           key name;
           ordered-by user;
           description "HCM Profile Name";
           max-elements 101;
           leaf name {
             description "HCM profile name";
             type string {
               length "1 .. 63";
             }
           }
           uses apply-advanced;
           container tag-rule {
             description "Tag rule to be included in this profile";
             uses apply-advanced;
             leaf tag-rule-name {
               description "Tag Rule name";
               type string {
               }
             }
           }
         }
       }
       container cos {
         description "Class of Service services configuration";
         uses cos-object;
       }
       container pgcp {
         description "Packet Gateway Control Protocol services configuration";
         uses apply-advanced;
         container traceoptions {
           description "Trace options for packet gateway service";
           uses apply-advanced;
           container flag {
             presence "enable flag";
             description "Per-component trace options";
             uses apply-advanced;
             leaf default {
               description "Default trace level for all the components";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
             container h248-stack {
               presence "enable h248-stack";
               description "H248 stack sub-components";
               uses apply-advanced;
               leaf default {
                 description "Default trace level for the H248 stack subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf control-association {
                 description "Control association trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf media-gateway {
                 description "Media gateway trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messages {
                 description "Enable H248 dump messages";
                 type empty;
               }
             }
             container bgf-core {
               presence "enable bgf-core";
               description "BGF core sub-components";
               uses apply-advanced;
               leaf default {
                 description "Default trace level for the bgf core subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf firewall {
                 description "Firewall trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf gate-logic {
                 description "Gate trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf policy {
                 description "Policy trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf pic-broker {
                 description "PIC broker trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf statistics {
                 description "Statistics trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common  trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
             container sbc-utils {
               presence "enable sbc-utils";
               description "SBC utils sub-components";
               uses apply-advanced;
               leaf default {
                 description "Default trace level for the sbc-utils subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common utils trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf configuration {
                 description "Configuration trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf device-monitor {
                 description "Device-monitor trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf ipc {
                 description "IPC trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf memory-management {
                 description "Memory mgmt trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messaging {
                 description "Messaging trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf user-interface {
                 description "UI trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         list media-service {
           key name;
           ordered-by user;
           description "One or more PGCP media service";
           status deprecated;
           max-elements 32;
           uses pgcp_media_service_object;
         }
         list virtual-interface {
           key name;
           ordered-by user;
           description "One or more Virtual Interfaces";
           max-elements 1024;
           uses pgcp_virtual_interface_object;
         }
         list gateway {
           key name;
           ordered-by user;
           description "One or more Packet Gateways";
           max-elements 32;
           uses pgcp_gateway_object;
         }
         list rule {
           key name;
           ordered-by user;
           description "One or more PGCP rules";
           max-elements 64;
           uses pgcp_rule_object;
         }
         list rule-set {
           key name;
           ordered-by user;
           description "Define a Set of PGCP rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         container session-mirroring {
           description "Session mirroring configuration";
           presence "enable session-mirroring";
           uses pgcp_session_mirroring_object;
         }
         leaf notification-rate-limit {
           description "Max number of notifications/second sent to PGC";
           type union {
             type string {
               pattern "<.*>|$.*";
             }
             type int32 {
               range "10 .. 1000";
             }
           }
         }
       }
       container border-signaling-gateway {
         description "Border signaling service configuration";
         uses apply-advanced;
         list gateway {
           key name;
           ordered-by user;
           max-elements 4;
           uses gateway_type;
         }
       }
       container ids {
         description "Configure the intrusion detection system";
         uses apply-advanced;
         list rule {
           key name;
           ordered-by user;
           description "Define an IDS rule";
           uses ids_rule_object;
         }
         list rule-set {
           key name;
           ordered-by user;
           description "Define a set of IDS rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container nat {
         description "Configure Network Address Translation";
         uses nat-object;
       }
       container pcp {
         description "Configure Port Control Protocol";
         uses pcp-object;
       }
       container l2tp {
         presence "enable l2tp";
         description "Configure Layer 2 Tunneling Protocol service";
         uses apply-advanced;
         list tunnel-group {
           key name;
           ordered-by user;
           description "Layer 2 Tunneling Protocol profile";
           uses l2tp_tunnel_group_object;
         }
         container ip-reassembly {
           description "Configure IP Reassembly parameters";
           uses apply-advanced;
           leaf service-set {
             description "Name of IP Reassembly service set";
             type string {
               length "1 .. 63";
             }
           }
         }
         container traceoptions {
           description "Layer 2 Tunneling Protocol daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "gres" {
                   description "Trace GRES events";
                 }
                 enum "init" {
                   description "Trace daemon initialization";
                 }
                 enum "events" {
                   description "Trace interface events";
                 }
                 enum "memory" {
                   description "Trace memory management code";
                 }
                 enum "message" {
                   description "Trace message processing code";
                 }
                 enum "packet-error" {
                   description "Trace Packet error events";
                 }
                 enum "parse" {
                   description "Trace parsing events";
                 }
                 enum "receive-packets" {
                   description "Trace received L2TP packets";
                 }
                 enum "session-db" {
                   description "Trace session database interactions";
                 }
                 enum "states" {
                   description "Trace state machine events";
                 }
                 enum "timer" {
                   description "Trace timer events";
                 }
                 enum "transmit-packets" {
                   description "Trace tranmitted L2TP packets";
                 }
                 enum "routing-socket" {
                   description "Trace routing socket events";
                 }
                 enum "routing-process" {
                   description "Trace routing process interactions";
                 }
                 enum "protocol" {
                   description "Trace Layer 2 Tunneling Protocol events";
                 }
                 enum "configuration" {
                   description "Trace configuration events";
                 }
                 enum "ipc-tx" {
                   description "Trace IPC transmit events";
                 }
                 enum "ipc-rx" {
                   description "Trace IPC receive events";
                 }
                 enum "general" {
                   description "Trace general events";
                 }
                 enum "tunnel" {
                   description "Trace tunnel events";
                 }
                 enum "stats" {
                   description "Trace libstats events";
                 }
                 enum "authentication" {
                   description "Trace authentication process interactions";
                 }
                 enum "all" {
                   description "Trace everything";
                 }
               }
             }
           }
           leaf debug-level {
             description "Trace level for PPP, L2TP, RADIUS, and UDP";
             type enumeration {
               enum "error" {
                 description "Errors";
               }
               enum "detail" {
                 description "Detailed debug information";
               }
               enum "packet-dump" {
                 description "Packet decode information";
               }
             }
           }
           container filter {
             presence "enable filter";
             description "Filter to control trace messages";
             uses apply-advanced;
             list protocol {
               key name;
               ordered-by user;
               description "Additional filter for protocol";
               leaf name {
                 type enumeration {
                   enum "ppp" {
                     description "Trace Point-to-Point Protocol events";
                   }
                   enum "l2tp" {
                     description "Trace Layer 2 Tunneling Protocol events";
                   }
                   enum "radius" {
                     description "Trace RADIUS events";
                   }
                   enum "udp" {
                     description "Trace User Datagram Protocol events";
                   }
                 }
               }
             }
             leaf user-name {
               description "Additional filter by user name";
               type string {
                 length "1 .. 64";
               }
             }
             container user {
               presence "enable user";
               description "Filter by user name";
               uses apply-advanced;
               leaf username {
                 description "Name of the user to be filtered";
                 type string {
                   length "1 .. 64";
                 }
               }
             }
           }
           list interfaces {
             key name;
             ordered-by user;
             description "Layer 2 Tunneling Protocol service interface";
             uses l2tp_interface_traceoptions;
           }
         }
         leaf weighted-load-balancing {
           description "Enable weighted-load-balancing for LAC sessions";
           type empty;
         }
         leaf destination-equal-load-balancing {
           description "Enable equal load balancing of destinations";
           type empty;
         }
         leaf drain {
           description "Prevents creation of destinations, tunnels and sessions";
           type empty;
         }
         leaf failover-within-preference {
           description "Enable failover-within-preference level for LAC sessions";
           type empty;
         }
         leaf disable-calling-number-avp {
           description "Disable the calling number AVP in ICRQ packet";
           type empty;
         }
         leaf disable-failover-protocol {
           description "Disable failover protocol resync mechanism";
           status deprecated;
           type empty;
         }
         leaf rx-connect-speed-when-equal {
           description "Generate rx connect speed AVP when tx equals rx speed";
           type empty;
         }
         leaf tx-connect-speed-method {
           description "TX connect speed method";
           default "static";
           type enumeration {
             enum "none" {
               description "Disable sending tx/rx speed AVPs";
             }
             enum "static" {
               description "Use advisory speed";
             }
             enum "ancp" {
               description "Use ANCP sourced tx/rx speed";
             }
             enum "pppoe-ia-tag" {
               description "Use tx/rx speed sent in the PPPoE IA tag";
             }
             enum "service-profile" {
               description "Use tx/rx speed from service profile configuration";
             }
           }
         }
         leaf maximum-sessions {
           description "Maximum number of sessions per chassis";
           default "512000";
           type union {
             type uint32;
             type string {
               pattern "<.*>|$.*";
             }
           }
         }
         container tunnel {
           description "System wide tunnel attributes";
           uses apply-advanced;
           list name {
             key name;
             ordered-by user;
             leaf name {
               description "Locally assigned name of the tunnel(in format Destination name/Tunnel name or Tunnel name)";
               type string {
                 length "1 .. 129";
               }
             }
             list address {
               key name;
               ordered-by user;
               description "Address of the tunnel destination";
               leaf name {
                 description "Address of remote system";
                 type jt:ipv4addr;
               }
               list routing-instance {
                 key name;
                 ordered-by user;
                 description "Routing instance in which tunnel exists";
                 leaf name {
                   description "Routing instance in which tunnel exists";
                   type string {
                   }
                 }
                 leaf drain {
                   description "Prevents assignment of sessions to tunnel";
                   type empty;
                 }
               }
               leaf drain {
                 description "Prevents assignment of sessions to tunnel";
                 type empty;
               }
             }
             leaf drain {
               description "Prevents sessions assignment to tunnel";
               type empty;
             }
           }
           leaf assignment-id-format {
             description "Assignment id format";
             default "assignment-id";
             type enumeration {
               enum "assignment-id" {
                 description "Configure the format to be assignment-id only";
               }
               enum "client-server-id" {
                 description "Configure the format to be client-auth-id + server-auth-id + assignment-id";
               }
             }
           }
           leaf retransmission-count-established {
             description "Max Retransmission count for Established tunnels";
             default "7";
             type union {
               type string {
                 pattern "<.*>|$.*";
               }
               type uint16 {
                 range "2 .. 30";
               }
             }
           }
           leaf retransmission-count-not-established {
             description "Max Retransmission count for Not Established tunnels";
             default "5";
             type union {
               type string {
                 pattern "<.*>|$.*";
               }
               type uint16 {
                 range "2 .. 30";
               }
             }
           }
           leaf nas-port-method {
             description "Tunnel network access server port method";
             type enumeration {
               enum "cisco-avp" {
                 description "Limited Cisco vendor specific mechanism";
               }
             }
           }
           leaf minimum-retransmission-timeout {
             description "Min retransmission timeout for control packets in seconds (default 1)";
             default "1";
             type enumeration {
               enum "1" {
                 description "1 second";
               }
               enum "2" {
                 description "2 seconds";
               }
               enum "4" {
                 description "4 seconds";
               }
               enum "8" {
                 description "8 seconds";
               }
               enum "16" {
                 description "16 seconds";
               }
             }
           }
           leaf idle-timeout {
             description "Tunnel idle timeout value in seconds";
             default "60";
             type union {
               type string {
                 pattern "<.*>|$.*";
               }
               type uint32 {
                 range "0 .. 86400";
               }
             }
           }
           leaf rx-window-size {
             description "Tunnel Receive Window Size";
             default "4";
             type union {
               type string {
                 pattern "<.*>|$.*";
               }
               type uint16 {
                 range "4 .. 128";
               }
             }
           }
           container tx-address-change {
             presence "enable tx-address-change";
             description "Tunnel Tx Address Change";
             uses apply-advanced;
             leaf accept {
               description "Accept Tx IP Address or UDP Port Change";
               type empty;
             }
             leaf ignore {
               description "Ignore Tx IP Address or UDP Port Change";
               type empty;
             }
             leaf ignore-ip-address {
               description "Ignore Tx IP Address Change";
               type empty;
             }
             leaf ignore-udp-port {
               description "Ignore Tx UDP Port Change";
               type empty;
             }
             leaf reject {
               description "Reject Tx IP Address or UDP Port Change";
               type empty;
             }
             leaf reject-ip-address {
               description "Reject Tx IP Address Change";
               type empty;
             }
             leaf reject-udp-port {
               description "Reject Tx UDP Port Change";
               type empty;
             }
           }
           leaf maximum-sessions {
             description "Maximum number of sessions per tunnel";
             default "65535";
             type union {
               type uint32;
               type string {
                 pattern "<.*>|$.*";
               }
             }
           }
           leaf failover-resync {
             description "Tunnel Failover Resync Mechanism";
             type enumeration {
               enum "silent-failover" {
                 description "Use silent failover as failover resync mechanism";
               }
               enum "failover-protocol" {
                 description "Use L2TP failover protocol as failover resync mechanism if peer supports";
               }
             }
           }
         }
         leaf destruct-timeout {
           description "The destruct timeout in seconds";
           default "300";
           type union {
             type string {
               pattern "<.*>|$.*";
             }
             type uint16 {
               range "10 .. 3600";
             }
           }
         }
         leaf tunnel-switch-profile {
           description "Default tunnel switch profile name";
           type string {
             length "1 .. 63";
           }
         }
         container destination {
           description "System wide destination attributes";
           presence "enable destination";
           uses l2tp_destination_object;
         }
         container access-line-information {
           description "Enable system wide sending of access-line attributes";
           presence "enable access-line-information";
           uses l2tp_access_line_object;
         }
         list session-limit-group {
           key name;
           ordered-by user;
           description "Session-limit-group configuration";
           leaf name {
             description "Name of the group";
             type string {
               length "1 .. 63";
             }
           }
           uses apply-advanced;
           leaf maximum-sessions {
             description "Maximum number of sessions per tunnel-group";
             type union {
               type uint32;
               type string {
                 pattern "<.*>|$.*";
               }
             }
           }
         }
         leaf enable-ipv6-services-for-lac {
           description "Enable IPv6 services for LAC sessions";
           type empty;
         }
         leaf enable-snmp-tunnel-statistics {
           description "Enable L2TP tunnel statistics for availability via SNMP";
           type empty;
         }
       }
       container adaptive-services-pics {
         description "Adaptive Services PIC daemon configuration";
         uses apply-advanced;
         container traceoptions {
           description "Adaptive Services PIC daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "routing-socket" {
                   description "Trace routing socket events";
                 }
                 enum "routing-protocol" {
                   description "Trace routing protocol events";
                 }
                 enum "service-identification" {
                   description "Trace service-identification events";
                 }
                 enum "configuration" {
                   description "Trace configuration events";
                 }
                 enum "ipc" {
                   description "Trace IPC related events";
                 }
                 enum "kernel-object" {
                   description "Trace kernel object management";
                 }
                 enum "snmp" {
                   description "Trace SNMP operations";
                 }
                 enum "all" {
                   description "Trace everything";
                 }
               }
             }
           }
         }
       }
       container license-management {
         description "Configure license management server";
         uses apply-advanced;
         container license-server {
           presence "enable license-server";
           uses apply-advanced;
           leaf ip-address {
             description "Address of the license log server";
             type jt:ipv4addr;
           }
           leaf log-interval {
             description "Time interval to send data to Log Collector";
             default "300";
             type union {
               type string {
                 pattern "<.*>|$.*";
               }
               type uint32 {
                 range "60 .. 86400";
               }
             }
           }
           leaf-list services {
             ordered-by user;
             description "List of services that require throughput data export";
             type enumeration {
               enum "jflow" {
                 description "Jflow Service";
               }
               enum "cgnat" {
                 description "CGNAT Service";
               }
               enum "firewall" {
                 description "Firewall Service";
               }
             }
           }
         }
       }
       container rtlog {
         presence "enable rtlog";
         description "Secure log daemon options";
         uses apply-advanced;
         container traceoptions {
           description "Security log daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container soft-gre {
         presence "enable soft-gre";
         description "Soft GRE tunnel definitions";
         uses apply-advanced;
         list tunnel-group {
           key name;
           ordered-by user;
           uses soft_gre_tunnel_group_object;
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             type string {
               length "1 .. 63";
             }
           }
           uses apply-advanced;
           leaf collector {
             description "Specify a collector name";
             type string {
               length "1 .. 63";
             }
           }
           leaf-list collector-group {
             ordered-by user;
             description "Specify a collector-group name";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
           leaf session-end-reason {
             description "Session end reason";
             type enumeration {
               enum "custom-reason" {
                 description "Custom specific session end reason";
               }
               enum "default-reason" {
                 description "Default session end reason";
               }
             }
           }
         }
         container traceoptions {
           description "Trace options for JFLOW-LOG";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "configuration" {
                   description "Trace configuration events";
                 }
                 enum "flow" {
                   description "Trace flow events";
                 }
                 enum "all" {
                   description "Trace everything";
                 }
               }
             }
           }
         }
       }
       container service-device-pools {
         description "Configure service device pools";
         uses apply-advanced;
         list pool {
           key name;
           ordered-by user;
           description "Define service device pool";
           uses service_device_pool_object;
         }
       }
       container network-slicing {
         description "Configure network wide slicing parameters";
         uses apply-advanced;
         list slice {
           key name;
           description "Configure network wide slice name";
           max-elements 8000;
           leaf name {
             description "Name of the network wide slice";
             type string {
               length "1 .. 64";
             }
           }
         }
       }
       container redundancy-set {
         description "Redundancy-set settings";
         uses apply-advanced;
         container traceoptions {
           description "Services redundancy trace options";
           uses srd-traceoptions-object;
         }
         list rs-id-object {
           key name;
           ordered-by user;
           description "Definition of redundancy-set";
           uses srd-rs-id-object;
         }
       }
       container analytics {
         presence "enable analytics";
         description "Traffic analytics configuration options";
         uses apply-advanced;
         container zero-suppression {
           description "Configure suppression of zeros for GRPC sensors";
           uses apply-advanced;
           leaf no-zero-suppression {
             description "Disable zero suppression";
             type empty;
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:ipaddr;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipv4addr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf loss-priority {
             description "Packet Loss Priority for exported packets, applicable only for PFE sensors";
             type enumeration {
               enum "low" {
                 description "Marking when loss priority is low";
               }
               enum "high" {
                 description "Marking when loss priority is high";
               }
               enum "medium-low" {
                 description "Marking when loss priority is medium-low";
               }
               enum "medium-high" {
                 description "Marking when loss priority is medium-high";
               }
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-sdm" {
                 description "Use gpb self-describing-message format";
               }
               enum "gpb-gnmi" {
                 description "Use gnmi format for gpb messages";
               }
               enum "json-gnmi" {
                 description "Use gnmi format for json messages";
               }
             }
           }
           leaf transport {
             description "Telemetry export transport protocol";
             type enumeration {
               enum "udp" {
                 description "Use UDP transport protocol";
               }
               enum "grpc" {
                 description "Use grpc transport";
               }
             }
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 255";
             }
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
             max-elements 10;
           }
           leaf target-defined {
             description "Allow target to decide periodic, on-change or mix";
             type empty;
           }
           leaf life-time {
             description "Denotes sensor life-time";
             type enumeration {
               enum "long-lived" {
                 description "A long-lived subscription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                         enum "interface-queue-statistics" {
                           description "Interface Queue statistics";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "0 .. 86400";
                       }
                     }
                   }
                   leaf sensors {
                     description "Space separated list of sensor paths";
                     type string {
                       length "1 .. 2048";
                     }
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
         container traceoptions {
           description "Traffic analytics trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
             }
             leaf low {
               description "Low queue depth threshold";
               units "bytes";
               type union {
                 type string {
                   pattern "<.*>|$.*";
                 }
                 type uint32 {
                   range "1 .. 1250000000";
                 }
               }
             }
           }
           container latency-threshold {
             description "Latency threshold configuration";
             leaf high {
               description "High latency threshold";
               units "nanoseconds";
               type union {
                 type string {
                   pattern "<.*>|$.*";
                 }
                 type uint32 {
                   range "1 .. 100000000";
                 }
               }
             }
             leaf low {
               description "Low latency threshold";
               units "nanoseconds";
               type union {
                 type string {
                   pattern "<.*>|$.*";
                 }
                 type uint32 {
                   range "1 .. 100000000";
                 }
               }
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
         container traffic-statistics {
           description "Traffic statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Traffic statistics polling interval";
             units "seconds";
             type union {
               type string {
                 pattern "<.*>|$.*";
               }
               type uint32 {
                 range "1 .. 300";
               }
             }
           }
         }
         container queue-statistics {
           description "Microburst statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Queue statistics polling interval";
             units "milliseconds";
             type union {
               type string {
                 pattern "<.*>|$.*";
               }
               type uint32 {
                 range "1 .. 1000";
               }
             }
           }
         }
         container interfaces {
           description "Interface configuration options";
           status deprecated;
           uses apply-advanced;
           list interface {
             key name;
             uses interface_type;
           }
         }
         container streaming-servers {
           description "Remote streaming servers configuration options";
           status deprecated;
           uses apply-advanced;
           list address {
             key name;
             ordered-by user;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               leaf stream-format {
                 description "Streaming data format";
                 type enumeration {
                   enum "json" {
                     description "Javascript object notation";
                   }
                   enum "csv" {
                     description "Comma separated value";
                   }
                   enum "tsv" {
                     description "Tab separated value";
                   }
                 }
               }
               list stream-type {
                 key name;
                 description "Type of statistics to stream";
                 leaf name {
                   type enumeration {
                     enum "traffic-statistics" {
                       description "Enable streaming of traffic statistics";
                     }
                     enum "queue-statistics" {
                       description "Enable streaming of queue statistics";
                     }
                   }
                 }
                 uses apply-advanced;
               }
             }
           }
         }
       }
       container traffic-load-balance {
         description "Traffic load balance configuration";
         uses tdir_service_load_balance_object;
       }
       container network-monitoring {
         description "Network monitoring probe configuration";
         uses tdir_netmon_object;
       }
       container policies {
         presence "enable policies";
         uses policy-object-type;
       }
       list address-book {
         key name;
         ordered-by user;
         description "Services address book";
         max-elements 4096;
         uses named-address-book-type;
       }
       container traceoptions {
         description "Network security daemon tracing options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "configuration" {
                 description "Trace configuration events";
               }
               enum "routing-socket" {
                 description "Trace routing socket events";
               }
               enum "compilation" {
                 description "Trace compilation events";
               }
               enum "operational-command" {
                 description "Trace show or clear security commands via log file uspinfo.log";
               }
               enum "all" {
                 description "Trace everything";
               }
             }
           }
         }
         leaf rate-limit {
           description "Limit the incoming rate of trace messages";
           default "0";
           type union {
             type string {
               pattern "<.*>|$.*";
             }
             type uint32 {
               range "0 .. 4294967295";
             }
           }
         }
       }
       container web-filter {
         description "Web Filtering service configuration";
         uses apply-advanced;
         leaf multi-tenant-support {
           description "Enable multi-tenant-support";
           type empty;
         }
         container multi-tenant-hash {
           description "Multi-tenant hashed file configuration";
           uses dnsf-multitenant-hash-object;
         }
         list profile {
           key name;
           ordered-by user;
           description "Web Filter profile";
           max-elements 8;
           uses urlf-profile-object;
         }
         list ip-address-list {
           key name;
           ordered-by user;
           description "SecIntel ip address list";
           uses si-ip-address-list-object;
         }
         container traceoptions {
           description "Trace options for Web Filter ";
           uses urlf-traceoptions-object;
         }
       }
     }
   }
   grouping aacl_rule_object {
     leaf name {
       description "Rule name";
       type string {
         length "1 .. 63";
       }
     }
     uses apply-advanced;
     leaf dynamic {
       description "Make rule dynamic";
       type empty;
     }
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in AACL rule";
       leaf name {
         description "Term name";
         type string {
           length "1 .. 63";
         }
       }
       uses apply-advanced;
       container from {
         description "Match criteria";
         presence "enable from";
         uses aacl_match_object;
       }
       container then {
         description "Action to take if the 'from' condition is matched";
         uses apply-advanced;
         leaf forwarding-class {
           description "Forwarding class assigned to outgoing packets";
           type string {
           }
         }
         leaf count {
           description "Count packets by application or Application group";
           type enumeration {
             enum "none" {
               description "Do not count any application or group";
             }
             enum "application" {
               description "Count by application name";
             }
             enum "application-group" {
               description "Count by application group";
             }
             enum "application-group-any" {
               description "Count all application groups as a single total in group 'any'";
             }
             enum "nested-application" {
               description "Count by nested application name";
             }
           }
         }
         leaf log {
           description "Log session information for this application match";
           type enumeration {
             enum "none" {
               description "Do not log session information";
             }
             enum "session-start" {
               description "Log session start information for this match";
             }
             enum "session-start-end" {
               description "Log session start/end information for this match";
             }
             enum "session-start-end-no-stats" {
               description "Log session start/end information with no stats";
             }
             enum "session-start-interim-end" {
               description "Log session start/interim/end information for this match";
             }
             enum "session-interim-end" {
               description "Log session interim/end information for this match";
             }
             enum "session-end" {
               description "Log session end information for this match";
             }
           }
         }
         leaf police {
           description "Policer name";
           type string {
           }
         }
         choice designation {
           case case_1 {
             leaf accept {
               description "Accept the packet";
               type empty;
             }
           }
           case case_2 {
             leaf discard {
               description "Discard the packet";
               type empty;
             }
           }
         }
       }
     }
   }
   grouping aacl_match_object {
     uses apply-advanced;
     list source-address {
       key name;
       ordered-by user;
       description "Match IP source address";
       uses sfw_addr_object;
     }
     list destination-address {
       key name;
       ordered-by user;
       description "Match IP destination address";
       uses sfw_addr_object;
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     choice app-rule {
       case case_1 {
         leaf application-group-any {
           description "Use to wildcard or match any application group";
           type empty;
         }
       }
       case case_2 {
         leaf application-unknown {
           description "Use to specify unknown application as the match criteria.";
           type empty;
         }
       }
       case case_3 {
         leaf nested-application-unknown {
           description "Use to specify unknown nested application as the match criteria.";
           type empty;
         }
       }
       case case_4 {
         leaf-list applications {
           ordered-by user;
           description "Match one or more applications";
           type string;
         }
       }
       case case_5 {
         leaf-list nested-applications {
           ordered-by user;
           description "Match one or more nested-applications";
           type string;
         }
       }
       case case_6 {
         leaf-list application-groups {
           ordered-by user;
           description "Match one or more applications";
           type string;
         }
       }
     }
   }
   grouping aamwd-traceoptions {
     description "Advanced anti-malware trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "connection" {
             description "Trace the connection to server";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace advanced-anti-malware policy";
           }
           enum "smb" {
             description "Trace smb protocol operations";
           }
           enum "smtp" {
             description "Trace smtp protocol operations";
           }
         }
       }
     }
   }
   grouping action-object-type {
     uses apply-advanced;
     container preferred-route {
       description "Preferred route action";
       uses apply-advanced;
       leaf withdraw {
         description "Withdraw the preferred route";
         type empty;
       }
       list routing-instances {
         key name;
         ordered-by user;
         description "Routing-instance";
         leaf name {
           type string;
         }
         uses apply-advanced;
         list route {
           key name;
           ordered-by user;
           description "Route";
           leaf name {
             type jt:ipprefix;
           }
           uses apply-advanced;
           choice next_hop {
             case case_1 {
               leaf-list next-hop {
                 ordered-by user;
                 description "Next hop to destination of route-action";
                 type union {
                   type jt:ipaddr-or-interface;
                   type string {
                     pattern "<.*>|$.*";
                   }
                 }
               }
             }
             case case_2 {
               leaf discard {
                 description "Drop packets to destination; send no ICMP unreachables";
                 type empty;
               }
             }
           }
           leaf direct-next-hop {
             description "Accept only direct nexthop";
             type empty;
           }
           leaf preferred-metric {
             description "Preferred metric value assigned to route action";
             type union {
               type string {
                 pattern "<.*>|$.*";
               }
               type uint32 {
                 range "1 .. 255";
               }
             }
           }
         }
       }
       list route {
         key name;
         ordered-by user;
         description "Route";
         leaf name {
           type jt:ipprefix;
         }
         uses apply-advanced;
         choice next_hop {
           case case_1 {
             leaf-list next-hop {
               ordered-by user;
               description "Next hop to destination of route-action";
               type union {
                 type jt:ipaddr-or-interface;
                 type string {
                   pattern "<.*>|$.*";
                 }
               }
             }
           }
           case case_2 {
             leaf discard {
               description "Drop packets to destination; send no ICMP unreachables";
               type empty;
             }
           }
         }
         leaf direct-next-hop {
           description "Accept only direct nexthop";
           type empty;
         }
         leaf preferred-metric {
           description "Preferred metric value assigned to route action";
           type union {
             type string {
               pattern "<.*>|$.*";
             }
             type uint32 {
               range "1 .. 255";
             }
           }
         }
       }
     }
     list interface {
       key name;
       ordered-by user;
       description "Interface enabling/disabling action";
       leaf name {
         type union {
           type jt:interface-wildcard;
           type string {
             pattern "<.*>|$.*";
           }
         }
       }
       uses apply-advanced;
       choice action {
         case case_1 {
           leaf enable {
             description "Enable interface";
             type empty;
           }
         }
         case case_2 {
           leaf disable {
             description "Disable interface";
             type empty;
           }
         }
       }
     }
   }
   grouping address-filter-type {
     description "IP address filter";
     uses apply-advanced;
     leaf address-book {
       description "Referenced address book";
       type string;
     }
     leaf address-set {
       description "Referenced address set";
       type string {
         length "1 .. 63";
       }
     }
   }
   grouping antivirus-traceoptions {
     description "Anti-virus trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "content" {
             description "Trace the content buffer management";
           }
           enum "daemon" {
             description "Trace advanced-anti-malware daemon";
           }
           enum "http" {
             description "Trace http protocol operations";
           }
           enum "identification" {
             description "Trace file identification";
           }
           enum "imap" {
             description "Trace imap protocol operations";
           }
           enum "parser" {
             description "Trace protocol context parser";
           }
           enum "plugin" {
             description "Trace advanced-anti-malware plugin";
           }
           enum "policy" {
             description "Trace anti-virus policy";
           }
           enum "smb" {
             description "Trace smb protocol operations";
           }
           enum "smtp" {
             description "Trace smtp protocol operations";
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping batch-query-type {
     description "Batch query configuration";
     uses apply-advanced;
     leaf items-per-batch {
       description "Items number per batch query";
       default "200";
       type union {
         type string {
           pattern "<.*>|$.*";
         }
         type uint32 {
           range "100 .. 1000";
         }
       }
     }
     leaf query-interval {
       description "Query interval";
       default "5";
       units "seconds";
       type union {
         type string {
           pattern "<.*>|$.*";
         }
         type uint32 {
           range "1 .. 60";
         }
       }
     }
   }
   grouping bbefwa-trace-options-type {
     description "Trace options for fixed wireless access service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Fixed wireless access operations to include in debugging trace";
       leaf name {
         type enumeration {
           enum "configuration" {
             description "Configuration operations";
           }
           enum "cli" {
             description "Cli command operations";
           }
           enum "general" {
             description "Miscellaneous operations";
           }
           enum "statistics" {
             description "Statistics operations";
           }
           enum "tunnel" {
             description "GTP-U Tunnel operations";
           }
           enum "gateway" {
             description "Mobile management entity operations";
           }
           enum "authentication" {
             description "Mme authentication operations";
           }
           enum "infra" {
             description "Infrastructure operations";
           }
           enum "all" {
             description "All operations";
           }
         }
       }
     }
   }
   grouping bgp-logical-system {
     description "Logical systems configuration for rpm";
     leaf name {
       description "Logical system name";
       type string {
       }
     }
     uses apply-advanced;
     list routing-instances {
       key name;
       description "Routing instances";
       uses bgp-routing-instances;
     }
   }
   grouping bgp-routing-instances {
     description "Routing-instance configuration for rpm";
     leaf name {
       description "Routing instance name";
       type string;
     }
     uses apply-advanced;
   }
   grouping cm-traceoptions-type {
     description "Trace options for SAEGW charging";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "general" {
             description "Trace general events";
           }
           enum "state-machine" {
             description "Trace state-machine events";
           }
           enum "mirroring" {
             description "Trace mirroring events";
           }
           enum "all" {
             description "Trace everything";
           }
         }
       }
     }
   }
   grouping collector_destinations_type {
     leaf name {
       description "FTP destination URL (allows {text} macros)";
       type string;
     }
     uses apply-advanced;
     leaf password {
       description "Password for accessing URL";
       type jt:unreadable;
     }
   }
   grouping collector_transfer_log_archive_type {
     uses apply-advanced;
     leaf filename-prefix {
       description "Filename prefix for transfer log";
       type string {
       }
     }
     leaf maximum-age {
       description "Maximum age of transfer log file";
       default "15";
       units "minutes";
       type union {
         type string {
           pattern "<.*>|$.*";
         }
         type uint32 {
           range "1 .. 360";
         }
       }
     }
     list archive-sites {
       key name;
       ordered-by user;
       max-elements 5;
       leaf name {
         description "Primary and failover URLs to receive archive files";
         type string;
       }
       leaf password {
         description "Password to log in to the archive site";
         type jt:unreadable;
       }
     }
   }
   grouping cos-object {
     description "Class of Service services configuration";
     uses apply-advanced;
     list application-profile {
       key name;
       ordered-by user;
       description "One or more CoS application profiles";
       uses cos_application_profile_object;
     }
     list rule {
       key name;
       ordered-by user;
       description "One or more CoS rules";
       uses cos_rule_object;
     }
     list rule-set {
       key name;
       ordered-by user;
       description "Define a Set of CoS rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping cos_application_profile_object {
     leaf name {
       description "Profile name";
       type string {
         length "1 .. 63";
       }
     }
     uses apply-advanced;
     container sip {
       presence "enable sip";
       description "CoS treatment of Session Initiation Protocol data";
       uses apply-advanced;
       container voice {
         presence "enable voice";
         description "CoS treatment of SIP voice data";
         uses apply-advanced;
         leaf dscp {
           description "Code point alias or bit string";
           type string {
           }
         }
         leaf forwarding-class {
           description "Forwarding class assigned to outgoing packets";
           type string {
           }
         }
       }
       container video {
         presence "enable video";
         description "CoS treatment of SIP video data";
         uses apply-advanced;
         leaf dscp {
           description "Code point alias or bit string";
           type string {
           }
         }
         leaf forwarding-class {
           description "Forwarding class assigned to outgoing packets";
           type string {
           }
         }
       }
     }
     container ftp {
       presence "enable ftp";
       description "CoS treatment for FTP data";
       uses apply-advanced;
       container data {
         presence "enable data";
         uses apply-advanced;
         leaf dscp {
           description "Code point alias or bit string";
           type string {
           }
         }
         leaf forwarding-class {
           description "Forwarding class assigned to outgoing packets";
           type string {
           }
         }
       }
     }
   }
   grouping cos_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in CoS rule";
       leaf name {
         description "Term name";
         type string {
           length "1 .. 63";
         }
       }
       uses apply-advanced;
       container from {
         description "Match criteria";
         uses sfw_match_object;
       }
       container then {
         description "Action to take if the 'from' condition is matched";
         uses apply-advanced;
         leaf dscp {
           description "Code point alias or bit string";
           type string {
           }
         }
         leaf forwarding-class {
           description "Forwarding class assigned to outgoing packets";
           type string {
           }
         }
         leaf application-profile {
           description "CoS application profile";
           type string {
           }
         }
         leaf syslog {
           description "System log information about the packet";
           type empty;
         }
         choice designation {
           case case_1 {
             leaf reflexive {
               description "Apply mirror rule to reverse traffic";
               type empty;
             }
           }
           case case_2 {
             leaf revert {
               description "Apply received COS values to reverse traffic";
               type empty;
             }
           }
           case case_3 {
             container reverse {
               presence "enable reverse";
               description "CoS treatment for reverse traffic";
               uses apply-advanced;
               leaf dscp {
                 description "Code point alias or bit string";
                 type string {
                 }
               }
               leaf forwarding-class {
                 description "Forwarding class assigned to outgoing packets";
                 type string {
                 }
               }
               leaf application-profile {
                 description "CoS application profile";
                 type string {
                 }
               }
               leaf syslog {
                 description "System log information about the packet";
                 type empty;
               }
             }
           }
         }
       }
     }
     list policy {
       key name;
       ordered-by user;
       description "One or more policies in CoS rule";
       leaf name {
         description "Policy name";
         type string {
           length "1 .. 63";
         }
       }
       uses apply-advanced;
       container match {
         description "Match criteria";
         uses sfw_match_object;
       }
       container then {
         description "Action to take if the 'from' condition is matched";
         uses apply-advanced;
         leaf dscp {
           description "Code point alias or bit string";
           type string {
           }
         }
         leaf forwarding-class {
           description "Forwarding class assigned to outgoing packets";
           type string {
           }
         }
         leaf application-profile {
           description "CoS application profile";
           type string {
           }
         }
         choice designation {
           case case_1 {
             leaf reflexive {
               description "Apply mirror rule to reverse traffic";
               type empty;
             }
           }
           case case_2 {
             leaf revert {
               description "Apply received COS values to reverse traffic";
               type empty;
             }
           }
           case case_3 {
             container reverse {
               presence "enable reverse";
               description "CoS treatment for reverse traffic";
               uses apply-advanced;
               leaf dscp {
                 description "Code point alias or bit string";
                 type string {
                 }
               }
               leaf forwarding-class {
                 description "Forwarding class assigned to outgoing packets";
                 type string {
                 }
               }
               leaf application-profile {
                 description "CoS application profile";
                 type string {
                 }
               }
             }
           }
         }
       }
     }
   }
   grouping cpcd-rule-object-type {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a captive portal content delivery term";
       leaf name {
         description "Term name";
         type string {
           length "1 .. 63";
         }
       }
       uses apply-advanced;
       container from {
         description "Define match criteria";
         uses cpcd-match-object-type;
       }
       container then {
         description "Action to take if the 'from' condition is matched";
         uses cpcd-action-object-type;
       }
     }
   }
   grouping cpcd-action-object-type {
     uses apply-advanced;
     choice designation {
       case case_1 {
         leaf accept {
           description "Accept the packet";
           type empty;
         }
       }
       case case_2 {
         container rewrite {
           presence "enable rewrite";
           description "Rewrite the IP-DA of the packet";
           uses apply-advanced;
           leaf destination-address {
             description "The destination IP address";
             type jt:ipaddr;
           }
           leaf destination-port {
             description "The destination port";
             type union {
               type string {
                 pattern "<.*>|$.*";
               }
               type uint16 {
                 range "1 .. 65535";
               }
             }
           }
         }
       }
       case case_3 {
         container redirect {
           presence "enable redirect";
           description "Redirect the http packet";
           leaf url {
             description "URL of the captive portal file";
             type string {
             }
           }
         }
       }
       case case_4 {
         container insert {
           description "Insert tag into the http packet";
           uses apply-advanced;
           list tag {
             key name;
             ordered-by user;
             description "Tag name to be inserted";
             leaf name {
               description "Tag name";
               type string {
                 length "1 .. 127";
               }
             }
             uses apply-advanced;
             leaf tag-value {
               description "Tag value to be inserted";
               type string;
             }
           }
         }
       }
     }
     leaf syslog {
       description "System log information about the packet";
       type empty;
     }
   }
   grouping cpcd-match-object-type {
     uses apply-advanced;
     list destination-address {
       key name;
       ordered-by user;
       description "Match IP destination address";
       leaf name {
         description "Match IP address";
         type string;
       }
       leaf except {
         description "Match address not in this prefix";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     list applications {
       key name;
       ordered-by user;
       description "Match one or more applications";
       leaf name {
         type string {
           length "1 .. 63";
         }
       }
       uses apply-advanced;
       leaf application-protocol {
         description "Application protocol type";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf protocol {
         description "Match IP protocol type";
         type string;
       }
       leaf source-port {
         description "Match TCP/UDP source port";
         type string;
       }
       leaf destination-port {
         description "Match TCP/UDP destination port";
         type string;
       }
     }
   }
   grouping cpcd-trace-options-type {
     description "Trace options for captive portal and content delivery service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Captive portal operations to include in debugging trace";
       leaf name {
         type enumeration {
           enum "configuration" {
             description "Configuration operations";
           }
           enum "clicommand" {
             description "Cli command operations";
           }
           enum "general" {
             description "Miscellaneous operations";
           }
           enum "rtsock" {
             description "Routing socket operations";
           }
           enum "statistics" {
             description "Statistics operations";
           }
           enum "rules" {
             description "Rules operations";
           }
           enum "ssets" {
             description "Service sets operations";
           }
           enum "ipc" {
             description "RE-PIC operations";
           }
           enum "gres" {
             description "GRES operations";
           }
           enum "re-services" {
             description "RE Service Operations";
           }
           enum "re-svc-debug-stat" {
             description "RE Service debug stats";
           }
           enum "all" {
             description "All operations";
           }
         }
       }
     }
   }
   grouping dfc_group_type {
     description "Configure DFC group parameters";
     leaf name {
       description "DFC group name";
       type string {
         length "1 .. 64";
       }
     }
     uses apply-advanced;
     leaf-list interfaces {
       ordered-by user;
       description "DFC PIC(s) in this group";
       type union {
         type jt:interface-device;
         type string {
           pattern "<.*>|$.*";
         }
       }
       max-elements 1;
     }
     leaf input-packet-rate-threshold {
       description " Input pps (max 300k on MO-III, 1M on MS-400)";
       default "1024000";
       units "pps";
       type string;
     }
     leaf max-duplicates {
       description "Maximum content destinations for the capture group";
       type union {
         type string {
           pattern "<.*>|$.*";
         }
         type uint32 {
           range "1 .. 64";
         }
       }
     }
     leaf duplicates-dropped-periodicity {
       description "Periodicity of DuplicatesDropped notification in secs";
       type union {
         type string {
           pattern "<.*>|$.*";
         }
         type uint32 {
           range "1 .. 255";
         }
       }
     }
     container pic-memory-threshold {
       description "PIC memory threshold";
       leaf percentage {
         description "Threshold in percentage";
         units "percent";
         type union {
           type string {
             pattern "<.*>|$.*";
           }
           type uint32 {
             range "10 .. 100";
           }
         }
       }
     }
     list control-source {
       key name;
       ordered-by user;
       description "Configure control source parameters";
       max-elements 64;
       uses dfc_control_source_type;
     }
     list content-destination {
       key name;
       ordered-by user;
       description "Configure content destination parameters";
       max-elements 64;
       uses content_destination_type;
     }
   }
   grouping content_destination_type {
     leaf name {
       description "Content destination identifier";
       type string {
         length "1 .. 48";
       }
     }
     uses apply-advanced;
     leaf address {
       description "Content destination IP address";
       type jt:ipv4addr;
     }
     leaf ttl {
       description "Time to live";
       default "255";
       type union {
         type string {
           pattern "<.*>|$.*";
         }
         type uint32 {
           range "1 .. 255";
         }
       }
     }
     leaf soft-limit-clear {
       description "Soft limit clear threshold";
       units "bps";
       type string;
     }
     leaf soft-limit {
       description "Soft limit threshold";
       units "bps";
       type string;
     }
     leaf hard-limit-target {
       description "Hard limit target threshold";
       units "bps";
       type string;
     }
     leaf hard-limit {
       description "Hard limit threshold";
       units "bps";
       type string;
     }
   }
   grouping dfc_control_source_type {
     leaf name {
       description "Control source identifier";
       type string {
         length "1 .. 48";
       }
     }
     uses apply-advanced;
     leaf-list source-addresses {
       ordered-by user;
       description "Allowed control source IP address list";
       type jt:ipv4addr;
       max-elements 8;
     }
     leaf service-port {
       description "Service port";
       type union {
         type uint16;
         type string {
           pattern "<.*>|$.*";
         }
       }
     }
     list notification-targets {
       key name;
       description "Notification target list";
       max-elements 8;
       uses dfc_notification_target_type;
     }
     leaf no-syslog {
       description "Disable syslog";
       type empty;
     }
     leaf shared-key {
       description "Shared key with control source";
       type string {
         length "1 .. 20";
       }
     }
     leaf-list allowed-destinations {
       ordered-by user;
       description "Allowed destinations";
       type string {
         length "1 .. 48";
       }
       max-elements 16;
     }
     leaf minimum-priority {
       description "Minimum priority of the control source";
       default "0";
       type union {
         type string {
           pattern "<.*>|$.*";
         }
         type uint32 {
           range "0 .. 255";
         }
       }
     }
   }
   grouping dfc_notification_target_type {
     leaf name {
       description "Notification target IP address";
       type jt:ipv4addr;
     }
     uses apply-advanced;
     leaf port {
       description "Notification target port";
       type union {
         type uint16;
         type string {
           pattern "<.*>|$.*";
         }
       }
     }
   }
   grouping dnsf-multitenant-hash-object {
     uses apply-advanced;
     container file-hash-key {
       description "Define web-filter global file key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
     }
   }
   grouping drop-policy-term {
     description "One or more drop terms";
     leaf name {
       description "Term name";
       type string {
       }
     }
     uses apply-advanced;
     container from {
       description "Define match criteria";
       uses apply-advanced;
       container source-address {
         description "Source IP Address";
         presence "enable source-address";
         uses li_policy_addr_simple_object;
       }
       container destination-address {
         description "Destination IP Address";
         presence "enable destination-address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
       }
     }
     uses apply-advanced;
     container from {
       description "Define match criteria";
       uses apply-advanced;
       container source-address {
         description "Source IPv6 Address or Prefix";
         presence "enable source-address";
         uses li_policy_addr6_simple_object;
       }
       container destination-address {
         description "Destination IPv6 Address or Prefix";
         presence "enable destination-address";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping dslite_object {
     leaf name {
       description "DS-Lite concentrator name";
       type string {
         length "1 .. 63";
       }
     }
     uses apply-advanced;
     leaf softwire-address {
       description "Softwire concentrator address";
       type jt:ipv6addr;
     }
     leaf mtu-v6 {
       description "MTU for the softwire tunnel";
       type union {
         type string {
           pattern "<.*>|$.*";
         }
         type uint32 {
           range "1280 .. 9192";
         }
       }
     }
     leaf copy-dscp {
       description "Copy DSCP (type of service) from IPv6 to IPv4 header";
       type empty;
     }
     leaf auto-update-mtu {
       description "Auto update MTU from received ICMPv6 messages";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       type union {
         type string {
           pattern "<.*>|$.*";
         }
         type uint32 {
           range "0 .. 16384";
         }
       }
     }
   }
   grouping dyn-filterd-traceoptions {
     description "Dynamic Filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "config" {
             description "Trace config handling events";
           }
           enum "connection" {
             description "Trace the connection to server";
           }
           enum "daemon" {
             description "Trace generic daemon handling events";
           }
           enum "filters" {
             description "Trace filter related events";
           }
           enum "pki" {
             description "Trace Public Key Encryption events";
           }
           enum "policy" {
             description "Trace policy events from RE to PFE";
           }
         }
       }
     }
   }
   grouping explicit-config {
     uses apply-advanced;
     list profile {
       key name;
       ordered-by user;
       description "Configure explicit proxy profile";
       leaf name {
         description "Explicit proxy profile name";
         type string {
           length "1 .. 63";
         }
       }
       uses apply-advanced;
       leaf-list listening-port {
         description "Listening ports for explicit proxy traffic";
         type union {
           type string {
             pattern "<.*>|$.*";
           }
           type uint16 {
             range "1025 .. 65535";
           }
         }
       }
       leaf preferred-egress-source-ip {
         description "Specify preferred egress source IP";
         default "default-egress-ip";
         type enumeration {
           enum "default-egress-ip" {
             description "Egress source IP will be the IP address associated with outgoing interface";
           }
           enum "explicit-proxy-ip" {
             description "Egress source IP will be the explicit proxy IP address on which the proxy request was made";
           }
         }
       }
       leaf proxy-mode {
         description "Supported modes for explict proxy";
         default "hop-by-hop";
         type enumeration {
           enum "hop-by-hop" {
             description "Modify hop-by-hop headers";
           }
           enum "opaque" {
             description "Relay messages directly without altering any content";
           }
         }
       }
       container ssl-proxy {
         presence "enable ssl-proxy";
         description "SSL Proxy profile";
         uses apply-advanced;
         leaf profile-name {
           description "Specify SSL proxy service profile name";
           type string;
         }
       }
       container captive-portal {
         presence "enable captive-portal";
         description "Authentication captive portal profile";
         uses apply-advanced;
         leaf profile-name {
           description "Specify Captive portal service profile name";
           type string;
         }
       }
       container add-forwarded-header {
         description "Adds the forwarded header in the request messages";
         uses apply-advanced;
         leaf obfuscated-forwarded-for-info {
           description "Adds the forwarded header with obfuscated identifiers for client information";
           type string {
             length "1 .. 63";
           }
         }
         leaf obfuscated-forwarded-by-info {
           description "Adds the forwarded header with obfuscated identifiers for proxy information";
           type string {
             length "1 .. 63";
           }
         }
         leaf add-client-ipaddr-in-forwarded-for-info {
           description "Adds the IP address of the client in the forwarded header";
           type empty;
         }
         leaf add-proxy-ipaddr-in-forwarded-by-info {
           description "Adds the explicit proxy IP address in the forwarded header";
           type empty;
         }
         leaf add-forwarded-proto-info {
           description "Adds the http protocol information in the forwarded header";
           type empty;
         }
       }
       container security-metadata-streaming-policy {
         description "Specify security-metadata-streaming-policy";
         uses apply-advanced;
         leaf policy-name {
           type string {
             length "1 .. 63";
           }
         }
       }
       leaf session-rate-limiter {
         description "Number of sessions per second";
         default "2500";
         type union {
           type string {
             pattern "<.*>|$.*";
           }
           type uint32 {
             range "1 .. 32000";
           }
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping file_specification_type {
     leaf name {
       description "Name for file type";
       type string;
     }
     uses apply-advanced;
     leaf name-format {
       description "Format string for filename (allows {text} macros)";
       type string;
     }
     leaf data-format {
       description "Data format for flow collection output";
       type enumeration {
         enum "flow-compressed" {
           description "Flow format (compressed)";
         }
       }
     }
     container transfer {
       leaf timeout {
         description "Timeout in seconds when the file is transferred";
         default "600";
         type union {
           type string {
             pattern "<.*>|$.*";
           }
           type uint32 {
             range "60 .. 1800";
           }
         }
       }
       leaf record-level {
         description "Number of records at which the file is transferred";
         default "500000";
         type union {
           type string {
             pattern "<.*>|$.*";
           }
           type uint32 {
             range "10000 .. 1000000";
           }
         }
       }
     }
   }
   grouping fiveqi {
     leaf name {
       description "5QI number";
       type union {
         type string {
           pattern "<.*>|$.*";
         }
         type uint32 {
           range "0 .. 63";
         }
       }
     }
     uses apply-advanced;
     container upstream-rewrite {
       description "AGF Upstream QOS attribute - rewrite";
       uses apply-advanced;
       leaf forwarding-class {
         description "Name of forwarding class";
         type string {
           length "1 .. 64";
         }
       }
       leaf loss-priority {
         description "Loss priority (low/high)";
         type enumeration {
           enum "low" {
             description "Code points to classify to loss priority low";
           }
           enum "high" {
             description "Code points to classify to loss priority high";
           }
         }
       }
       leaf dscp {
         type union {
           type string {
             pattern "<.*>|$.*";
           }
           type uint32 {
             range "0 .. 63";
           }
         }
       }
       leaf dscp-n3 {
         type union {
           type string {
             pattern "<.*>|$.*";
           }
           type uint32 {
             range "0 .. 63";
           }
         }
       }
     }
   }
   grouping flow-traceoptions-object {
     description "Trace options for flow services";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Events and other information to include in trace output";
       leaf name {
         type enumeration {
           enum "all" {
             description "All events";
           }
           enum "basic-datapath" {
             description "Basic packet flow";
           }
           enum "high-availability" {
             description "Flow high-availability information";
           }
           enum "host-traffic" {
             description "Flow host-traffic information";
           }
           enum "fragmentation" {
             description "Ip fragmentation and reassembly events";
           }
           enum "multicast" {
             description "Multicast flow information";
           }
           enum "route" {
             description "Route lookup information";
           }
           enum "session" {
             description "Session creation and deletion events";
           }
           enum "session-scan" {
             description "Session scan information";
           }
           enum "tcp-basic" {
             description "TCP packet flow";
           }
           enum "tunnel" {
             description "Tunnel information";
           }
           enum "jexec" {
             description "Junos forwarding module";
           }
         }
       }
     }
     leaf rate-limit {
       description "Limit the incoming rate of trace messages";
       default "0";
       type union {
         type string {
           pattern "<.*>|$.*";
         }
         type uint32 {
           range "0 .. 4294967295";
         }
       }
     }
     list packet-filter {
       key name;
       ordered-by user;
       description "Flow packet debug filters";
       max-elements 64;
       uses flow-filter-type;
     }
     container trace-level {
       description "FLow trace level";
       uses apply-advanced;
       choice level {
         case case_1 {
           leaf minimal {
             description "Significant messages including warning, error, criticality, alert and emergency.";
             type empty;
           }
         }
         case case_2 {
           leaf brief {
             description "Brief messages including notice, in addition to minimal messages";
             type empty;
           }
         }
         case case_3 {
           leaf detail {
             description "Detail messages including info and debug, in addition to brief messages";
             type empty;
           }
         }
       }
     }
     leaf root-override {
       description "Allow collect flow trace in root from all logical-systems and tenants";
       type empty;
     }
   }
   grouping flow-filter-type {
     description "Flow filter settings";
     leaf name {
       description "Name of the filter";
       type string {
         length "1 .. 63";
       }
     }
     uses apply-advanced;
     leaf protocol {
       description "Match IP protocol type";
       type string;
     }
     leaf source-prefix {
       description "Source IP address prefix";
       type jt:ipprefix;
     }
     leaf destination-prefix {
       description "Destination IP address prefix";
       type jt:ipprefix;
     }
     leaf conn-tag {
       description "Session connection tag";
       type union {
         type string {
           pattern "<.*>|$.*";
         }
         type uint32 {
           range "0 .. 4294967295";
         }
       }
     }
     leaf logical-system {
       description "Logical system";
       status deprecated;
       type string {
         length "1 .. 63";
       }
     }
     leaf source-port {
       description "Match TCP/UDP source port";
       type string;
     }
     leaf destination-port {
       description "Match TCP/UDP destination port";
       type string;
     }
     leaf interface {
       description "Source logical interface";
       type union {
         type jt:interface-name;
         type string {
           pattern "<.*>|$.*";
         }
       }
     }
   }
   grouping fwa-authentication-type {
     description "FWA authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf imsi {
         description "Include IMSI";
         type empty;
       }
       leaf msisdn {
         description "Include MSISDN";
         type empty;
       }
       leaf mei {
         description "Include MEI";
         type empty;
       }
     }
   }
   grouping gateway_type {
     leaf name {
       description "Gateway name";
       type string;
     }
     uses apply-advanced;
     leaf service-interface {
       description "Associated services interface";
       type union {
         type jt:interface-device;
         type string {
           pattern "<.*>|$.*";
         }
       }
     }
     container sip {
       presence "enable sip";
       uses apply-advanced;
       container timers {
         description "Timers configuration";
         presence "enable timers";
         uses sip_timers_type;
       }
       list new-transaction-policy {
         key name;
         ordered-by user;
         description "Definition of a new-transaction policy";
         max-elements 500;
         uses transaction_policy_type;
       }
       list new-transaction-policy-set {
         key name;
         ordered-by user;
         description "Definition of a new-transaction policy set";
         max-elements 5;
         uses new_transaction_set_type;
       }
       list new-registration-policy {
         key name;
         ordered-by user;
         description "Definition of a new-registration policy";
         max-elements 500;
         uses registration_policy_type;
       }
       list new-registration-policy-set {
         key name;
         ordered-by user;
         description "Definition of a new-registration policy set";
         max-elements 5;
         uses new_registration_set_type;
       }
       list new-call-usage-policy {
         key name;
         ordered-by user;
         description "Definition of a new-call usage policy";
         max-elements 500;
         uses call_usage_policy_type;
       }
       list new-call-usage-policy-set {
         key name;
         ordered-by user;
         description "Definition of a new-call usage policy set";
         max-elements 5;
         uses new_call_usage_set_type;
       }
       container routing-destinations {
         description "Definition of routing destinations";
         presence "enable routing-destinations";
         uses routing-destinations;
       }
       container message-manipulation-rules {
         description "Definition of manipulation rules";
         uses header-manipulation-message-manipulation-rules-type;
       }
       leaf local-tag-prefix {
         description "Local tag prefix";
         default "bsg";
         type string;
       }
       list signaling-realms {
         key name;
         ordered-by user;
         description "Signaling realm";
         uses signaling-realm;
       }
       leaf local-uri-prefix {
         description "Local URI prefix";
         default "J";
         type string;
       }
     }
     list admission-control {
       key name;
       ordered-by user;
       description "Definition of an admission controller";
       max-elements 10;
       uses admission-control-type;
     }
     list service-point {
       key name;
       ordered-by user;
       max-elements 100;
       uses service_point_type;
     }
     container name-resolution-cache {
       presence "enable name-resolution-cache";
       uses name-resolution-cache-type;
     }
     container embedded-spdf {
       presence "enable embedded-spdf";
       uses apply-advanced;
       list service-class {
         key name;
         ordered-by user;
         description "Definition of service class policies";
         max-elements 5;
         leaf name {
           description "Service class name";
           type string {
             length "1 .. 63";
           }
         }
         uses apply-advanced;
         list term {
           key name;
           ordered-by user;
           description "Service class settings by media type";
           max-elements 6;
           leaf name {
             description "Term name";
             type string;
           }
           uses apply-advanced;
           container from {
             presence "enable from";
             description "The media-related filter that the rate limiting and DSCP marking are based on";
             uses apply-advanced;
             leaf-list media-type {
               ordered-by user;
               description "Media types to filter on";
               type enumeration {
                 enum "any-media" {
                 }
                 enum "audio" {
                 }
                 enum "video" {
                 }
               }
             }
           }
           container then {
             presence "enable then";
             description "The action to take based on the 'from' filter";
             uses apply-advanced;
             leaf reject {
               description "Reject the request";
               type empty;
             }
             leaf committed-information-rate {
               description "Committed information rate value per stream";
               default "0x7FFFFFFF";
               units "bytes-per-second";
               type union {
                 type string {
                   pattern "<.*>|$.*";
                 }
                 type uint32 {
                   range "0 .. 2147483647";
                 }
               }
             }
             leaf committed-burst-size {
               description "Committed burst size value per stream";
               default "0x7FFFFFFF";
               units "bytes";
               type union {
                 type string {
                   pattern "<.*>|$.*";
                 }
                 type uint32 {
                   range "20 .. 2147483647";
                 }
               }
             }
             leaf dscp {
               description "Code point alias or 6-bit pattern";
               default "be";
               type string {
               }
             }
           }
         }
       }
     }
     container traceoptions {
       description "Trace options for border signaling gateway";
       uses apply-advanced;
       container flag {
         presence "enable flag";
         description "Per-component trace options";
         uses apply-advanced;
         leaf minimum {
           description "Minimum trace level for all the components";
           default "error";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         leaf session-trace {
           description "Trace level for the session tracing component";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         container sip-stack {
           presence "enable sip-stack";
           description "Sip stack trace level options";
           uses apply-advanced;
           leaf event-tracing {
             description "Event tracing";
             type empty;
           }
           leaf ips-tracing {
             description "IPS tracing";
             type empty;
           }
           leaf per-tracing {
             description "Performance tracing";
             type empty;
           }
           leaf dev-logging {
             description "Development tracing";
             type empty;
           }
           leaf verbose-logging {
             description "Verbose tracing";
             type empty;
           }
           leaf pd-log-level {
             description "Set pd trace level";
             type enumeration {
               enum "problem" {
                 description "Record a problem";
               }
               enum "exception" {
                 description "Record and exception that has been encountered in the code";
               }
               enum "audit" {
                 description "Record ordinary events for accounting purposes";
               }
             }
           }
           leaf pd-log-detail {
             description "Set detail level for DC logs";
             type enumeration {
               enum "full" {
                 description "Full details for every entry";
               }
               enum "summary" {
                 description "Summary details for every entry";
               }
             }
           }
         }
         container signaling {
           presence "enable signaling";
           description "Signaling component sub-components";
           uses apply-advanced;
           leaf minimum {
             description "Minimum trace level for the signaling subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf sip-stack-wrapper {
             description "Sip stack wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b-wrapper {
             description "B2B wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ua {
             description "UA trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b {
             description "B2B trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf topology-hiding {
             description "Topology hiding trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf policy {
             description "Policy trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf name-resolution-cache {
             description "Name resolution cache trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf accounting-trigger {
             description "Accounting trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event-trigger {
             description "Event trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Packet capture trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container framework {
           presence "enable framework";
           description "Framework component sub-components";
           uses apply-advanced;
           leaf minimum {
             description "Minimum trace level for the framework subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf executor {
             description "Executor trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf action {
             description "Action trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event {
             description "Event trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf freezer {
             description "Freezer trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory pool trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container datastore {
           presence "enable datastore";
           description "Datastore component sub-components";
           uses apply-advanced;
           leaf minimum {
             description "Minimum trace level for the datastore subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf data {
             description "Data trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf handle {
             description "Handle trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf db {
             description "DB trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container sbc-utils {
           presence "enable sbc-utils";
           description "SBC utils component sub-components";
           uses apply-advanced;
           leaf minimum {
             description "Minimum trace level for the sbc-utils subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf configuration {
             description "Configuration trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ipc {
             description "IPC trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf device-monitor {
             description "Device-monitor trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-management {
             description "Memory mgmt trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf message {
             description "Messaging trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf common {
             description "Common utils trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf user-interface {
             description "User-interface trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory-pool trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Trace packet capture events";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
       }
       container file {
         description "Trace file information";
         status deprecated;
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
     }
   }
   grouping admission-control-type {
     leaf name {
       description "Admission control profile name";
       type string;
     }
     uses apply-advanced;
     container dialogs {
       presence "enable dialogs";
       description "Dialog admission control rules";
       uses apply-advanced;
       leaf maximum-concurrent {
         description "Maximum concurrent dialogs allowed";
         type union {
           type string {
             pattern "<.*>|$.*";
           }
           type uint32 {
             range "0 .. 100000";
           }
         }
       }
       leaf committed-attempts-rate {
         description "Committed rate of dialog admission attempts";
         type union {
           type string {
             pattern "<.*>|$.*";
           }
           type uint32 {
             range "0 .. 500";
           }
         }
       }
       leaf committed-burst-size {
         description "Committed burst size of dialog admission attempts";
         type union {
           type string {
             pattern "<.*>|$.*";
           }
           type uint32 {
             range "0 .. 1000";
           }
         }
       }
     }
     container transactions {
       presence "enable transactions";
       description "Transaction admission control rules";
       uses apply-advanced;
       leaf maximum-concurrent {
         description "Maximum concurrent transactions allowed";
         type union {
           type string {
             pattern "<.*>|$.*";
           }
           type uint32 {
             range "0 .. 50000";
           }
         }
       }
       leaf committed-attempts-rate {
         description "Committed rate of transaction admission attempts";
         type union {
           type string {
             pattern "<.*>|$.*";
           }
           type uint32 {
             range "0 .. 1500";
           }
         }
       }
       leaf committed-burst-size {
         description "Committed burst size of transaction admission attempts";
         type union {
           type string {
             pattern "<.*>|$.*";
           }
           type uint32 {
             range "0 .. 3000";
           }
         }
       }
     }
   }
   grouping call_usage_policy_type {
     leaf name {
       description "Policy name";
       type string;
     }
     uses apply-advanced;
     list term {
       key name;
       ordered-by user;
       description "Term definition";
       max-elements 20;
       leaf name {
         description "Term name";
         type string;
       }
       uses apply-advanced;
       container from {
         presence "enable from";
         uses apply-advanced;
         leaf-list source-address {
           ordered-by user;
           description "Source addresses and masks";
           type jt:ipaddr;
           max-elements 5;
         }
         list method {
           key name;
           ordered-by user;
           description "Methods";
           uses call-usage-method-type;
         }
         container request-uri {
           presence "enable request-uri";
           description "Request URI field";
           uses apply-advanced;
           leaf-list regular-expression {
             ordered-by user;
             description "Regular expression matched on incoming Request-URI";
             type jt:regular-expression;
             max-elements 5;
           }
         }
         container contact {
           presence "enable contact";
           description "Contact field";
           uses apply-advanced;
           leaf-list regular-expression {
             ordered-by user;
             description "Regular expression matched on incoming contact";
             type jt:regular-expression;
             max-elements 5;
           }
         }
       }
       container then {
         description "Action";
         presence "enable then";
         uses new_call_then_type;
       }
     }
   }
   grouping call-usage-method-type {
     leaf name {
       type enumeration {
         enum "method-invite" {
         }
       }
     }
     uses apply-advanced;
   }
   grouping hcm_tag_rule_object {
     leaf name {
       description "Rule name";
       type string {
         length "1 .. 63";
       }
     }
     uses apply-advanced;
     list term {
       key name;
       ordered-by user;
       description "One or more terms in HCM tag rule";
       leaf name {
         description "Term name";
         type union {
           type string {
             pattern "<.*>|$.*";
           }
           type uint16 {
             range "1 .. 32767";
           }
         }
       }
       uses apply-advanced;
       container from {
         description "Match criteria";
         presence "enable from";
         uses hcm_tag_match_object;
       }
       container then {
         description "Action to take if the 'from' condition is matched";
         uses apply-advanced;
         list tag {
           key name;
           ordered-by user;
           description "One or more terms in HCM tag rule";
           leaf name {
             description "Tag name";
             type string {
               length "1 .. 63";
             }
           }
           uses apply-advanced;
           leaf tag-header {
             description "Tag header string";
             type string {
               length "1 .. 63";
             }
           }
           leaf do-not-rename-existing-tag-header {
             description "Disable renaming of the tag header";
             type empty;
           }
           leaf tag-separator {
             description "Tag separator character";
             type string {
               length 1;
             }
           }
           leaf-list tag-attribute {
             ordered-by user;
             description "One or more tag attributes";
             type enumeration {
               enum "ipv4addr" {
               }
               enum "ipv6addr" {
               }
             }
           }
           container encrypt {
             description "Specify encryption or hashing algorithm";
             uses apply-advanced;
             leaf hash {
               description "Hashing algorithm";
               type enumeration {
                 enum "md5" {
                   description "Md5 hash";
                 }
               }
             }
             leaf prefix {
               description "Hash prefix key";
               type string {
                 length "1 .. 63";
               }
             }
           }
           leaf ipv4-mask {
             description "Specify a logical and mask for the x-forwarded-for address";
             type jt:ipv4addr;
           }
           leaf ipv4-or-value {
             description "Specify a logical or mask for x-forwarded address";
             type jt:ipv4addr;
           }
           leaf ipv6-mask {
             description "Specify a logical and mask for the x-forwarded-for address";
             type jt:ipv6addr;
           }
           leaf ipv6-or-value {
             description "Specify a logical or mask for x-forwarded address";
             type jt:ipv6addr;
           }
         }
         leaf count {
           description "Enable statistics for term";
           type empty;
         }
       }
     }
   }
   grouping hcm_tag_match_object {
     uses apply-advanced;
     list destination-address {
       key name;
       ordered-by user;
       description "Match IP destination address";
       uses sfw_addr_object;
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list destination-ports {
       ordered-by user;
       description "Destination port list specification";
       type union {
         type string {
           pattern "<.*>|$.*";
         }
         type uint32 {
           range "0 .. 65535";
         }
       }
     }
     list destination-port-range {
       key "low high";
       ordered-by user;
       description "Match destination port range";
       leaf low {
         description "Lower limit of port range";
         type union {
           type string {
             pattern "<.*>|$.*";
           }
           type uint32 {
             range "0 .. 65535";
           }
         }
       }
       leaf high {
         description "Upper limit of port range";
         type union {
           type string {
             pattern "<.*>|$.*";
           }
           type uint32 {
             range "0 .. 65535";
           }
         }
       }
     }
   }
   grouping hcm_url_list_object {
     leaf name {
       description "List name";
       type string {
         length "1 .. 63";
       }
     }
     uses apply-advanced;
     list host {
       key name;
       ordered-by user;
       description "One or more host(s)";
       leaf name {
         description "Domain name";
         type string {
           length "1 .. 32";
         }
       }
       uses apply-advanced;
     }
     list request-uri {
       key name;
       ordered-by user;
       description "One or more uri's";
       leaf name {
         description "Uri name";
         type string {
           length "1 .. 40";
         }
       }
       uses apply-advanced;
     }
   }
   grouping hcm_url_rule_object {
     leaf name {
       description "Rule name";
       type string {
         length "1 .. 63";
       }
     }
     uses apply-advanced;
     list term {
       key name;
       ordered-by user;
       description "One or more terms in HCM url_rule";
       leaf name {
         description "Term name";
         type union {
           type string {
             pattern "<.*>|$.*";
           }
           type uint16 {
             range "1 .. 255";
           }
         }
       }
       uses apply-advanced;
       container from {
         description "Match criteria";
         presence "enable from";
         uses hcm_url_match_object;
       }
       container then {
         description "Action to take if the 'from' condition is matched";
         uses apply-advanced;
         leaf count {
           description "Enable statistics for term";
           type empty;
         }
         leaf log-request {
           description "Enable logging for term";
           type empty;
         }
         choice designation {
           case case_1 {
             leaf accept {
               description "Accept the URL";
               type empty;
             }
           }
           case case_2 {
             leaf discard {
               description "Discard the URL";
               type empty;
             }
           }
         }
       }
     }
   }
   grouping hcm_url_match_object {
     uses apply-advanced;
     list url-list {
       key name;
       ordered-by user;
       description "List of Url lists to referance";
       leaf name {
         description "Url list name";
         type string {
           length "1 .. 63";
         }
       }
       uses apply-advanced;
     }
     list url {
       key name;
       ordered-by user;
       description "Rule specific url list";
       leaf name {
         description "Url name";
         type union {
           type string {
             pattern "<.*>|$.*";
           }
           type uint16 {
             range "1 .. 32767";
           }
         }
       }
       uses apply-advanced;
       list host {
         key name;
         ordered-by user;
         description "One or more host(s)";
         leaf name {
           description "Domain name";
           type string {
             length "1 .. 32";
           }
         }
         uses apply-advanced;
       }
       list request-uri {
         key name;
         ordered-by user;
         description "One or more uri's";
         leaf name {
           description "Uri name";
           type string {
             length "1 .. 40";
           }
         }
         uses apply-advanced;
       }
     }
   }
   grouping header-manipulation-message-manipulation-rules-type {
     description "Definition of header manipulation";
     uses apply-advanced;
     list manipulation-rule {
       key name;
       ordered-by user;
       description "Definition of manipulation rules";
       uses header-manipulation-manipulation-rule-type;
     }
   }
   grouping header-manipulation-manipulation-rule-type {
     leaf name {
       description "Header manipulation rule name";
       type string;
     }
     uses apply-advanced;
     container actions {
       description "Header manipulation actions";
       uses header-manipulation-actions-type;
     }
   }
   grouping header-manipulation-actions-type {
     description "Manipulations on sip-headers or request-uri";
     uses apply-advanced;
     list sip-header {
       key name;
       ordered-by user;
       description "Manipulation of the SIP header";
       max-elements 50;
       leaf name {
         description "SIP header field name";
         type string;
       }
       uses apply-advanced;
       container field-value {
         description "Manipulation on the header's field value";
         uses header-manipulation-sip-header-field-value-type;
       }
     }
     container request-uri {
       presence "enable request-uri";
       description "Manipulation of the message request-uri";
       uses apply-advanced;
       container field-value {
         presence "enable field-value";
         description "Manipulation on the request-uri field value";
         uses apply-advanced;
         list modify-regular-expression {
           key name;
           ordered-by user;
           description "Set modify regular expression and patterns";
           max-elements 5;
           uses header-manipulation-modify-type;
         }
       }
     }
   }
   grouping header-manipulation-modify-type {
     description "Modify header using regular expression";
     leaf name {
       description "Regular expression pattern";
       type jt:regular-expression;
     }
     leaf with {
       description "Modification string";
       type string;
     }
   }
   grouping header-manipulation-sip-header-field-value-type {
     uses apply-advanced;
     leaf remove-all {
       description "Remove all headers";
       type empty;
     }
     list remove-regular-expression {
       key name;
       ordered-by user;
       description "Remove field-value";
       max-elements 5;
       uses header-manipulation-remove-type;
     }
     list reject-regular-expression {
       key name;
       ordered-by user;
       description "Reject message using regular expression";
       max-elements 5;
       uses header-manipulation-reject-type;
     }
     list modify-regular-expression {
       key name;
       ordered-by user;
       description "Modify field-value using regular expression";
       max-elements 5;
       uses header-manipulation-modify-type;
     }
     list add {
       key name;
       ordered-by user;
       description "Add field-value to header";
       max-elements 5;
       uses header-manipulation-add-type;
     }
     list add-missing {
       key name;
       ordered-by user;
       description "Add field-value only if header is missing";
       max-elements 5;
       uses header-manipulation-add-missing-type;
     }
     list add-overwrite {
       key name;
       ordered-by user;
       description "Overwrite headers field-value";
       max-elements 5;
       uses header-manipulation-add-overwrite-type;
     }
   }
   grouping header-manipulation-add-missing-type {
     description "Add header only if missing";
     leaf name {
       description "Field-value to add";
       type string;
     }
   }
   grouping header-manipulation-add-overwrite-type {
     description "Overwrite existing header";
     leaf name {
       description "Field-value to add";
       type string;
     }
   }
   grouping header-manipulation-add-type {
     description "Add header";
     leaf name {
       description "Field-value to add";
       type string;
     }
   }
   grouping header-manipulation-reject-type {
     description "Reject messages that match a regular expression";
     leaf name {
       description "Regular expression pattern";
       type jt:regular-expression;
     }
   }
   grouping header-manipulation-remove-type {
     description "Remove headers that match a regular expression";
     leaf name {
       description "Regular expression pattern";
       type jt:regular-expression;
     }
   }
   grouping icap-profile-object {
     leaf name {
       description "ICAP service profile name";
       type string {
         length "1 .. 63";
       }
     }
     uses apply-advanced;
     list server {
       key name;
       ordered-by user;
       description "Configure service redirection server";
       max-elements 16;
       uses icap-redir-server;
     }
     container http {
       description "ICAP methods switch";
       uses http-redirect-object;
     }
     container fallback-option {
       description "Failure event actions";
       uses icap-redirect-fallback;
     }
     leaf timeout {
       description "Server response timeout in milliseconds";
       default "500";
       type union {
         type string {
           pattern "<.*>|$.*";
         }
         type uint16 {
           range "100 .. 50000";
         }
       }
     }
   }
   grouping http-redirect-object {
     uses apply-advanced;
     leaf redirect-request {
       description "Enable redirect service on HTTP request";
       type empty;
     }
     leaf redirect-response {
       description "Enable redirect service on HTTP response";
       type empty;
     }
   }
   grouping icap-redir-server {
     leaf name {
       description "Server name";
       type string {
         length "1 .. 63";
       }
     }
     uses apply-advanced;
     container authorization {
       description "User authentication";
       uses apply-advanced;
       leaf authorization-type {
         description "Authentication type. 'Basic' by default";
         type string {
           length "1 .. 127";
         }
       }
       container credentials {
         description "Credentials text";
         choice credentials-choice {
           case case_1 {
             leaf ascii {
               description "ASCII string";
               type string {
                 length "1 .. 511";
               }
             }
           }
           case case_2 {
             leaf base64 {
               description "Base64 string";
               type string {
                 length "1 .. 511";
               }
             }
           }
         }
       }
     }
     leaf host {
       description "Host name/IP address";
       type string {
         length "1 .. 255";
       }
     }
     leaf port {
       description "Server listening port";
       default "1344";
       type union {
         type string {
           pattern "<.*>|$.*";
         }
         type uint16 {
           range "1025 .. 65535";
         }
       }
     }
     leaf reqmod-uri {
       description "REQMOD option resource identifier";
       type string {
         length "0 .. 1023";
       }
     }
     leaf respmod-uri {
       description "RESPMOD option resource identifier";
       type string {
         length "0 .. 1023";
       }
     }
     container routing-instance {
       description "Routing instance";
       leaf ri-name {
         description "Routing instance name";
         type string {
           length "1 .. 127";
         }
       }
     }
     leaf sockets {
       description "Number of connections to create";
       default "8";
       type union {
         type string {
           pattern "<.*>|$.*";
         }
         type uint8 {
           range "1 .. 64";
         }
       }
     }
     leaf tls-profile {
       description "TLS profile";
       type string {
         length "1 .. 63";
       }
     }
   }
   grouping icap-redirect-fallback {
     uses apply-advanced;
     leaf timeout {
       description "Request timeout action";
       default "permit";
       type enumeration {
         enum "permit" {
           description "Direct permit action";
         }
         enum "log-permit" {
           description "Log then permit action";
         }
         enum "block" {
           description "Block action";
         }
       }
     }
     leaf connectivity {
       description "Connection-related failure action";
       default "permit";
       type enumeration {
         enum "permit" {
           description "Direct permit action";
         }
         enum "log-permit" {
           description "Log then permit action";
         }
         enum "block" {
           description "Block action";
         }
       }
     }
     leaf default-action {
       description "Default failure action";
       default "permit";
       type enumeration {
         enum "permit" {
           description "Direct permit action";
         }
         enum "log-permit" {
           description "Log then permit action";
         }
         enum "block" {
           description "Block action";
         }
       }
     }
   }
   grouping icap-redirect-traceoptions {
     description "ICAP redirect traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Trace flags";
       leaf name {
         type enumeration {
           enum "all" {
             description "Trace everything";
           }
           enum "icap-redirect-re" {
             description "Trace events on RE side";
           }
           enum "icap-redirect-control" {
             description "Trace events on PFE-ukernel side";
           }
           enum "icap-redirect-connection" {
             description "Trace ICAP server connection events";
           }
           enum "icap-redirect-protocol" {
             description "Trace redirect packet events";
           }
         }
       }
     }
   }
   grouping identity-management-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses identity-server-connection-type;
     }
     container secondary {
       description "Secondary server";
       uses identity-server-connection-type;
     }
     leaf token-api {
       description "API of acquiring token for OAuth2 authentication";
       type string {
         length "1 .. 128";
       }
     }
     leaf query-api {
       description "Query API";
       type string {
         length "4 .. 128";
       }
     }
   }
   grouping identity-server-connection-type {
     description "Connection parameters per server";
     uses apply-advanced;
     leaf address {
       description "Server address as fqdn or ip address";
       type string;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
     leaf source {
       description "Client address";
       type jt:ipaddr;
     }
     leaf interface {
       description "Interface name";
       type union {
         type jt:interface-name;
         type string {
           pattern "<.*>|$.*";
         }
       }
     }
     leaf routing-instance {
       description "Routing instance name";
       type string;
     }
   }
   grouping ids-option-type {
     description "Configure screen object";
     leaf name {
       description "Screen object name";
       type string {
         length "1 .. 64";
       }
     }
     uses apply-advanced;
     leaf description {
       description "Text description of screen";
       type string {
         length "1 .. 900";
       }
     }
     leaf alarm-without-drop {
       description "Do not drop packet, only generate alarm";
       type empty;
     }
     leaf match-direction {
       description "Match direction";
       type enumeration {
         enum "input" {
           description "Match on input to interface";
         }
         enum "output" {
           description "Match on output from interface";
         }
         enum "input-output" {
           description "Match on input to or output from interface";
         }
       }
     }
     container aggregation {
       presence "enable aggregation";
       description "Configure the source and Destination prefix for a ids-option";
       uses apply-advanced;
       leaf source-prefix-mask {
         description "Source IPV4 prefix";
         type union {
           type string {
             pattern "<.*>|$.*";
           }
           type uint32 {
             range "1 .. 32";
           }
         }
       }
       leaf destination-prefix-mask {
         description "Destination IPV4 prefix";
         type union {
           type string {
             pattern "<.*>|$.*";
           }
           type uint32 {
             range "1 .. 32";
           }
         }
       }
       leaf source-prefix-v6-mask {
         description "Source IPV6 prefix";
         type union {
           type string {
             pattern "<.*>|$.*";
           }
           type uint32 {
             range "1 .. 128";
           }
         }
       }
       leaf destination-prefix-v6-mask {
         description "Destination IPV6 prefix";
         type union {
           type string {
             pattern "<.*>|$.*";
           }
           type uint32 {
             range "1 .. 128";
           }
         }
       }
     }
     container icmp {
       description "Configure ICMP ids options";
       uses apply-advanced;
       container ip-sweep {
         presence "enable ip-sweep";
         description "Configure ip sweep ids option";
         leaf threshold {
           description "Threshold";
           default "5000";
           units "microseconds in which 10 ICMP packets are detected";
           type union {
             type string {
               pattern "<.*>|$.*";
             }
             type uint32 {
               range "1000 .. 1000000";
             }
           }
         }
       }
       leaf fragment {
         description "Enable ICMP fragment ids option";
         type empty;
       }
       leaf large {
         description "Enable large ICMP packet (size > 1024) ids option";
         type empty;
       }
       container flood {
         presence "enable flood";
         description "Configure icmp flood ids option";
         leaf threshold {
           description "Threshold";
           default "1000";
           units "ICMP packets per second";
           type union {
             type string {
               pattern "<.*>|$.*";
             }
             type uint32;
           }
         }
       }
       leaf ping-death {
         description "Enable ping of death ids option";
         type empty;
       }
       leaf icmpv6-malformed {
         description "Enable icmpv6 malformed ids option";
         type empty;
       }
     }
     container ip {
       description "Configure IP layer ids options";
       uses apply-advanced;
       leaf bad-option {
         description "Enable ip with bad option ids option";
         type empty;
       }
       leaf record-route-option {
         description "Enable ip with record route option ids option";
         type empty;
       }
       leaf timestamp-option {
         description "Enable ip with timestamp option ids option";
         type empty;
       }
       leaf security-option {
         description "Enable ip with security option ids option";
         type empty;
       }
       leaf stream-option {
         description "Enable ip with stream option ids option";
         type empty;
       }
       leaf spoofing {
         description "Enable IP address spoofing ids option";
         type empty;
       }
       leaf source-route-option {
         description "Enable ip source route ids option";
         type empty;
       }
       leaf loose-source-route-option {
         description "Enable ip with loose source route ids option";
         type empty;
       }
       leaf strict-source-route-option {
         description "Enable ip with strict source route ids option";
         type empty;
       }
       leaf unknown-protocol {
         description "Enable ip unknown protocol ids option";
         type empty;
       }
       container block-frag {
         presence "enable block-frag";
         description "Enable ip fragment blocking ids option";
         uses apply-advanced;
         leaf-list white-list {
           ordered-by user;
           description "Configure ip block fragmentation white list group name";
           type string;
           max-elements 2;
         }
       }
       leaf tear-drop {
         description "Enable tear drop ids option";
         type empty;
       }
       container ipv6-extension-header {
         description "Configure ipv6 extension header ids option";
         uses apply-advanced;
         container hop-by-hop-header {
           presence "enable hop-by-hop-header";
           description "Enable ipv6 hop by hop option header ids option";
           uses apply-advanced;
           leaf jumbo-payload-option {
             description "Enable jumbo payload option ids option";
             type empty;
           }
           leaf router-alert-option {
             description "Enable router alert option ids option";
             type empty;
           }
           leaf quick-start-option {
             description "Enable quick start option ids option";
             type empty;
           }
           leaf CALIPSO-option {
             description "Enable Common Architecture Label ipv6 Security Option ids option";
             type empty;
           }
           leaf SMF-DPD-option {
             description "Enable Simplified Multicast Forwarding ipv6 Duplicate Packet Detection option ids option";
             type empty;
           }
           leaf RPL-option {
             description "Enable Routing Protocol for Low-power and Lossy networks option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf routing-header {
           description "Enable ipv6 routing header ids option";
           type empty;
         }
         leaf fragment-header {
           description "Enable ipv6 fragment header ids option";
           type empty;
         }
         leaf ESP-header {
           description "Enable ipv6 Encapsulating Security Payload header ids option";
           type empty;
         }
         leaf AH-header {
           description "Enable ipv6 Authentication Header ids option";
           type empty;
         }
         leaf no-next-header {
           description "Enable ipv6 no next header ids option";
           type empty;
         }
         container destination-header {
           presence "enable destination-header";
           description "Enable ipv6 destination option header ids option";
           uses apply-advanced;
           leaf tunnel-encapsulation-limit-option {
             description "Enable tunnel encapsulation limit option ids option";
             type empty;
           }
           leaf home-address-option {
             description "Enable home address option ids option";
             type empty;
           }
           leaf ILNP-nonce-option {
             description "Enable Identifier-Locator Network Protocol Nonce option ids option";
             type empty;
           }
           leaf line-identification-option {
             description "Enable line identification option ids option";
             type empty;
           }
           list user-defined-option-type {
             key name;
             ordered-by user;
             description "User-defined option type range";
             max-elements 256;
             leaf name {
               description "User-defined option type low value";
               type union {
                 type string {
                   pattern "<.*>|$.*";
                 }
                 type uint32 {
                   range "1 .. 255";
                 }
               }
             }
             container to {
               description "Upper limit of option type range";
               uses apply-advanced;
               leaf type-high {
                 description "User-defined option type high value";
                 type union {
                   type string {
                     pattern "<.*>|$.*";
                   }
                   type uint32 {
                     range "1 .. 255";
                   }
                 }
               }
             }
           }
         }
         leaf shim6-header {
           description "Enable ipv6 shim header ids option";
           type empty;
         }
         leaf mobility-header {
           description "Enable ipv6 mobility header ids option";
           type empty;
         }
         leaf HIP-header {
           description "Enable ipv6 Host Identify Protocol header ids option";
           type empty;
         }
         list user-defined-header-type {
           key name;
           ordered-by user;
           description "User-defined header type range";
           max-elements 256;
           leaf name {
             description "User-defined header type low value";
             type union {
               type string {
                 pattern "<.*>|$.*";
               }
               type uint32 {
                 range "0 .. 255";
               }
             }
           }
           container to {
             description "Upper limit of header type range";
             uses apply-advanced;
             leaf type-high {
               description "User-defined header type high value";
               type union {
                 type string {
                   pattern "<.*>|$.*";
                 }
                 type uint32 {
                   range "0 .. 255";
                 }
               }
             }
           }
         }
       }
       leaf ipv6-extension-header-limit {
         description "Enable ipv6 extension header limit ids option";
         type union {
           type string {
             pattern "<.*>|$.*";
           }
           type uint32 {
             range "0 .. 32";
           }
         }
       }
       leaf ipv6-malformed-header {
         description "Enable ipv6 malformed header ids option";
         type empty;
       }
       container tunnel {
         description "Configure IP tunnel ids options";
         uses apply-advanced;
         leaf bad-inner-header {
           description "Enable IP tunnel bad inner header ids option";
           type empty;
         }
         container gre {
           description "Configure IP tunnel GRE ids option";
           uses apply-advanced;
           leaf gre-6in4 {
             description "Enable IP tunnel GRE 6in4 ids option";
             type empty;
           }
           leaf gre-4in6 {
             description "Enable IP tunnel GRE 4in6 ids option";
             type empty;
           }
           leaf gre-6in6 {
             description "Enable IP tunnel GRE 6in6 ids option";
             type empty;
           }
           leaf gre-4in4 {
             description "Enable IP tunnel GRE 4in4 ids option";
             type empty;
           }
         }
         container ip-in-udp {
           description "Configure IP tunnel IPinUDP ids option";
           uses apply-advanced;
           leaf teredo {
             description "Enable IP tunnel IPinUDP Teredo ids option";
             type empty;
           }
         }
         container ipip {
           description "Configure IP tunnel IPIP ids option";
           uses apply-advanced;
           leaf ipip-6to4relay {
             description "Enable IP tunnel IPIP 6to4 Relay ids option";
             type empty;
           }
           leaf ipip-6in4 {
             description "Enable IP tunnel IPIP 6in4 ids option";
             type empty;
           }
           leaf ipip-4in6 {
             description "Enable IP tunnel IPIP 4in6 ids option";
             type empty;
           }
           leaf ipip-4in4 {
             description "Enable IP tunnel IPIP 4in4 ids option";
             type empty;
           }
           leaf ipip-6in6 {
             description "Enable IP tunnel IPIP 6in6 ids option";
             type empty;
           }
           leaf ipip-6over4 {
             description "Enable IP tunnel IPIP 6over4 ids option";
             type empty;
           }
           leaf isatap {
             description "Enable IP tunnel IPIP ISATAP ids option";
             type empty;
           }
           leaf dslite {
             description "Enable IP tunnel IPIP DS-Lite ids option";
             type empty;
           }
         }
       }
     }
     container tcp {
       description "Configure TCP Layer ids options";
       uses apply-advanced;
       leaf syn-fin {
         description "Enable SYN and FIN bits set attack ids option";
         type empty;
       }
       leaf fin-no-ack {
         description "Enable Fin bit with no ACK bit ids option";
         type empty;
       }
       leaf tcp-no-flag {
         description "Enable TCP packet without flag ids option";
         type empty;
       }
       leaf syn-frag {
         description "Enable SYN fragment ids option";
         type empty;
       }
       leaf syn-defense {
         description "Enable tcp syn-defense";
         type empty;
       }
       container port-scan {
         presence "enable port-scan";
         description "Configure TCP port scan ids option";
         leaf threshold {
           description "Threshold";
           default "5000";
           units "microseconds in which 10 attack packets are detected";
           type union {
             type string {
               pattern "<.*>|$.*";
             }
             type uint32 {
               range "1000 .. 1000000";
             }
           }
         }
       }
       container syn-ack-ack-proxy {
         presence "enable syn-ack-ack-proxy";
         description "Configure syn-ack-ack proxy ids option";
         leaf threshold {
           description "Threshold";
           default "512";
           units "un-authenticated connections";
           type union {
             type string {
               pattern "<.*>|$.*";
             }
             type uint32 {
               range "1 .. 250000";
             }
           }
         }
       }
       container syn-flood {
         presence "enable syn-flood";
         description "Configure SYN flood ids option";
         uses apply-advanced;
         leaf alarm-threshold {
           description "Alarm threshold";
           default "512";
           units "requests per second";
           type union {
             type string {
               pattern "<.*>|$.*";
             }
             type uint32;
           }
         }
         leaf attack-threshold {
           description "Attack threshold";
           default "200";
           units "proxied requests per second";
           type union {
             type string {
               pattern "<.*>|$.*";
             }
             type uint32;
           }
         }
         leaf source-threshold {
           description "Source threshold";
           default "4000";
           units "SYN pps";
           type union {
             type string {
               pattern "<.*>|$.*";
             }
             type uint32;
           }
         }
         leaf destination-threshold {
           description "Destination threshold";
           default "4000";
           units "SYN pps";
           type union {
             type string {
               pattern "<.*>|$.*";
             }
             type uint32;
           }
         }
         leaf queue-size {
           description "Queue size";
           status deprecated;
           default "1024";
           units "proxied requests in queue";
           type union {
             type string {
               pattern "<.*>|$.*";
             }
             type uint32 {
               range "200 .. 20000";
             }
           }
         }
         leaf timeout {
           description "SYN flood ager timeout";
           default "20";
           units "seconds";
           type union {
             type string {
               pattern "<.*>|$.*";
             }
             type uint32 {
               range "1 .. 50";
             }
           }
         }
         list white-list {
           key name;
           description "Set of IP addresses that will not trigger a screen";
           max-elements 2;
           leaf name {
             description "White-list name";
             type string {
               length "1 .. 32";
             }
           }
           uses apply-advanced;
           leaf-list source-address {
             ordered-by user;
             description "Source address";
             type jt:ipprefix;
             max-elements 32;
           }
           leaf-list destination-address {
             ordered-by user;
             description "Destination address";
             type jt:ipprefix;
             max-elements 32;
           }
         }
       }
       leaf land {
         description "Enable land attack ids option";
         type empty;
       }
       leaf winnuke {
         description "Enable winnuke attack ids option";
         type empty;
       }
       container tcp-sweep {
         presence "enable tcp-sweep";
         description "Configure TCP sweep ids option";
         leaf threshold {
           description "Threshold";
           default "5000";
           units "microseconds in which 10 TCP packets are detected";
           type union {
             type string {
               pattern "<.*>|$.*";
             }
             type uint32 {
               range "1000 .. 1000000";
             }
           }
         }
       }
     }
     container udp {
       description "Configure UDP layer ids options";
       uses apply-advanced;
       container flood {
         presence "enable flood";
         description "Configure UDP flood ids option";
         uses apply-advanced;
         leaf threshold {
           description "Threshold";
           default "1000";
           units "UDP packets per second";
           type union {
             type string {
               pattern "<.*>|$.*";
             }
             type uint32;
           }
         }
         leaf-list white-list {
           ordered-by user;
           description "Configure UDP flood white list group name";
           type string;
           max-elements 2;
         }
       }
       container udp-sweep {
         presence "enable udp-sweep";
         description "Configure UDP sweep ids option";
         leaf threshold {
           description "Threshold";
           default "5000";
           units "microseconds in which 10 UDP packets are detected";
           type union {
             type string {
               pattern "<.*>|$.*";
             }
             type uint32 {
               range "1000 .. 1000000";
             }
           }
         }
       }
       container port-scan {
         presence "enable port-scan";
         description "Configure UDP port scan ids option";
         leaf threshold {
           description "Threshold";
           default "5000";
           units "microseconds in which 10 attack packets are detected";
           type union {
             type string {
               pattern "<.*>|$.*";
             }
             type uint32 {
               range "1000 .. 1000000";
             }
           }
         }
       }
     }
     container limit-session {
       description "Limit sessions";
       uses apply-advanced;
       leaf source-ip-based {
         description "Limit sessions from the same source IP";
         type union {
           type string {
             pattern "<.*>|$.*";
           }
           type uint32;
         }
       }
       leaf destination-ip-based {
         description "Limit sessions to the same destination IP";
         type union {
           type string {
             pattern "<.*>|$.*";
           }
           type uint32;
         }
       }
       container by-source {
         presence "enable by-source";
         description "Limit sessions from the same source IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
       container by-destination {
         presence "enable by-destination";
         description "Limit sessions to the same destination IP or subnet";
         uses apply-advanced;
         leaf maximum-sessions {
           description "Limit sessions on the basis of maximum concurrent sessions";
           type union {
             type string {
               pattern "<.*>|$.*";
             }
             type uint32;
           }
         }
         leaf packet-rate {
           description "Limit sessions on the basis of packet rate";
           type union {
             type string {
               pattern "<.*>|$.*";
             }
             type uint32 {
               range "1 .. 4294967295";
             }
           }
         }
         leaf session-rate {
           description "Limit sessions on the basis of session rate";
           type union {
             type string {
               pattern "<.*>|$.*";
             }
             type uint32 {
               range "1 .. 4294967295";
             }
           }
         }
         container by-protocol {
           description "Limit sessions on the basis of protocol";
           presence "enable by-protocol";
           uses by-protocol-object-type;
         }
         leaf-list whitelist {
           ordered-by user;
           description "Configure white list group name";
           type string;
           max-elements 10;
         }
       }
     }
   }
   grouping by-protocol-object-type {
     description "Configure limit-session on the basis of protocol";
     uses apply-advanced;
     container tcp {
       description "Configure limit-session on the basis of TCP";
       presence "enable tcp";
       uses by-protocol-object-limit-tcp-type;
     }
     container udp {
       description "Configure limit-session on the basis of UDP";
       presence "enable udp";
       uses by-protocol-object-limit-type;
     }
     container icmp {
       description "Configure limit-session on the basis of ICMP";
       presence "enable icmp";
       uses by-protocol-object-limit-type;
     }
   }
   grouping by-protocol-object-limit-tcp-type {
     description "Configure the limit-session for tcp protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
     container syn-cookie {
       presence "enable syn-cookie";
       description "Configure syn-cookie parameters";
       uses apply-advanced;
       leaf mss {
         description "TCP maximum segment size";
         type union {
           type string {
             pattern "<.*>|$.*";
           }
           type uint32 {
             range "64 .. 65535";
           }
         }
       }
       leaf threshold-rate {
         description "TCP-SYN cps rate to trigger SYN-COOKIE";
         type union {
           type string {
             pattern "<.*>|$.*";
           }
           type uint32 {
             range "1 .. 4294967295";
           }
         }
       }
       leaf threshold-num {
         description "Number of sessions to trigger SYN-COOKIE";
         type union {
           type string {
             pattern "<.*>|$.*";
           }
           type uint32;
         }
       }
     }
   }
   grouping by-protocol-object-limit-type {
     description "Configure the limit-session for each protocol";
     uses apply-advanced;
     leaf maximum-sessions {
       description "Limit sessions on the basis of maximum concurrent sessions";
       type union {
         type string {
           pattern "<.*>|$.*";
         }
         type uint32;
       }
     }
     leaf packet-rate {
       description "Limit sessions on the basis of packet rate";
       type union {
         type string {
           pattern "<.*>|$.*";
         }
         type uint32 {
           range "1 .. 4294967295";
         }
       }
     }
     leaf session-rate {
       description "Limit sessions on the basis of session rate";
       type union {
         type string {
           pattern "<.*>|$.*";
         }
         type uint32 {
           range "1 .. 4294967295";
         }
       }
     }
     leaf-list whitelist {
       ordered-by user;
       description "Configure white list group name";
       type string;
       max-elements 10;
     }
   }
   grouping ids-wlist-type {
     leaf name {
       description "White-list name";
       type string {
         length "1 .. 32";
       }
     }
     uses apply-advanced;
     leaf-list address {
       ordered-by user;
       description "Address";
       type jt:ipprefix;
       max-elements 32;
     }
   }
   grouping ids_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to and output from interface";
         }
       }
     }
     list term {
       key name;
       ordered-by user;
       description "Define an IDS term";
       leaf name {
         description "Term name";
         type string {
           length "1 .. 63";
         }
       }
       uses apply-advanced;
       container from {
         description "Define match criteria";
         uses sfw_match_object;
       }
       container then {
         description "Action to take if the 'from' condition is matched";
         uses apply-advanced;
         choice accept_choice {
           case case_1 {
             leaf force-entry {
               description "Force entries in IDS tables for matching traffic";
               type empty;
             }
           }
           case case_2 {
             leaf ignore-entry {
               description "Ignore IDS events for matching traffic";
               type empty;
             }
           }
           case case_3 {
             leaf user-interface {
               description "User-interface trace level";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
           }
         }
         container aggregation {
           description "Define aggregation parameters";
           uses apply-advanced;
           leaf source-prefix {
             description "Prefix length for IPv4 source addresses";
             type union {
               type string {
                 pattern "<.*>|$.*";
               }
               type int32 {
                 range "1 .. 32";
               }
             }
           }
           leaf destination-prefix {
             description "Prefix length for IPv4 destination addresses";
             type union {
               type string {
                 pattern "<.*>|$.*";
               }
               type int32 {
                 range "1 .. 32";
               }
             }
           }
           leaf source-prefix-ipv6 {
             description "Prefix length for IPv6 source addresses";
             type union {
               type string {
                 pattern "<.*>|$.*";
               }
               type int32 {
                 range "1 .. 128";
               }
             }
           }
           leaf destination-prefix-ipv6 {
             description "Prefix length for IPv6 destination addresses";
             type union {
               type string {
                 pattern "<.*>|$.*";
               }
               type int32 {
                 range "1 .. 128";
               }
             }
           }
         }
         container logging {
           description "Define system logging parameters";
           uses apply-advanced;
           leaf threshold {
             description "Threshold above which events should be logged";
             type union {
               type int32;
               type string {
                 pattern "<.*>|$.*";
               }
             }
           }
           leaf syslog {
             description "System log information about the packet";
             type empty;
           }
         }
         container syn-cookie {
           description "Define SYN cookie parameters";
           uses apply-advanced;
           leaf threshold {
             description "Threshold above which SYN cookies are enabled";
             type union {
               type int32;
               type string {
                 pattern "<.*>|$.*";
               }
             }
           }
           leaf mss {
             description "MSS value for TCP delayed binding";
             type union {
               type string {
                 pattern "<.*>|$.*";
               }
               type int32 {
                 range "128 .. 8192";
               }
             }
           }
         }
         container session-limit {
           description "Define IDS session limit parameters";
           uses apply-advanced;
           container by-source {
             description "Define IDS session limit parameters by source";
             uses ids_limit_type;
           }
           container by-destination {
             description "Define IDS session limit parameters by destination";
             uses ids_limit_type;
           }
           container by-pair {
             description "Define IDS session limit parameters by source-destination pair";
             presence "enable by-pair";
             uses ids_limit_type;
           }
         }
         leaf-list allow-ip-options {
           ordered-by user;
           type string;
         }
         leaf-list allow-ipv6-extension-header {
           ordered-by user;
           type string;
         }
         leaf tcp-syn-defense {
           description "Enable tcp-syn-defense";
           type empty;
         }
         leaf tcp-syn-fragment-check {
           description "Enable tcp syn fragment check";
           type empty;
         }
         leaf tcp-winnuke-check {
           description "Enable tcp winnuke check";
           type empty;
         }
         leaf icmp-fragment-check {
           description "Enable icmp fragment check";
           type empty;
         }
         leaf icmp-large-packet-check {
           description "Enable icmp large packet check";
           type empty;
         }
         leaf land-attack-check {
           description "Enable land attack checks";
           type enumeration {
             enum "ip-only" {
               description "Land attack check is on IP address only";
             }
             enum "ip-port" {
               description "Land attack check is on both IP and port";
             }
           }
         }
       }
     }
   }
   grouping ids_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
     leaf hold-time {
       description "How long to keep limit information after session is deleted";
       units "second";
       type union {
         type string {
           pattern "<.*>|$.*";
         }
         type int32 {
           range "0 .. 60";
         }
       }
     }
     container by-protocol {
       description "Define IDS session limit parameters";
       uses apply-advanced;
       container tcp {
         description "Define TCP IDS session limits";
         uses ids_proto_limit_type;
       }
       container udp {
         description "Define UDP IDS session limits by source";
         uses ids_proto_limit_type;
       }
       container icmp {
         description "Define ICMP IDS session limits by source";
         uses ids_proto_limit_type;
       }
     }
   }
   grouping ids_proto_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
   }
   grouping ims-connection-type {
     description "Identity management connection";
     uses apply-advanced;
     leaf connect-method {
       description "Method of connection";
       type enumeration {
         enum "https" {
           description "HTTPS connection";
         }
         enum "http" {
           description "HTTP connection";
         }
       }
     }
     leaf port {
       description "Server port";
       default "443";
       type union {
         type string {
           pattern "<.*>|$.*";
         }
         type uint32 {
           range "1 .. 65535";
         }
       }
     }
     container primary {
       description "Primary server";
       uses server-connection-type;
     }
     container secondary {
       description "Secondary server";
       uses server-connection-type;
     }
     leaf token-api {
       description "API of acquiring token for OAuth2 authentication";
       type string {
         length "1 .. 128";
       }
     }
     leaf query-api {
       description "Query API";
       type string {
         length "4 .. 128";
       }
     }
   }
   grouping ims-traceoptions-type {
     description "Identity management tracing Options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "all" {
             description "Trace identity management all modules";
           }
           enum "authentication-management" {
             description "Trace advanced-query auth table management module";
           }
           enum "configuration" {
             description "Trace identity management configuration";
           }
           enum "dispatcher" {
             description "Trace dispatcher module";
           }
           enum "query" {
             description "Trace query process";
           }
           enum "jims-validator-query" {
             description "Trace jims validator query process";
           }
           enum "memory" {
             description "Trace memory";
           }
         }
       }
     }
   }
   grouping inband-telemetry-profile-type {
     description "Inband Telemetry Profile";
     leaf name {
       description "Profile Name";
       type string {
         length "1 .. 32";
       }
     }
     uses apply-advanced;
     leaf sample-rate {
       description "Ratio of packets to be sampled (1 out of N)";
       type union {
         type string {
           pattern "<.*>|$.*";
         }
         type uint32 {
           range "1 .. 16777215";
         }
       }
     }
     container collector {
       description "Profile options";
       uses apply-advanced;
       leaf source-address {
         description "Source IP Address";
         type jt:ipv4addr;
       }
       leaf destination-address {
         description "Destination IP Address";
         type jt:ipv4addr;
       }
       leaf destination-port {
         description "Destionation Port";
         type union {
           type string {
             pattern "<.*>|$.*";
           }
           type uint32 {
             range "1 .. 65535";
           }
         }
       }
       leaf maximum-clip-length {
         description "Maximum data packet length for export";
         default "256";
         type union {
           type string {
             pattern "<.*>|$.*";
           }
           type uint32 {
             range "64 .. 9000";
           }
         }
       }
       leaf mtu {
         description "Maximum size of export packet";
         default "9000";
         type union {
           type string {
             pattern "<.*>|$.*";
           }
           type uint32 {
             range "256 .. 9000";
           }
         }
       }
     }
   }
   grouping interface_map_type {
     uses apply-advanced;
     leaf file-specification {
       description "Default file specification";
       type string;
     }
     leaf collector {
       description "Default Collector PIC to be used for flow manipulation";
       type union {
         type jt:interface-device;
         type string {
           pattern "<.*>|$.*";
         }
       }
     }
     list input_intf_to_cpic_map {
       key name;
       uses input_intf_to_cpic_map_type;
     }
   }
   grouping input_intf_to_cpic_map_type {
     leaf name {
       description "Input interface for flow collection";
       type union {
         type jt:interface-name;
         type string {
           pattern "<.*>|$.*";
         }
       }
     }
     uses apply-advanced;
     leaf file-specification {
       description "File specification to use for this interface";
       type string;
     }
     leaf collector {
       description "Collector PIC to be used for flow manipulation";
       type union {
         type jt:interface-device;
         type string {
           pattern "<.*>|$.*";
         }
       }
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping ipr_profile_object {
     leaf name {
       description "IP-reassembly profile name";
       type string {
         length "1 .. 32";
       }
     }
     uses apply-advanced;
     leaf timeout {
       description "IP-reassembly timeout value";
       type union {
         type string {
           pattern "<.*>|$.*";
         }
         type int32 {
           range "2 .. 60";
         }
       }
     }
     leaf max-reassembly-pending-packets {
       description "IP-reassembly pending packets";
       type union {
         type string {
           pattern "<.*>|$.*";
         }
         type int32 {
           range "100 .. 100000";
         }
       }
     }
   }
   grouping ipr_rule_object {
     leaf name {
       description "Rule name";
       type string {
         length "1 .. 63";
       }
     }
     uses apply-advanced;
     leaf match-direction {
       description "Direction for which the rule match is applied";
       type enumeration {
         enum "input" {
           description "Match on input to interface";
         }
       }
     }
   }
   grouping jims-validator-type {
     description "Web server from JIMS for Validate or group query request";
     uses apply-advanced;
     leaf address {
       description "IP address or hostname of web server";
       type string {
         length "1 .. 128";
       }
     }
     leaf client-id {
       description "Client ID for OAuth2 grant";
       type string {
         length "1 .. 64";
       }
     }
     leaf client-secret {
       description "Client secret for OAuth2 grant";
       type string {
         length "1 .. 128";
       }
     }
     leaf port {
       description "Web server port";
       default "591";
       type union {
         type string {
           pattern "<.*>|$.*";
         }
         type uint32 {
           range "1 .. 65535";
         }
       }
     }
   }
   grouping juniper-pic-services-logging-options {
     uses apply-advanced;
     container traceoptions {
       description "Fsad trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "init" {
               description "Trace initialization events";
             }
             enum "bookkeeping" {
               description "Trace bookkeeping events";
             }
             enum "connections" {
               description "Trace connection-specific events";
             }
             enum "charging" {
               description "Trace charging-specific events";
             }
             enum "flow-collector" {
               description "Trace flow collector specific events";
             }
             enum "all" {
               description "Trace everything";
             }
           }
         }
       }
     }
   }
   grouping juniper-services-captive-portal {
     uses apply-advanced;
     leaf authentication-profile-name {
       description "Access profile name to use for authentication";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
             }
             enum "parse" {
               description "Trace configuration parsing";
             }
             enum "esw-if" {
               description "Trace ESW Interactions";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
         }
         enum "https" {
           description "Encrypted HTTPS will be used for Captive Portal authentication";
         }
       }
     }
     container custom-options {
       presence "enable custom-options";
       description "Captive Portal html user interface customization options";
       uses apply-advanced;
       leaf header-logo {
         description "Path to logo image file";
         type string {
           length "1 .. 255";
         }
       }
       leaf header-bgcolor {
         description "Background color of the html header in hex html format";
         type string {
           length 7;
         }
       }
       leaf header-text-color {
         description "Text color of the html header in hex html format";
         type string {
           length 7;
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
         }
       }
       leaf form-header-text-color {
         description "Text color of the login form header in hex html format";
         type string {
           length 7;
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
         }
       }
       leaf footer-text-color {
         description "Text color of the footer in hex html format";
         type string {
           length 7;
         }
       }
       leaf post-authentication-url {
         description "Post authentication redirection URL";
         type string {
           length "1 .. 255";
         }
       }
     }
   }
   grouping l2tp_access_line_object {
     uses apply-advanced;
     leaf connection-speed-update {
       description "Support connection speed updates";
       type empty;
     }
   }
   grouping l2tp_destination_object {
     uses apply-advanced;
     leaf lockout-timeout {
       description "The lockout timeout in seconds";
       default "300";
       type union {
         type string {
           pattern "<.*>|$.*";
         }
         type uint16 {
           range "60 .. 3600";
         }
       }
     }
     list lockout-result-code {
       key name;
       ordered-by user;
       description "The lockout result code";
       leaf name {
         description "The lockout result code";
         type enumeration {
           enum "1" {
             description "Clear control connection or Loss of carrier";
           }
           enum "2" {
             description "Reason indicated in error code";
           }
           enum "3" {
             description "Control Channel exists or Administrator reasons";
           }
           enum "4" {
             description "Unauthorized for channel or Temporary facilities unavailable";
           }
           enum "5" {
             description "Version unsupported or Permanent facilities unavailable";
           }
           enum "6" {
             description "Requester shut down or Invalid destination";
           }
           enum "7" {
             description "FSM error or No carrier detected";
           }
           enum "8" {
             description "Busy signal";
           }
           enum "9" {
             description "Lack of dial tone";
           }
           enum "10" {
             description "Unable to established within time";
           }
           enum "11" {
             description "No framing was detected";
           }
         }
       }
       uses apply-advanced;
       list error-code {
         key name;
         ordered-by user;
         description "The lockout error code";
         leaf name {
           description "The lockout error code";
           type enumeration {
             enum "1" {
               description "No control connection";
             }
             enum "2" {
               description "Length is wrong";
             }
             enum "3" {
               description "Field value out of order or Reserved field non-zero";
             }
             enum "4" {
               description "Insufficient resources";
             }
             enum "5" {
               description "The Session ID is invalid";
             }
             enum "6" {
               description "Vendor-specific error";
             }
             enum "7" {
               description "Try another LNS destination";
             }
             enum "8" {
               description "Session or tunnel was shutdown";
             }
           }
         }
         uses apply-advanced;
       }
     }
     list address {
       key name;
       ordered-by user;
       leaf name {
         description "Address of remote system";
         type jt:ipv4addr;
       }
       container access-line-information {
         presence "enable access-line-information";
         description "Enable sending access-line attributes";
         uses apply-advanced;
         leaf connection-speed-update {
           description "Support connection speed updates";
           type empty;
         }
       }
       list routing-instance {
         key name;
         ordered-by user;
         description "Routing instance in which destination exists";
         leaf name {
           description "Routing instance in which destination exists";
           type string {
           }
         }
         leaf drain {
           description "Prevents creation of tunnels and sessions at destination";
           type empty;
         }
       }
       leaf drain {
         description "Prevents creation of tunnels and sessions at destination";
         type empty;
       }
     }
     list name {
       key name;
       ordered-by user;
       leaf name {
         description "Locally assigned name of the destination";
         type string {
           length "1 .. 63";
         }
       }
       leaf drain {
         description "Prevents tunnels and sessions at destination";
         type empty;
       }
     }
   }
   grouping l2tp_interface_traceoptions {
     leaf name {
       description "Name of Layer 2 Tunneling Protocol service interface";
       type union {
         type jt:interface-device;
         type string {
           pattern "<.*>|$.*";
         }
       }
     }
     uses apply-advanced;
     list flag {
       key name;
       ordered-by user;
       description "Tracing parameters";
       leaf name {
         type enumeration {
           enum "ipc" {
             description "Trace L2TP IPC messages between PIC and Routing Engine";
           }
           enum "protocol" {
             description "Trace L2TP, PPP, and multilink handling";
           }
           enum "packet-dump" {
             description "Dump each packet content based on debug level";
           }
           enum "system" {
             description "Trace packet processing on the PIC";
           }
           enum "all" {
             description "Trace everything";
           }
         }
       }
     }
     leaf debug-level {
       description "Trace level for PIC";
       default "error";
       type enumeration {
         enum "error" {
           description "Errors";
         }
         enum "detail" {
           description "Detailed debug information";
         }
         enum "extensive" {
           description "All PIC debug information";
         }
       }
     }
   }
   grouping l2tp_tunnel_group_object {
     leaf name {
       description "Name of Layer 2 Tunneling Protocol profile";
       type string {
         length "1 .. 63";
       }
     }
     uses apply-advanced;
     leaf l2tp-access-profile {
       description "Tunnel profile name";
       type string {
         length "1 .. 63";
       }
     }
     leaf ppp-access-profile {
       description "User profile name";
       type string {
         length "1 .. 63";
       }
     }
     leaf aaa-access-profile {
       description "AAA profile name";
       type string {
         length "1 .. 63";
       }
     }
     leaf receive-window {
       description "Maximum receive window size";
       default "16";
       units "bytes";
       type union {
         type uint16;
         type string {
           pattern "<.*>|$.*";
         }
       }
     }
     leaf maximum-send-window {
       description "Limits the other end receive window size";
       default "32";
       units "bytes";
       type union {
         type uint16;
         type string {
           pattern "<.*>|$.*";
         }
       }
     }
     leaf retransmit-interval {
       description "Retransmit interval";
       default "30";
       units "seconds";
       type union {
         type uint16;
         type string {
           pattern "<.*>|$.*";
         }
       }
     }
     leaf hello-interval {
       description "Hello interval for tunnel keepalive";
       default "60";
       units "seconds";
       type union {
         type string {
           pattern "<.*>|$.*";
         }
         type uint16 {
           range "0 .. 3600";
         }
       }
     }
     leaf hide-avps {
       description "Hide L2TP AVPs";
       type empty;
     }
     leaf no-tos-reflect {
       description "Disable ToS bit reflect onto outer L2TP header";
       type empty;
     }
     leaf tos-reflect {
       description "Enable ToS bit reflect onto outer L2TP header";
       type empty;
     }
     leaf tunnel-timeout {
       description "Time to tear down tunnel when a connection is lost";
       default "120";
       units "seconds";
       type union {
         type uint16;
         type string {
           pattern "<.*>|$.*";
         }
       }
     }
     container local-gateway {
       presence "enable local-gateway";
       uses apply-advanced;
       leaf address {
         description "L2TP network server IP address";
         type jt:ipv4addr;
       }
       leaf gateway-name {
         description "L2TP network server name for use with remote host";
         type string;
       }
     }
     choice anchor-points {
       case case_1 {
         leaf service-interface {
           description "Services interface to use";
           type string;
         }
       }
       case case_2 {
         leaf service-device-pool {
           description "Service interface pool name to use";
           type string {
             length "1 .. 63";
           }
         }
       }
     }
     leaf dynamic-profile {
       description " dynamic profile for interface to use";
       type string {
         length "1 .. 80";
       }
     }
     leaf tunnel-switch-profile {
       description "Tunnel switch profile name";
       type string {
         length "1 .. 63";
       }
     }
     container syslog {
       description "Define system logging parameters";
       uses log-object;
     }
     leaf maximum-sessions {
       description "Maximum number of sessions per tunnel-group";
       type union {
         type uint32;
         type string {
           pattern "<.*>|$.*";
         }
       }
     }
     leaf service-profile {
       description "Dynamic service profile(s) to be applied to this session";
       type string;
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping log-object {
     description "Configure security log";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
     list host {
       key name;
       ordered-by user;
       max-elements 10;
       leaf name {
         description "Name of host to notify";
         type string {
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           type jt:ipaddr;
         }
         leaf vrf-name {
           description "Routing instance name for tcp logging";
           type string;
         }
         leaf ssl-profile {
           description "SSL profile name for tcp logging";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
     leaf disable {
       description "Disable security logging for the device";
       type empty;
     }
     leaf utc-timestamp {
       description "Use UTC time for security log timestamps";
       type empty;
     }
     leaf mode {
       description "Controls how security logs are processed and exported";
       type enumeration {
         enum "stream" {
           description "Process security logs directly in the forwarding plane";
         }
         enum "event" {
           description "Process security logs in the control plane";
         }
         enum "stream-event" {
           description "Process security logs in both forwarding plane and control plane";
         }
       }
     }
     leaf event-rate {
       description "Control plane event rate";
       units "logs per second";
       type union {
         type string {
           pattern "<.*>|$.*";
         }
         type uint32 {
           range "0 .. 1500";
         }
       }
     }
     leaf format {
       description "Set security log format for the device";
       type enumeration {
         enum "syslog" {
           description "Traditional syslog";
         }
         enum "sd-syslog" {
           description "Structured syslog";
         }
         enum "binary" {
           description "Binary log";
         }
       }
     }
     leaf escape {
       description "Enable escape defined by RFC5424 for the sd and binary format logs";
       type empty;
     }
     container time-format {
       description "Configure year or millisecond for syslog";
       uses time-format-object;
     }
     leaf rate-cap {
       description "Data plane event rate";
       units "logs per second";
       type union {
         type string {
           pattern "<.*>|$.*";
         }
         type uint32 {
           range "0 .. 5000";
         }
       }
     }
     leaf max-database-record {
       description "Maximum records in database";
       default "0";
       type union {
         type string {
           pattern "<.*>|$.*";
         }
         type uint32;
       }
     }
     container report {
       presence "enable report";
       description "Set security log report settings";
       uses apply-advanced;
       leaf database-capacity {
         description "Total capacity of all the tables in database";
         type enumeration {
           enum "max-db-size" {
             description "Increases database size to 216M entries";
           }
         }
       }
       container logs-per-table {
         presence "enable logs-per-table";
         description "Log number per table in database";
         uses apply-advanced;
         leaf session-all {
           description "Log number of session";
           type union {
             type string {
               pattern "<.*>|$.*";
             }
             type uint32;
           }
         }
         leaf screen {
           description "Log number of screen";
           type union {
             type string {
               pattern "<.*>|$.*";
             }
             type uint32;
           }
         }
         leaf idp {
           description "Log number of idp";
           type union {
             type string {
               pattern "<.*>|$.*";
             }
             type uint32;
           }
         }
         leaf utm {
           description "Log number of utm";
           type union {
             type string {
               pattern "<.*>|$.*";
             }
             type uint32;
           }
         }
         leaf ipsec-vpn {
           description "Log number of ipsec-vpn";
           type union {
             type string {
               pattern "<.*>|$.*";
             }
             type uint32;
           }
         }
         leaf sky {
           description "Log number of sky";
           type union {
             type string {
               pattern "<.*>|$.*";
             }
             type uint32;
           }
         }
       }
       container log-share-per-table {
         presence "enable log-share-per-table";
         description "Log share(%) per table in database";
         uses apply-advanced;
         leaf session-all {
           description "Percentage share for session table (%)";
           type union {
             type string {
               pattern "<.*>|$.*";
             }
             type uint32;
           }
         }
         leaf screen {
           description "Percentage share for screen table (%)";
           type union {
             type string {
               pattern "<.*>|$.*";
             }
             type uint32;
           }
         }
         leaf idp {
           description "Percentage share for idp table (%)";
           type union {
             type string {
               pattern "<.*>|$.*";
             }
             type uint32;
           }
         }
         leaf utm {
           description "Percentage share for utm table (%)";
           type union {
             type string {
               pattern "<.*>|$.*";
             }
             type uint32;
           }
         }
         leaf ipsec-vpn {
           description "Percentage share for ipsec-vpn table (%)";
           type union {
             type string {
               pattern "<.*>|$.*";
             }
             type uint32;
           }
         }
         leaf atp {
           description "Percentage share for atp table (%)";
           type union {
             type string {
               pattern "<.*>|$.*";
             }
             type uint32;
           }
         }
         leaf dns {
           description "Percentage share for dns table (%)";
           type union {
             type string {
               pattern "<.*>|$.*";
             }
             type uint32;
           }
         }
       }
       leaf table-lifetime {
         description "Table lifetime day(s)";
         default "90";
         type union {
           type string {
             pattern "<.*>|$.*";
           }
           type uint32 {
             range "0 .. 365";
           }
         }
       }
       leaf table-mode {
         description "Report table mode";
         type enumeration {
           enum "dense" {
             description "Enable dense mode(B-Tree)";
           }
           enum "disabl-dense" {
             description "Disable dense mode(Moving to R-Tree)";
           }
         }
       }
       container database-filter {
         presence "enable database-filter";
         description "Check the logs whether should be inserted into database";
         uses apply-advanced;
         list event-category {
           key name;
           ordered-by user;
           description "Filter by event-category";
           leaf name {
             description "Name";
             type enumeration {
               enum "session" {
                 description "Session log";
               }
               enum "screen" {
                 description "Screen log";
               }
               enum "idp" {
                 description "IDP log";
               }
               enum "webfilter" {
                 description "Webfilter log";
               }
               enum "content-filter" {
                 description "Content-filter log";
               }
               enum "anti-virus" {
                 description "Antivirus log";
               }
               enum "anti-spam" {
                 description "Anti-spam log";
               }
               enum "ipsec" {
                 description "IPsec VPN log";
               }
               enum "sky" {
                 description "Sky ATP log";
               }
               enum "secintel" {
                 description "Secintel log";
               }
               enum "icap" {
                 description "ICAP log";
               }
               enum "ssl-proxy" {
                 description "SSL proxy log";
               }
               enum "dnsf" {
                 description "DNSF log";
               }
               enum "dns" {
                 description "Dns log";
               }
               enum "session-create" {
                 description "Session create log";
               }
               enum "session-close" {
                 description "Session close log";
               }
               enum "session-deny" {
                 description "Session deny log";
               }
             }
           }
           uses apply-advanced;
         }
         leaf exclude {
           description "Exclude the logs";
           type empty;
         }
       }
     }
     choice source {
       case case_1 {
         leaf source-address {
           description "Source ip address used when exporting security logs";
           type jt:ipaddr;
         }
       }
       case case_2 {
         leaf source-interface {
           description "Source interface used when exporting security logs";
           type union {
             type jt:interface-name;
             type string {
               pattern "<.*>|$.*";
             }
           }
         }
       }
     }
     container transport {
       presence "enable transport";
       description "Set security log transport settings";
       uses apply-advanced;
       leaf tcp-connections {
         description "Set tcp connection number per-stream";
         type union {
           type string {
             pattern "<.*>|$.*";
           }
           type uint32 {
             range "1 .. 5";
           }
         }
       }
       leaf protocol {
         description "Set security log transport protocol for the device";
         type enumeration {
           enum "udp" {
             description "UDP transfer for log";
           }
           enum "tcp" {
             description "TCP transfer for log";
           }
           enum "tls" {
             description "TLS transfer for log";
           }
         }
       }
       leaf tls-profile {
         description "TLS profile";
         type string;
       }
     }
     leaf facility-override {
       description "Alternate facility for logging to remote host";
       type enumeration {
         enum "authorization" {
           description "Authorization system";
         }
         enum "daemon" {
           description "Various system processes";
         }
         enum "ftp" {
           description "FTP process";
         }
         enum "kernel" {
           description "Kernel";
         }
         enum "user" {
           description "User processes";
         }
         enum "local0" {
           description "Local logging option number 0";
         }
         enum "local1" {
           description "Local logging option number 1";
         }
         enum "local2" {
           description "Local logging option number 2";
         }
         enum "local3" {
           description "Local logging option number 3";
         }
         enum "local4" {
           description "Local logging option number 4";
         }
         enum "local5" {
           description "Local logging option number 5";
         }
         enum "local6" {
           description "Local logging option number 6";
         }
         enum "local7" {
           description "Local logging option number 7";
         }
       }
     }
     leaf local-log-tag {
       description "Tag included in logs";
       type string {
       }
     }
     list local-category {
       key name;
       ordered-by user;
       description "Selects the type of events that may be logged locally";
       leaf name {
         type enumeration {
           enum "all" {
             description "All events are logged";
           }
           enum "content-security" {
             description "Content security events are logged";
           }
           enum "fw-auth" {
             description "Fw-auth events are logged";
           }
           enum "screen" {
             description "Screen events are logged";
           }
           enum "alg" {
             description "Alg events are logged";
           }
           enum "nat" {
             description "Nat events are logged";
           }
           enum "flow" {
             description "Flow events are logged";
           }
           enum "sctp" {
             description "Sctp events are logged";
           }
           enum "gtp" {
             description "Gtp events are logged";
           }
           enum "ipsec" {
             description "Ipsec events are logged";
           }
           enum "idp" {
             description "Idp events are logged";
           }
           enum "rtlog" {
             description "Rtlog events are logged";
           }
           enum "pst-ds-lite" {
             description "Pst-ds-lite events are logged";
           }
           enum "appqos" {
             description "Appqos events are logged";
           }
           enum "secintel" {
             description "Secintel events are logged";
           }
           enum "aamw" {
             description "AAMW events are logged";
           }
           enum "sfw" {
             description "Stateful Firewall events are logged";
           }
           enum "session" {
             description "Session open and close events are logged";
           }
           enum "session-open" {
             description "Session open events are logged";
           }
           enum "session-close" {
             description "Session close events are logged";
           }
           enum "urlf" {
             description "URLF events are logged";
           }
           enum "ha" {
             description "Stateful High-Availability open and close events are logged";
           }
           enum "ha-open" {
             description "Stateful High-Availability open events are logged";
           }
           enum "ha-close" {
             description "Stateful High-Availability close events are logged";
           }
           enum "pcp" {
             description "PCP logs";
           }
           enum "dnsf" {
             description "DNSF";
           }
           enum "dns" {
             description "DNS";
           }
         }
       }
       uses apply-advanced;
     }
     leaf root-streaming {
       description "Logs will be streamed from the Root LSYS";
       type empty;
     }
     list stream {
       key name;
       ordered-by user;
       description "Set security log stream settings";
       max-elements 8;
       leaf name {
         description "Name of security log stream";
         type string {
           length "1 .. 63";
         }
       }
       uses apply-advanced;
       leaf severity {
         description "Severity threshold for security logs";
         type enumeration {
           enum "emergency" {
             description "Conditions that cause security functions to stop";
           }
           enum "alert" {
             description "Conditions that require immediate attention";
           }
           enum "critical" {
             description "Critical conditions";
           }
           enum "error" {
             description "General error conditions";
           }
           enum "warning" {
             description "General warning conditions";
           }
           enum "notice" {
             description "Non-error conditions that are of interest";
           }
           enum "info" {
             description "Information about normal security operations";
           }
           enum "debug" {
             description "Information normally used in debugging";
           }
         }
       }
       leaf format {
         description "Specify the log stream format";
         type enumeration {
           enum "syslog" {
             description "Traditional syslog";
           }
           enum "sd-syslog" {
             description "Structured syslog";
           }
           enum "welf" {
             description "Web Trends Extended Log Format";
           }
           enum "binary" {
             description "Binary log";
           }
         }
       }
       list category {
         key name;
         ordered-by user;
         description "Selects the type of events that may be logged";
         leaf name {
           type enumeration {
             enum "all" {
               description "All events are logged";
             }
             enum "content-security" {
               description "Content security events are logged";
             }
             enum "fw-auth" {
               description "Fw-auth events are logged";
             }
             enum "screen" {
               description "Screen events are logged";
             }
             enum "alg" {
               description "Alg events are logged";
             }
             enum "nat" {
               description "Nat events are logged";
             }
             enum "flow" {
               description "Flow events are logged";
             }
             enum "sctp" {
               description "Sctp events are logged";
             }
             enum "gtp" {
               description "Gtp events are logged";
             }
             enum "ipsec" {
               description "Ipsec events are logged";
             }
             enum "idp" {
               description "Idp events are logged";
             }
             enum "rtlog" {
               description "Rtlog events are logged";
             }
             enum "pst-ds-lite" {
               description "Pst-ds-lite events are logged";
             }
             enum "appqos" {
               description "Appqos events are logged";
             }
             enum "secintel" {
               description "Secintel events are logged";
             }
             enum "aamw" {
               description "AAMW events are logged";
             }
             enum "sfw" {
               description "Stateful Firewall events are logged";
             }
             enum "session" {
               description "Session open and close events are logged";
             }
             enum "session-open" {
               description "Session open events are logged";
             }
             enum "session-close" {
               description "Session close events are logged";
             }
             enum "urlf" {
               description "URLF events are logged";
             }
             enum "ha" {
               description "Stateful High-Availability open and close events are logged";
             }
             enum "ha-open" {
               description "Stateful High-Availability open events are logged";
             }
             enum "ha-close" {
               description "Stateful High-Availability close events are logged";
             }
             enum "pcp" {
               description "PCP logs";
             }
             enum "dnsf" {
               description "DNSF";
             }
             enum "dns" {
               description "DNS";
             }
           }
         }
         uses apply-advanced;
       }
       list filter {
         key name;
         ordered-by user;
         description "Selects the filter to filter the logs to be logged";
         leaf name {
           type enumeration {
             enum "threat-attack" {
               description "Threat-attack security events are logged";
             }
           }
         }
         uses apply-advanced;
       }
       container host {
         description "Destination to send security logs to";
         uses host-object;
       }
       container rate-limit {
         description "Rate-limit for security logs";
         uses apply-advanced;
         leaf rate {
           description "Log rate";
           units "logs per second";
           type union {
             type string {
               pattern "<.*>|$.*";
             }
             type uint32 {
               range "1 .. 65535";
             }
           }
         }
       }
       container file {
         description "Security log file options for logs in local file";
         uses apply-advanced;
         leaf localfilename {
           description "Name of local log file";
           type string {
             length "1 .. 256";
           }
         }
         leaf size {
           description "Maximum size of local log file in megabytes";
           type union {
             type string {
               pattern "<.*>|$.*";
             }
             type uint32;
           }
         }
         leaf rotation {
           description "Maximum number of rotate files";
           default "10";
           type union {
             type string {
               pattern "<.*>|$.*";
             }
             type uint32;
           }
         }
         leaf allow-duplicates {
           description "To disable log consolidation";
           type empty;
         }
       }
       container transport {
         presence "enable transport";
         description "Set security log transport settings";
         uses apply-advanced;
         leaf tcp-connections {
           description "Set tcp connection number per-stream";
           type union {
             type string {
               pattern "<.*>|$.*";
             }
             type uint32 {
               range "1 .. 5";
             }
           }
         }
         leaf protocol {
           description "Set security log transport protocol for the device";
           type enumeration {
             enum "udp" {
               description "UDP transfer for log";
             }
             enum "tcp" {
               description "TCP transfer for log";
             }
             enum "tls" {
               description "TLS transfer for log";
             }
           }
         }
         leaf tls-profile {
           description "TLS profile";
           type string;
         }
       }
       container time-format {
         description "Configure year or millisecond for syslog";
         uses time-format-object;
       }
       leaf source-address {
         description "Source ip address used when exporting security logs";
         type jt:ipaddr;
       }
     }
     container file {
       description "Security log file options for logs in binary/protobuf format";
       uses apply-advanced;
       leaf filename {
         description "Name of log file";
         type string {
           length "1 .. 256";
         }
       }
       leaf size {
         description "Maximum size of log file in megabytes";
         type union {
           type string {
             pattern "<.*>|$.*";
           }
           type uint32 {
             range "1 .. 10";
           }
         }
       }
       leaf path {
         description "Path to log files";
         type string {
           length "1 .. 256";
         }
       }
       leaf files {
         description "Maximum number of log files";
         type union {
           type string {
             pattern "<.*>|$.*";
           }
           type uint32 {
             range "2 .. 10";
           }
         }
       }
     }
     container apply {
       description "Apply settings from other features";
       uses apply-advanced;
       leaf dscp-code-point {
         description "Apply setting class-of-service host-outbound-traffic dscp-code-point";
         type empty;
       }
     }
     container traceoptions {
       description "Security log daemon trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "List of things to include in trace";
         leaf name {
           type enumeration {
             enum "source" {
               description "Communication with security log forwarder";
             }
             enum "configuration" {
               description "Reading of configuration";
             }
             enum "all" {
               description "Everything";
             }
             enum "report" {
               description "Trace report";
             }
             enum "hpl" {
               description "Trace HPL logging";
             }
           }
         }
       }
     }
     list profile {
       key name;
       ordered-by user;
       description "Security log profile setting";
       max-elements 10;
       leaf name {
         description "Name of security log profile";
         type string {
           length "1 .. 63";
         }
       }
       uses apply-advanced;
       list stream-name {
         key name;
         ordered-by user;
         description "Use which stream ";
         max-elements 4;
         leaf name {
           description "Name of the stream";
           type string;
         }
         uses apply-advanced;
       }
       container category {
         presence "enable category";
         description "Selects the category of events for the profile";
         uses apply-advanced;
         container session {
           presence "enable session";
           description "Select session category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container webfilter {
           presence "enable webfilter";
           description "Select webfilter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antivirus {
           presence "enable antivirus";
           description "Select antivirus category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container content-filter {
           presence "enable content-filter";
           description "Select content-filter category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container antispam {
           presence "enable antispam";
           description "Select antispam category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container idp {
           presence "enable idp";
           description "Select idp category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container secintel {
           presence "enable secintel";
           description "Select secintel category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container aamw {
           presence "enable aamw";
           description "Select aamw category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container ssl-proxy {
           presence "enable ssl-proxy";
           description "Select ssl-proxy category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
         container apptrack {
           presence "enable apptrack";
           description "Select apptrack category";
           uses apply-advanced;
           list field-extra-name {
             key name;
             description "Select the extra Fields, only apply to sd-syslog and syslog formt";
             leaf name {
               description "The name of the extra field";
               type enumeration {
                 enum "sd-id" {
                   description "Add SD-ID field, only apply to sd-syslog and syslog formt";
                 }
                 enum "hostname" {
                   description "Add hostname field, only apply to sd-syslog and syslog formt";
                 }
                 enum "timestamp" {
                   description "Add timestamp field, only apply to sd-syslog and syslog formt";
                 }
               }
             }
             uses apply-advanced;
           }
           list field-name {
             key name;
             ordered-by user;
             description "Select the fields by order";
             leaf name {
               description "The name of the field";
               type string;
             }
             uses apply-advanced;
           }
         }
       }
       container default-profile {
         presence "enable default-profile";
         uses apply-advanced;
         leaf activate {
           description "Set this profile as default profile";
           type empty;
         }
       }
       container template {
         presence "enable template";
         description "Select the template for the profile";
         uses apply-advanced;
         choice template-id {
           case case_1 {
             leaf traditional-firewall {
               description "Traditional-firewall";
               type empty;
             }
           }
           case case_2 {
             leaf unified-ngfw {
               description "Unified-ngfw";
               type empty;
             }
           }
           case case_3 {
             leaf sd-wan {
               description "Sd-wan";
               type empty;
             }
           }
         }
       }
     }
   }
   grouping host-object {
     uses apply-advanced;
     leaf ipaddr {
       description "IP address/Host name";
       type string {
         length "1 .. 256";
       }
     }
     leaf port {
       description "Host port number";
       type union {
         type uint16;
         type string {
           pattern "<.*>|$.*";
         }
       }
     }
     leaf routing-instance {
       description "Routing-instance name";
       type string;
     }
     leaf log-tag {
       description "Tag included in logs to this host";
       type string {
       }
     }
   }
   grouping lrf-profile-object {
     leaf name {
       description "Name of profile";
       type string {
         length "1 .. 63";
       }
     }
     uses apply-advanced;
     leaf policy-based-logging {
       description "Set rule based on policy";
       type empty;
     }
     leaf http-log-multiple-transactions {
       description "Log http multiple transactions";
       type empty;
     }
     list rule {
       key name;
       ordered-by user;
       description "One or more LRF rules";
       max-elements 32;
       uses lrf_rule_object;
     }
     list collector {
       key name;
       ordered-by user;
       description "One or more LRF collectors";
       max-elements 8;
       uses lrf_collector_object;
     }
     leaf-list vendor-support {
       ordered-by user;
       description "LRF 3rd party vendor support sub-template";
       type enumeration {
         enum "ibm" {
           description "IBM supported sub-template";
         }
       }
     }
     list template {
       key name;
       ordered-by user;
       description "LRF template";
       max-elements 16;
       uses lrf-template-object;
     }
     container performance-mode {
       description "Enable performance mode knob for LRF performance";
       uses lrf_perf_object;
     }
   }
   grouping lrf-template-object {
     leaf name {
       description "Name of template";
       type string {
         length "1 .. 32";
       }
     }
     uses apply-advanced;
     leaf format {
       description "Template format";
       type enumeration {
         enum "ipfix" {
           description "IPFIX template";
         }
       }
     }
     leaf-list template-type {
       ordered-by user;
       description "Template type";
       type enumeration {
         enum "ipv4" {
           description "IPv4 type";
         }
         enum "ipv4-extended" {
           description "IPv4 Extended type";
         }
         enum "ipv6" {
           description "IPv6 type";
         }
         enum "ipv6-extended" {
           description "IPv6 Extended type";
         }
         enum "transport-layer" {
           description "Transport Layer type";
         }
         enum "flow-id" {
           description "Flow ID type";
         }
         enum "ipflow" {
           description "IPFlow type";
         }
         enum "ipflow-ts" {
           description "IPFlow TS type";
         }
         enum "ipflow-extended" {
           description "IPFlow Extended type";
         }
         enum "device-data" {
           description "Device Data type";
         }
         enum "l7-app" {
           description "L7 APP type";
         }
         enum "http" {
           description "HTTP type";
         }
         enum "subscriber-data" {
           description "Subscriber data type";
         }
         enum "mobile-subscriber" {
           description "Mobile subscriber type";
         }
         enum "ifl-subscriber" {
           description "IFL based subscriber type";
         }
         enum "wireline-subscriber" {
           description "Wireline subscriber type";
         }
         enum "ipflow-tcp-ts" {
           description "IPFlow TCP TS type (IBM specific)";
         }
         enum "ipflow-tcp" {
           description "IPFlow TCP type";
         }
         enum "video" {
           description "Video fields type";
         }
         enum "dns" {
           description "DNS fields type";
         }
         enum "status-code-distribution" {
           description "Status code distribution for HTTP and DNS";
         }
         enum "pcc" {
           description "PCC type";
         }
       }
     }
     leaf-list trigger-type {
       ordered-by user;
       description "Trigger type";
       type enumeration {
         enum "session-close" {
           description "Session close trigger";
         }
         enum "volume" {
           description "Volume trigger";
         }
         enum "time" {
           description "Time limit trigger";
         }
       }
     }
     leaf template-tx-interval {
       description "Template export interval";
       default "60";
       units "seconds";
       type union {
         type string {
           pattern "<.*>|$.*";
         }
         type uint32 {
           range "10 .. 600";
         }
       }
     }
   }
   grouping lrf_collector_object {
     leaf name {
       description "Name of collector";
       type string {
         length "1 .. 32";
       }
     }
     uses apply-advanced;
     container destination {
       presence "enable destination";
       description "Destination collector configuration";
       uses apply-advanced;
       leaf address {
         description "Destination IPv4 address of collector";
         type jt:ipv4addr;
       }
       leaf port {
         description "Destination port of collector";
         type union {
           type uint16;
           type string {
             pattern "<.*>|$.*";
           }
         }
       }
     }
     leaf source-address {
       description "Source address to be used in the export packets";
       type jt:ipv4addr;
     }
   }
   grouping lrf_perf_object {
     uses apply-advanced;
     leaf packet-count {
       description "Max packet inspection threshold including both c2s and s2c direction packets ";
       default "20";
       type union {
         type string {
           pattern "<.*>|$.*";
         }
         type uint32 {
           range "20 .. 1000";
         }
       }
     }
   }
   grouping lrf_rule_object {
     leaf name {
       description "Name of rule";
       type string {
         length "1 .. 63";
       }
     }
     uses apply-advanced;
     leaf match-direction {
       description "Match direction";
       default "both";
       type enumeration {
         enum "client-to-server" {
           description "Client to server";
         }
         enum "server-to-client" {
           description "Server to client";
         }
         enum "both" {
           description "Both client-to-server and server-to-client";
         }
       }
     }
     container from {
       description "Match criteria";
       presence "enable from";
       uses lrf_match_object;
     }
     container then {
       description "Action to take for matched condition";
       uses apply-advanced;
       container report {
         description "Report action";
         presence "enable report";
         uses lrf_report_object;
       }
     }
   }
   grouping lrf_match_object {
     uses apply-advanced;
     list source-prefix-list {
       key name;
       ordered-by user;
       description "One or more named lists of source prefixes to match";
       leaf name {
         description "Name of prefix list to match against";
         type string;
       }
       leaf except {
         description "Name of prefix list not to match against";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list source-ports {
       ordered-by user;
       description "Source port list specification";
       type union {
         type string {
           pattern "<.*>|$.*";
         }
         type uint32 {
           range "0 .. 65535";
         }
       }
     }
     leaf-list destination-ports {
       ordered-by user;
       description "Destination port list specification";
       type union {
         type string {
           pattern "<.*>|$.*";
         }
         type uint32 {
           range "0 .. 65535";
         }
       }
     }
     leaf app-unknown {
       description "Use to specify unknown application as the match criteria";
       type empty;
     }
     list application-names {
       key name;
       ordered-by user;
       description "Match one or more applications";
       leaf name {
         description "Name of application";
         type string {
           length "1 .. 63";
         }
       }
       uses apply-advanced;
     }
     list application-groups {
       key name;
       ordered-by user;
       description "Match one or more application groups";
       leaf name {
         description "Name of application group";
         type string {
           length "1 .. 63";
         }
       }
       uses apply-advanced;
     }
   }
   grouping lrf_report_object {
     uses apply-advanced;
     leaf volume-limit {
       description "Volume limit";
       units "megabytes";
       type union {
         type string {
           pattern "<.*>|$.*";
         }
         type uint16 {
           range "1 .. 1024";
         }
       }
     }
     leaf time-limit {
       description "Time limit";
       default "300";
       units "seconds";
       type union {
         type string {
           pattern "<.*>|$.*";
         }
         type uint32 {
           range "60 .. 1800";
         }
       }
     }
     leaf template {
       description "Template to be used for export";
       type string;
     }
     leaf-list collector {
       ordered-by user;
       description "List of collectors that receive the export packets";
       type string {
         length "1 .. 63";
       }
       max-elements 3;
     }
   }
   grouping macro-data-type {
     leaf name {
       description "Keyword part of the keyword-value pair";
       type string;
     }
     leaf value {
       description "Value part of the keyword-value pair";
       type string;
     }
   }
   grouping mape_object {
     leaf name {
       description "MAP-E softwire concentrator name";
       type string {
         length "1 .. 63";
       }
     }
     uses apply-advanced;
     leaf softwire-address {
       description "Softwire concentrator IPV6 Address";
       type jt:ipv6addr;
     }
     leaf ipv4-prefix {
       description "MAP-E domains's rule IPv4 prefix/len";
       type jt:ipv4prefix;
     }
     leaf mape-prefix {
       description "MAP-E domain's rule IPV6 prefix/len";
       type jt:ipv6prefix;
     }
     leaf ea-bits-len {
       description "MAP-E domain's rule EA (Embedded Address) len";
       type union {
         type string {
           pattern "<.*>|$.*";
         }
         type uint32 {
           range "0 .. 48";
         }
       }
     }
     leaf psid-offset {
       description "MAP-E domain's PSID offset";
       default "4";
       type union {
         type string {
           pattern "<.*>|$.*";
         }
         type uint32 {
           range "0 .. 16";
         }
       }
     }
     leaf psid-length {
       description "MAP-E domain's PSID length";
       type union {
         type string {
           pattern "<.*>|$.*";
         }
         type uint32 {
           range "0 .. 16";
         }
       }
     }
     leaf mtu-v6 {
       description "MTU for the MAP-E softwire tunnel";
       default "9192";
       type union {
         type string {
           pattern "<.*>|$.*";
         }
         type int32 {
           range "1280 .. 9192";
         }
       }
     }
     leaf version-03 {
       description "MAP-E map-03 support";
       type empty;
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
     leaf v4-partial-reassembly {
       description "For higher number of fragments/reassembled packet size";
       type empty;
     }
   }
   grouping mapt_object {
     leaf name {
       description "MAP-T softwire concentrator name";
       type string {
         length "1 .. 63";
       }
     }
     uses apply-advanced;
     leaf dmr-prefix {
       description "Softwire DMR IPV6 Address";
       type jt:ipv6prefix;
     }
     leaf ipv4-prefix {
       description "MAP-T domains's rule IPv4 prefix/len";
       type jt:ipv4prefix;
     }
     leaf mapt-prefix {
       description "MAP-T domain's rule IPV6 prefix/len";
       type jt:ipv6prefix;
     }
     leaf ea-bits-len {
       description "MAP-T domain's rule EA (Embedded Address) len";
       type union {
         type string {
           pattern "<.*>|$.*";
         }
         type uint8 {
           range "0 .. 48";
         }
       }
     }
     leaf psid-offset {
       description "MAP-T domain's PSID offset";
       default "4";
       type union {
         type string {
           pattern "<.*>|$.*";
         }
         type uint8 {
           range "0 .. 16";
         }
       }
     }
     leaf psid-length {
       description "MAP-T domain's PSID length";
       type union {
         type string {
           pattern "<.*>|$.*";
         }
         type uint8 {
           range "0 .. 16";
         }
       }
     }
     leaf mtu-v6 {
       description "MTU for the MAP-T softwire tunnel";
       default "9192";
       type union {
         type string {
           pattern "<.*>|$.*";
         }
         type uint16 {
           range "1280 .. 9192";
         }
       }
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping name-resolution-cache-type {
     description "Configuration of DNS responses cache";
     uses apply-advanced;
     container maximum-time-in-cache {
       presence "enable maximum-time-in-cache";
       description "Maximum time a DNS response may be held in the cache";
       choice maximum-time-in-cache {
         case case_1 {
           leaf unlimited {
             description "Cache according to TTL";
             type empty;
           }
         }
         case case_2 {
           leaf time {
             description "Seconds";
             type union {
               type string {
                 pattern "<.*>|$.*";
               }
               type uint32 {
                 range "0 .. 604800";
               }
             }
           }
         }
       }
     }
     leaf maximum-records-in-cache {
       description "Maximum number of DNS responses that may be held in the cache";
       default "5000";
       type union {
         type string {
           pattern "<.*>|$.*";
         }
         type uint32 {
           range "0 .. 50000";
         }
       }
     }
     leaf blacklist-period {
       description "Time (in seconds) a record will be held in the blacklist";
       default "600";
       type union {
         type string {
           pattern "<.*>|$.*";
         }
         type uint32 {
           range "0 .. 86400";
         }
       }
     }
     container accelerations {
       presence "enable accelerations";
       description "Mechanisms for accelerating DNS resolving";
       uses apply-advanced;
       leaf no-refresh-before-ttl-expiry {
         description "Don't send a new query for records that are about to expire";
         type empty;
       }
       leaf initiate-next-queries {
         description "Immediately initiate queries for referenced entries (e.g A entries referenced from SRV ones)";
         type empty;
       }
       leaf initiate-alternative-queries {
         description "Initiate NAPTR, SRV and A record queries, in parallel, for every new SIP URI";
         type empty;
       }
     }
   }
   grouping named-address-book-type {
     description "Configure global address book";
     leaf name {
       description "Address book name";
       type string;
     }
     uses apply-advanced;
     leaf description {
       description "Text description of address book";
       type string {
         length "1 .. 900";
       }
     }
     list address {
       key name;
       ordered-by user;
       description "Define a security address";
       uses address_type;
     }
     list address-set {
       key name;
       ordered-by user;
       description "Define a security address set";
       uses address_set_type;
     }
     container attach {
       description "Attach this address book to interface, zone or routing-instance";
       uses apply-advanced;
       list zone {
         key name;
         ordered-by user;
         description "Define a zone to be attached";
         leaf name {
           description "Security zone name";
           type string {
             length "1 .. 63";
           }
         }
         uses apply-advanced;
       }
     }
   }
   grouping address_set_type {
     leaf name {
       description "Security address-set name";
       type string {
         length "1 .. 63";
       }
     }
     uses apply-advanced;
     leaf description {
       description "Text description of address set";
       type string {
         length "1 .. 900";
       }
     }
     list address {
       key name;
       ordered-by user;
       description "Address to be included in this set";
       max-elements 16384;
       leaf name {
         description "Security address name";
         type string {
           length "1 .. 63";
         }
       }
       uses apply-advanced;
     }
     list address-set {
       key name;
       ordered-by user;
       description "Define an address-set name";
       max-elements 16384;
       leaf name {
         type string {
           length "1 .. 63";
         }
       }
       uses apply-advanced;
     }
   }
   grouping address_type {
     leaf name {
       description "Security address name";
       type string {
         length "1 .. 63";
       }
     }
     uses apply-advanced;
     leaf description {
       description "Text description of address";
       type string {
         length "1 .. 900";
       }
     }
     choice address-content {
       case case_1 {
         leaf ip-prefix {
           description "Numeric IPv4 or IPv6 address with prefix";
           type jt:ipprefix;
         }
       }
       case case_2 {
         list dns-name {
           key name;
           ordered-by user;
           description "DNS address name";
           max-elements 1;
           uses dns-name-type;
         }
       }
       case case_3 {
         list wildcard-address {
           key name;
           ordered-by user;
           description "Numeric IPv4 wildcard address with in the form of a.d.d.r/netmask";
           max-elements 1;
           uses wildcard-address-type;
         }
       }
       case case_4 {
         list range-address {
           key name;
           ordered-by user;
           description "Address range";
           max-elements 1;
           uses range-address-type;
         }
       }
       case case_5 {
         list address-range {
           key name;
           ordered-by user;
           description "Address range";
           max-elements 1;
           uses usf-range-address-type;
         }
       }
     }
   }
   grouping dns-name-type {
     description "DNS address name";
     leaf name {
       description "Fully qualified hostname";
       type string {
         length "1 .. 253";
       }
     }
     uses apply-advanced;
     leaf ipv4-only {
       description "IPv4 dns address";
       type empty;
     }
     leaf ipv6-only {
       description "IPv6 dns address";
       type empty;
     }
     leaf dns-query-interval {
       description "DNS Address query Interval";
       default "300";
       type union {
         type string {
           pattern "<.*>|$.*";
         }
         type uint32 {
           range "16 .. 86400";
         }
       }
     }
   }
   grouping nat-object {
     description "Configure Network Address Translation";
     uses apply-advanced;
     container source {
       description "Configure Source NAT";
       uses ssg-source-nat-object;
     }
     container destination {
       description "Configure Destination NAT";
       uses ssg-destination-nat-object;
     }
     container static {
       description "Configure Static NAT";
       uses ssg-static-nat-object;
     }
     container proxy-arp {
       description "Configure Proxy ARP";
       uses ssg-proxy-arp-object;
     }
     container proxy-ndp {
       description "Configure Proxy NDP";
       uses ssg-proxy-ndp-object;
     }
     container natv6v4 {
       description "Configure NAT between IPv6 and IPv4 options";
       uses apply-advanced;
       leaf no-v6-frag-header {
         description "V6 packet does not always add fragment header when performing nat translation from v4 side to v6 side ";
         type empty;
       }
     }
     leaf allow-overlapping-pools {
       description "IP addresses of NAT pools can overlap with other pool";
       type empty;
     }
     container traceoptions {
       description "NAT trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "routing-socket" {
               description "Trace routing socket events";
             }
             enum "routing-protocol" {
               description "Trace routing protocol events";
             }
             enum "all" {
               description "Trace everything";
             }
             enum "source-nat-re" {
               description "Trace source nat events on RE side";
             }
             enum "source-nat-rt" {
               description "Trace source nat events on PFE-RT side";
             }
             enum "source-nat-pfe" {
               description "Trace source nat events on PFE-ukernel side";
             }
             enum "destination-nat-re" {
               description "Trace destination nat events on RE side";
             }
             enum "destination-nat-rt" {
               description "Trace destination nat events on PFE-RT side";
             }
             enum "destination-nat-pfe" {
               description "Trace destination nat events on PFE-ukernel side";
             }
             enum "static-nat-re" {
               description "Trace static nat events on RE side";
             }
             enum "static-nat-rt" {
               description "Trace static nat events on PFE-RT side";
             }
             enum "static-nat-pfe" {
               description "Trace static nat events on PFE-ukernel side";
             }
             enum "nat-svc-set-re" {
               description "Trace NAT and svc-set events on RE side";
             }
           }
         }
         leaf syslog {
           description "Write NAT flow traces to system log also";
           type empty;
         }
       }
     }
     list pool {
       key name;
       ordered-by user;
       description "Define a NAT pool";
       uses nat_pool_object;
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     leaf allow-overlapping-nat-pools {
       description "Allow usage of overlapping and same nat pools in multiple service sets";
       type empty;
     }
     list rule {
       key name;
       ordered-by user;
       description "Define a NAT rule";
       uses nat_rule_object;
     }
     list port-forwarding {
       key name;
       ordered-by user;
       description "Define a port-forwarding pool";
       uses pf_mapping;
     }
     list rule-set {
       key name;
       ordered-by user;
       description "Defines a set of NAT rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping nat_pool_object {
     leaf name {
       description "Pool name";
       type string {
         length "1 .. 63";
       }
     }
     uses apply-advanced;
     container pgcp {
       presence "enable pgcp";
       description "NAT pool should be used exclusive by the pgcp service";
       uses apply-advanced;
       leaf remotely-controlled {
         description "Remotely controlled NAT pool allocation";
         type empty;
       }
       leaf ports-per-session {
         description "Number of ports to allocate in each call setup";
         default "2";
         type union {
           type uint8;
           type string {
             pattern "<.*>|$.*";
           }
         }
       }
       list hint {
         key name;
         ordered-by user;
         description "NAT-hint list (Any string available up to 3 characters, not mandatory field)";
         max-elements 5;
         uses nat_pgcp_hint_list_object;
       }
       leaf-list transport {
         ordered-by user;
         description "NAT pool transport types list";
         type enumeration {
           enum "tcp" {
             description "TCP";
           }
           enum "udp" {
             description "UDP";
           }
           enum "rtp-avp" {
             description "RTP/AVP";
           }
         }
       }
     }
     list address {
       key name;
       ordered-by user;
       description "Address or address prefix for NAT";
       leaf name {
         type jt:ipprefix-only;
       }
       uses apply-advanced;
     }
     container interface {
       description "Interface for nat pool";
       leaf interface-name {
         type union {
           type jt:interface-unit;
           type string {
             pattern "<.*>|$.*";
           }
         }
       }
     }
     leaf address-overload {
       description "Nat pool address overload with JunOS";
       type empty;
     }
     list address-range {
       key "low high";
       ordered-by user;
       description "Range of addresses for NAT";
       leaf low {
         description "Lower limit of address range";
         type jt:ipaddr;
       }
       leaf high {
         description "Upper limit of address range";
         type jt:ipaddr;
       }
     }
     container port {
       description "Specify ports for NAT";
       uses apply-advanced;
       choice port_choice {
         case case_1 {
           container automatic {
             presence "enable automatic";
             uses apply-advanced;
             choice automatic_choice {
               case case_1 {
                 leaf auto {
                   description "Automatically choose ports";
                   status deprecated;
                   type empty;
                 }
               }
               case case_2 {
                 leaf sequential {
                   description "Allocate ports in sequence";
                   type empty;
                 }
               }
               case case_3 {
                 leaf random-allocation {
                   description "Allocate ports randomly";
                   type empty;
                 }
               }
             }
           }
         }
         case case_2 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
             leaf random-allocation {
               description "Allocate ports randomly";
               type empty;
             }
           }
         }
       }
       choice block-allocation-choice {
         case case_1 {
           container secured-port-block-allocation {
             presence "enable secured-port-block-allocation";
             description "Secured Port block allocation";
             leaf block-size {
               description "Number of port per block.";
               default "128";
               type union {
                 type string {
                   pattern "<.*>|$.*";
                 }
                 type uint16 {
                   range "1 .. 64512";
                 }
               }
             }
             leaf max-blocks-per-address {
               description "Max block per address";
               default "8";
               type union {
                 type string {
                   pattern "<.*>|$.*";
                 }
                 type uint16 {
                   range "1 .. 512";
                 }
               }
             }
             leaf active-block-timeout {
               description "Active block timeout";
               default "120";
               type union {
                 type string {
                   pattern "<.*>|$.*";
                 }
                 type uint32 {
                   range "0 .. 86400";
                 }
               }
             }
           }
         }
         case case_2 {
           container deterministic-port-block-allocation {
             presence "enable deterministic-port-block-allocation";
             description "Deterministic Port Block Allocation";
             leaf block-size {
               description "Number of ports per block";
               default "512";
               type union {
                 type string {
                   pattern "<.*>|$.*";
                 }
                 type uint16 {
                   range "0 .. 64512";
                 }
               }
             }
             leaf include-boundary-addresses {
               description "Include network and broadcast in 'from' src-addresses";
               type empty;
             }
           }
         }
       }
       leaf preserve-parity {
         description "Allocate port with same parity as original port";
         type empty;
       }
       leaf preserve-range {
         description "Preserve privileged port range after NAT";
         type empty;
       }
     }
     container address-allocation {
       presence "enable address-allocation";
       description "Address allocation method for NAPT";
       uses apply-advanced;
       leaf round-robin {
         description "Round robin method of allocation";
         type empty;
       }
     }
     leaf mapping-timeout {
       description "Address-pooling paired and endpoint-independent mapping timeout (120..86400)";
       default "300";
       units "second";
       type union {
         type int32;
         type string {
           pattern "<.*>|$.*";
         }
       }
     }
     leaf flow-timeout {
       description "Default flow timeout for NAT flows";
       default "300";
       units "second";
       type union {
         type string {
           pattern "<.*>|$.*";
         }
         type int32 {
           range "30 .. 86400";
         }
       }
     }
     leaf ei-mapping-timeout {
       description "Endpoint-independent mapping timeout (120..86400)";
       units "second";
       type union {
         type int32;
         type string {
           pattern "<.*>|$.*";
         }
       }
     }
     leaf app-mapping-timeout {
       description "Address-pooling paired mapping timeout (120..86400)";
       units "second";
       type union {
         type int32;
         type string {
           pattern "<.*>|$.*";
         }
       }
     }
     leaf limit-ports-per-address {
       description "Limit number of ports allocated per host (IP address)";
       units "connections";
       type union {
         type string {
           pattern "<.*>|$.*";
         }
         type int32 {
           range "2 .. 65435";
         }
       }
     }
     container snmp-trap-thresholds {
       presence "enable snmp-trap-thresholds";
       description "Define snmp traps for service sets";
       uses apply-advanced;
       container address-port {
         presence "enable address-port";
         description "Nat pool address and port usage trap threshold range";
         leaf low {
           description "Lower limit of pool trap threshold";
           units "percent";
           type union {
             type string {
               pattern "<.*>|$.*";
             }
             type uint16 {
               range "0 .. 100";
             }
           }
         }
         leaf high {
           description "Upper limit of pool trap threshold";
           units "percent";
           type union {
             type string {
               pattern "<.*>|$.*";
             }
             type uint16 {
               range "0 .. 100";
             }
           }
         }
       }
     }
   }
   grouping nat_pgcp_hint_list_object {
     description "NAT hints";
     leaf name {
       description "NAT-hint string list";
       type string {
         length "1 .. 4";
       }
     }
   }
   grouping nat_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match an input to or output from on interface";
         }
       }
     }
     list term {
       key name;
       ordered-by user;
       description "Define a NAT term";
       leaf name {
         description "Term name";
         type string {
           length "1 .. 63";
         }
       }
       uses apply-advanced;
       leaf nat-type {
         description "NAT type (symmetric/full-cone)";
         type enumeration {
           enum "symmetric" {
             description "Symmetric NAT";
           }
           enum "full-cone" {
             description "Full Cone NAT";
           }
         }
       }
       container from {
         description "Define match criteria";
         uses sfw_match_object;
       }
       container then {
         description "Action to take if the 'from' condition is matched";
         uses apply-advanced;
         choice designation {
           case case_1 {
             leaf no-translation {
               description "Do not perform translation";
               type empty;
             }
           }
         }
         choice port-forwarding {
           case case_1 {
             leaf port-forwarding-mappings {
               description "Port forwarding mappings";
               type string {
                 length "1 .. 63";
               }
             }
           }
         }
         container translated {
           description "Define translation parameters";
           uses apply-advanced;
           choice source-pool-choice {
             case case_1 {
               leaf source-pool {
                 description "NAT pool for source translation";
                 type string {
                   length "1 .. 63";
                 }
               }
             }
             case case_2 {
               leaf source-prefix {
                 description "NAT prefix for source translation";
                 type jt:ipprefix-only;
               }
             }
           }
           leaf clat-prefix {
             description "Clat-prefix to be used for 464 translation type";
             type jt:ipprefix-only;
           }
           leaf clat-ipv6-prefix-length {
             description "The ipv6 prefix length for CLAT source address";
             default "64";
             type enumeration {
               enum "32" {
                 description "The ipv6 prefix length of 32";
               }
               enum "40" {
                 description "The ipv6 prefix length of 40";
               }
               enum "48" {
                 description "The ipv6 prefix length of 48";
               }
               enum "56" {
                 description "The ipv6 prefix length of 56";
               }
               enum "64" {
                 description "The ipv6 prefix length of 64";
               }
               enum "96" {
                 description "The ipv6 prefix length of 96";
               }
             }
           }
           choice destination-pool-choice {
             case case_1 {
               leaf destination-pool {
                 description "NAT pool for destination translation";
                 type string {
                   length "1 .. 63";
                 }
               }
             }
             case case_2 {
               leaf destination-prefix {
                 description "NAT prefix for destination translation";
                 type jt:ipprefix-only;
               }
             }
           }
           choice dns-alg-pool-choice {
             case case_1 {
               leaf dns-alg-pool {
                 description "NAT pool for dns alg mappings";
                 type string {
                   length "1 .. 63";
                 }
               }
             }
             case case_2 {
               leaf dns-alg-prefix {
                 description "DNS ALG 96 bit prefix for mapping IPv4 addresses to IPv6 addresses";
                 type jt:ipprefix-only;
               }
             }
           }
           choice dns-map-address-for-destination-translation-choice {
             case case_1 {
               leaf use-dns-map-for-destination-translation {
                 description "Use dns alg address map for destination translation";
                 status deprecated;
                 type empty;
               }
             }
           }
           choice overload-pool-choice {
             case case_1 {
               leaf overload-pool {
                 description "NAT pool to be used when source pool is overloaded";
                 type string {
                   length "1 .. 63";
                 }
               }
             }
             case case_2 {
               leaf overload-prefix {
                 description "NAT prefix to be used when source pool is overloaded";
                 type jt:ipprefix-only;
               }
             }
           }
           container translation-type {
             description "Type of translation to perform";
             uses apply-advanced;
             leaf source {
               description "Type of source translation";
               status deprecated;
               type enumeration {
                 enum "static" {
                   description "Static translation";
                   status deprecated;
                 }
                 enum "dynamic" {
                   description "Dynamic translation";
                   status deprecated;
                 }
               }
             }
             leaf destination {
               description "Type of destination translation";
               status deprecated;
               type enumeration {
                 enum "static" {
                   description "Static translation";
                   status deprecated;
                 }
               }
             }
             container basic-nat44 {
               presence "enable basic-nat44";
               description "Static source address (IPv4 to IPv4) translation";
             }
             container dynamic-nat44 {
               presence "enable dynamic-nat44";
               description "Dynamic source address only (IPv4 to IPv4) translation";
             }
             container napt-44 {
               presence "enable napt-44";
               description "Source address (IPv4 to IPv4) and port translation";
             }
             container dnat-44 {
               presence "enable dnat-44";
               description "Static Destination address (IPv4 to IPv4) translation";
             }
             container stateful-nat64 {
               presence "enable stateful-nat64";
               description "Dynamic source address (IPv6 to IPv4) and prefix removal for destination address (IPv6 to IPv4)translation";
             }
             container stateful-nat464 {
               presence "enable stateful-nat464";
               description "Prefix removal for Src and Dest address (IPv6 to IPv4) translation";
             }
             container basic-nat-pt {
               presence "enable basic-nat-pt";
               description "NAT-PT (static source address (IPv6 to IPv4) and prefix removal for destination address (IPv6 to IPv4) translation)";
             }
             container napt-pt {
               presence "enable napt-pt";
               description "NAT-PT (source address (IPv6 to IPv4) and source port and prefix removal for destination address (IPv6 to IPv4) translation)";
             }
             container basic-nat66 {
               presence "enable basic-nat66";
               description "Static source address (IPv6 to IPv6) translation [same as basic-nat44 but for IPv6 address family]";
             }
             container nptv6 {
               presence "enable nptv6";
               description "Stateless source address (IPv6 to IPv6) translation";
             }
             container napt-66 {
               presence "enable napt-66";
               description "Source address (IPv6 to IPv6) and port translation [same as napt-44 but for IPv6 address family]";
             }
             container twice-napt-44 {
               presence "enable twice-napt-44";
               description "Source NAPT and destination static translation for IPv4 address family";
             }
             container twice-basic-nat-44 {
               presence "enable twice-basic-nat-44";
               description "Source static and destination static translation for IPv4 address family";
             }
             container twice-dynamic-nat-44 {
               presence "enable twice-dynamic-nat-44";
               description "Source dynamic and destination static translation for IPv4 address family";
             }
             container deterministic-napt44 {
               presence "enable deterministic-napt44";
               description "Deterministic source NAPT for IPv4 family";
               uses apply-advanced;
             }
             container deterministic-napt64 {
               presence "enable deterministic-napt64";
               description "Deterministic source NAPT for IPv6 family";
             }
           }
           leaf mapping-type {
             description "Source NAT mapping type";
             type enumeration {
               enum "endpoint-independent" {
                 description "Endpoint independent mapping";
               }
             }
           }
           leaf flow-type {
             description "Source NAT flow type";
             type enumeration {
               enum "endpoint-independent" {
                 description "Endpoint independent flow";
               }
             }
           }
           leaf ignore-dst-nat-1to1-limitation {
             description "Ignore destination NAT 1:1 limitation";
             type empty;
           }
           container secure-nat-mapping {
             presence "enable secure-nat-mapping";
             description "Mapping options for enhanced security";
             uses apply-advanced;
             leaf eif-flow-limit {
               description "Number of inbound flows to be allowed for a EIF mapping";
               type union {
                 type string {
                   pattern "<.*>|$.*";
                 }
                 type uint16 {
                   range "0 .. 65534";
                 }
               }
             }
             leaf mapping-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
             leaf flow-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
           }
           container filtering-type {
             description "Source NAT filtering type";
             uses apply-advanced;
             container endpoint-independent {
               presence "enable endpoint-independent";
               description "Endpoint independent filtering";
               uses apply-advanced;
               list prefix-list {
                 key name;
                 ordered-by user;
                 description "One or more named lists of source prefixes to match";
                 leaf name {
                   description "Name of prefix list to match against";
                   type string;
                 }
                 leaf except {
                   description "Name of prefix list not to match against";
                   type empty;
                 }
               }
             }
           }
           leaf address-pooling {
             description "Address pooling behavior for source NAT";
             type enumeration {
               enum "paired" {
                 description "Address pooling behavior of paired";
               }
             }
           }
         }
         leaf syslog {
           description "System log information about the packet";
           type empty;
         }
       }
     }
   }
   grouping new_call_then_type {
     uses apply-advanced;
     leaf trace {
       description "Trace messages accepted on this policy";
       type empty;
     }
     container media-policy {
       description "Media policy parameters";
       uses apply-advanced;
       choice anchoring-policy {
         case case_1 {
           leaf no-anchoring {
             description "Setting this would bypass media packet gateway processing";
             type empty;
           }
         }
         case case_2 {
           leaf media-release {
             description "Release media - media will not be anchored";
             type empty;
           }
         }
       }
       container nat-traversal {
         presence "enable nat-traversal";
         description "Choose when to perform NAT traversal";
         uses apply-advanced;
         leaf nat-traversal-strategy {
           description "Choose when to perform NAT traversal";
           type enumeration {
             enum "never" {
               description "Never perform NAT traversal";
             }
             enum "always" {
               description "Always perform NAT traversal";
             }
             enum "same-as-signaling" {
               description "Perform NAT traversal according to signaling";
             }
           }
         }
         leaf force-bidirectional-media {
           description "Force bidirectional media";
           type empty;
         }
       }
       container data-inactivity-detection {
         description "Configuration of data inactivity indicators";
         uses apply-advanced;
         leaf inactivity-duration {
           description "The amount of time in seconds a stream is inactive before a notification is sent to the SPDF";
           units "seconds";
           type union {
             type string {
               pattern "<.*>|$.*";
             }
             type uint16 {
               range "30 .. 3600";
             }
           }
         }
       }
       leaf service-class {
         description "Rate limiting and dscp marking based on the media type";
         type string {
           length "1 .. 63";
         }
       }
     }
   }
   grouping new_call_usage_set_type {
     leaf name {
       description "Policy set name";
       type string;
     }
     uses apply-advanced;
     leaf-list policy-name {
       ordered-by user;
       description "Policy name";
       type string;
       max-elements 500;
     }
   }
   grouping new_registration_set_type {
     leaf name {
       description "Policy set name";
       type string;
     }
     uses apply-advanced;
     leaf-list policy-name {
       ordered-by user;
       description "Policy name";
       type string;
       max-elements 500;
     }
   }
   grouping new_transaction_set_type {
     leaf name {
       description "Policy set name";
       type string;
     }
     uses apply-advanced;
     leaf-list policy-name {
       ordered-by user;
       description "Policy name";
       type string;
       max-elements 500;
     }
   }
   grouping output-plugin {
     leaf name {
       description "Plugin name";
       type string;
     }
     uses apply-advanced;
     list parameters {
       key name;
       ordered-by user;
       description "List of key:value parameters for plugin";
       uses parameter-pair;
     }
   }
   grouping parameter-pair {
     leaf name {
       description "Parameter key";
       type string;
     }
     uses apply-advanced;
     leaf value {
       description "Parameter value";
       type string;
     }
   }
   grouping pcp-object {
     description "Configure Port Control Protocol";
     uses apply-advanced;
     container traceoptions {
       description "Trace options for PCP-LOG";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list server {
       key name;
       ordered-by user;
       description "Define a PCP server";
       uses pcp-server-object;
     }
     list rule {
       key name;
       ordered-by user;
       description "Define a PCP rule";
       uses pcp-rule-object;
     }
     list rule-set {
       key name;
       ordered-by user;
       description "Defines a set of PCP rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping pcp-rule-object {
     leaf name {
       description "Rule name";
       type string {
         length "1 .. 63";
       }
     }
     uses apply-advanced;
     leaf match-direction {
       description "Define direction for which the rule match is applied";
       type enumeration {
         enum "input" {
           description "Match on input to interface";
         }
         enum "output" {
           description "Match on output from interface";
         }
       }
     }
     list term {
       key name;
       ordered-by user;
       description "Define a PCP term";
       leaf name {
         description "Term name";
         type string {
           length "1 .. 63";
         }
       }
       uses apply-advanced;
       container from {
         description "Define match criteria";
         uses sfw_match_object;
       }
       container then {
         description "Action to take if the 'from' condition is matched";
         uses apply-advanced;
         leaf pcp-server {
           description "Define PCP server";
           type string {
             length "1 .. 63";
           }
         }
       }
     }
     container match {
       description "Define match criteria";
       uses sfw_match_object;
     }
     container then {
       description "Action to take if the 'from' condition is matched";
       uses apply-advanced;
       leaf pcp-server {
         description "Define PCP server";
         type string {
           length "1 .. 63";
         }
       }
     }
   }
   grouping pcp-server-object {
     leaf name {
       description "Name of PCP server";
       type string {
         length "1 .. 63";
       }
     }
     uses apply-advanced;
     leaf ipv4-address {
       description "Configure IPv4 address for this PCP server";
       type jt:ipv4addr;
     }
     leaf ipv6-address {
       description "Configure IPv6 address for this PCP server";
       type jt:ipv6addr;
     }
     leaf softwire-concentrator {
       description "Softwire ds-lite concentrator";
       type string {
         length "1 .. 63";
       }
     }
     leaf softwire-concentrator-name {
       description "Softwire ds-lite concentrator";
       type string {
         length "1 .. 63";
       }
     }
     leaf mapping-lifetime-minimum {
       description "Configure the minimum lifetime for any mapping";
       default "120";
       units "second";
       type union {
         type string {
           pattern "<.*>|$.*";
         }
         type uint16 {
           range "120 .. 3600";
         }
       }
     }
     leaf mapping-lifetime-maximum {
       description "Configure the maximum lifetime for any mapping";
       default "86400";
       units "second";
       type union {
         type string {
           pattern "<.*>|$.*";
         }
         type uint32 {
           range "120 .. 4294667";
         }
       }
     }
     leaf short-lifetime-error {
       description "Configure duration of a short-lifetime error";
       default "30";
       units "second";
       type union {
         type string {
           pattern "<.*>|$.*";
         }
         type uint16 {
           range "15 .. 300";
         }
       }
     }
     leaf long-lifetime-error {
       description "Configure duration of a long-lifetime error";
       default "1800";
       units "second";
       type union {
         type string {
           pattern "<.*>|$.*";
         }
         type uint16 {
           range "900 .. 18000";
         }
       }
     }
     leaf max-mappings-per-client {
       description "Configure maximum mappings permitted per client";
       default "32";
       type union {
         type string {
           pattern "<.*>|$.*";
         }
         type uint16 {
           range "1 .. 128";
         }
       }
     }
     container pcp-options {
       description "Configure PCP options supported by this server";
       leaf third-party {
         description "Enable Third Party option";
         type empty;
       }
       leaf prefer-failure {
         description "Enable Prefer Failure option";
         type empty;
       }
     }
     container nat-options {
       description "NAT options of this PCP server";
       uses apply-advanced;
       list pool {
         key name;
         ordered-by user;
         description "NAT pool name";
         uses nat_pool_list_object;
       }
     }
     container nat-option {
       description "NAT option of this PCP server";
       uses apply-advanced;
       list pool {
         key name;
         ordered-by user;
         description "NAT pool name";
         uses nat_pool_list_object_usf;
       }
     }
   }
   grouping nat_pool_list_object {
     description "One or more nat pools";
     leaf name {
       type string {
         length "1 .. 63";
       }
     }
   }
   grouping nat_pool_list_object_usf {
     description "One or more nat pools";
     leaf name {
       type string {
         length "1 .. 63";
       }
     }
   }
   grouping pf_mapping {
     leaf name {
       description "Port Forwarding name";
       type string {
         length "1 .. 63";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping pfcp-traceoptions-type {
     description "Trace options for SAEGW PFCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "decode" {
             description "Trace PFCP protocol decode events";
           }
           enum "encode" {
             description "Trace PFCP protocol encode events";
           }
           enum "general" {
             description "Trace PFCP general events";
           }
           enum "heartbeat" {
             description "Trace PFCP heart beat management events";
           }
           enum "request-cache" {
             description "Trace PFCP request-cache events";
           }
           enum "operational-commands" {
             description "Trace PFCP events related to operational-commands";
           }
           enum "all" {
             description "Trace everything";
           }
         }
       }
     }
   }
   grouping pgcp_gateway_object {
     description "One or more Packet Gateways";
     leaf name {
       description "Gateway Name";
       type string {
         length "1 .. 63";
       }
     }
     uses apply-advanced;
     leaf gateway-address {
       description "Local Gateway IP address";
       type jt:ipv4addr;
     }
     leaf routing-instance {
       description "Routing instance";
       default "inet.0";
       type string;
     }
     leaf gateway-port {
       description "Local Gateway transport port";
       default "2944";
       type union {
         type uint16;
         type string {
           pattern "<.*>|$.*";
         }
       }
     }
     leaf cleanup-timeout {
       description "When expires the PG will clean its gate state (Applicable in disconnections)";
       units "seconds";
       type union {
         type string {
           pattern "<.*>|$.*";
         }
         type uint16 {
           range "5 .. 65535";
         }
       }
     }
     leaf service-state {
       description "Service state";
       type enumeration {
         enum "in-service" {
           description "Gateway is operational";
         }
         enum "out-of-service-forced" {
           description "Gateway is nonoperational";
         }
         enum "out-of-service-graceful" {
           description "Gateway becomes nonoperational by draining";
         }
       }
     }
     container h248-timers {
       presence "enable h248-timers";
       uses pgcp_h248_timers_object;
     }
     container h248-properties {
       presence "enable h248-properties";
       uses pgcp_h248_properties_object;
     }
     container h248-options {
       presence "enable h248-options";
       uses pgcp_h248_options_object;
     }
     leaf max-concurrent-calls {
       description "Maximum number of concurrent calls";
       default "0";
       type union {
         type string {
           pattern "<.*>|$.*";
         }
         type uint32 {
           range "0 .. 20000";
         }
       }
     }
     list gateway-controller {
       key name;
       ordered-by user;
       max-elements 32;
       uses pgcp_controller_object;
     }
     container monitor {
       description "Monitor voice traffic";
       uses apply-advanced;
       container media {
         presence "enable media";
         description "Monitor media traffic";
         uses apply-advanced;
         leaf rtp {
           description "Monitor RTP traffic";
           type empty;
         }
         leaf rtcp {
           description "Monitor RTCP traffic";
           type empty;
         }
       }
     }
     container graceful-restart {
       presence "enable graceful-restart";
       uses apply-advanced;
       leaf maximum-synchronization-time {
         description "Maximum time for synchronization procedure with the PIC";
         status deprecated;
         default "720";
         units "seconds";
         type union {
           type string {
             pattern "<.*>|$.*";
           }
           type uint16 {
             range "0 .. 720";
           }
         }
       }
       leaf maximum-synchronization-mismatches {
         description "Maximum number of mismatches for synchronization procedure with the PIC";
         default "250";
         type union {
           type string {
             pattern "<.*>|$.*";
           }
           type uint32 {
             range "0 .. 20000";
           }
         }
       }
       leaf no-synchronization {
         description "Disable the synchronization procedure with the PIC";
         type empty;
       }
       leaf catchup-replication-delay {
         description "Delay between replication of new updates and catch-up";
         default "300";
         type union {
           type string {
             pattern "<.*>|$.*";
           }
           type uint16 {
             range "0 .. 600";
           }
         }
       }
     }
     container fast-update-filters {
       presence "enable fast-update-filters";
       uses apply-advanced;
       leaf maximum-terms {
         description "Maximum gate rate-limit terms to install at PFE";
         default "2000";
         type union {
           type string {
             pattern "<.*>|$.*";
           }
           type uint64 {
             range "0 .. 20000";
           }
         }
       }
       leaf maximum-term-percentage {
         description "Maximum percentage of gates with rate-limit terms at PFE";
         default "10";
         type union {
           type string {
             pattern "<.*>|$.*";
           }
           type uint8 {
             range "0 .. 100";
           }
         }
       }
     }
     container session-mirroring {
       presence "enable session-mirroring";
       uses pgcp_gateway_session_mirroring_object;
     }
     container data-inactivity-detection {
       uses apply-advanced;
       leaf inactivity-delay {
         description "Delay before data inactivity detection starts";
         default "0";
         units "seconds";
         type union {
           type string {
             pattern "<.*>|$.*";
           }
           type uint16 {
             range "0 .. 3600";
           }
         }
       }
       leaf latch-deadlock-delay {
         description "Delay value used for gates employing NAPT traversal";
         default "0";
         units "seconds";
         type union {
           type string {
             pattern "<.*>|$.*";
           }
           type uint16 {
             range "0 .. 3600";
           }
         }
       }
       leaf send-notification-on-delay {
         description "Send inactivity notification when delay expires";
         type empty;
       }
       leaf inactivity-duration {
         description "Default data inactivity duration (Q-MI)";
         default "15";
         units "seconds";
         type union {
           type string {
             pattern "<.*>|$.*";
           }
           type uint32 {
             range "5 .. 86400";
           }
         }
       }
       leaf stop-detection-on-drop {
         description "Stop detection when gate action is set to drop";
         type empty;
       }
       leaf no-rtcp-check {
         description "Do not detect data inactivity on rtcp stream";
         type empty;
       }
       container report-service-change {
         description "Configure the data-inactivity service-change behavior";
         uses apply-advanced;
         leaf service-change-type {
           description "Configure the service-change type to be sent upon data-inactivity";
           type enumeration {
             enum "forced-910" {
               description "Send FO/910 service change";
             }
             enum "forced-906" {
               description "Send FO/906 service change";
             }
           }
         }
       }
     }
     container overload-control {
       presence "enable overload-control";
       uses apply-advanced;
       leaf queue-limit-percentage {
         description "Overload control queue limit percentage";
         default "70";
         type union {
           type string {
             pattern "<.*>|$.*";
           }
           type uint8 {
             range "0 .. 100";
           }
         }
       }
       leaf reject-new-calls-threshold {
         description "Overload control reject new calls threshold";
         default "80";
         type union {
           type string {
             pattern "<.*>|$.*";
           }
           type uint8 {
             range "0 .. 100";
           }
         }
       }
       leaf reject-all-commands-threshold {
         description "Overload control reject all commands threshold";
         default "90";
         type union {
           type string {
             pattern "<.*>|$.*";
           }
           type uint8 {
             range "0 .. 100";
           }
         }
       }
       leaf queue-maximum-length {
         description "Overload control queue maximum length";
         default "100";
         type union {
           type string {
             pattern "<.*>|$.*";
           }
           type uint16 {
             range "10 .. 1000";
           }
         }
       }
       leaf error-code {
         description "Overload control error code";
         default "511";
         type union {
           type string {
             pattern "<.*>|$.*";
           }
           type uint16 {
             range "510 .. 511";
           }
         }
       }
     }
     container platform {
       presence "enable platform";
       description "Define the platform on which the gateway should be activated";
       uses apply-advanced;
       choice values {
         case case_1 {
           leaf routing-engine {
             description "The gateway should be activated on the RE";
             type empty;
           }
         }
         case case_2 {
           leaf device {
             description "The gateway should be activated on a services device";
             type union {
               type jt:interface-device;
               type string {
                 pattern "<.*>|$.*";
               }
             }
           }
         }
       }
     }
     leaf ipsec-transport-security-association {
       description "IPsec transport security association name";
       type string {
         length "1 .. 63";
       }
     }
   }
   grouping pgcp_controller_object {
     leaf name {
       description "PGCP Controller Name";
       type string {
         length "1 .. 63";
       }
     }
     uses apply-advanced;
     leaf controller-address {
       description "Gateway controller IP address";
       type jt:ipv4addr;
     }
     leaf controller-port {
       description "Gateway controller port";
       default "2944";
       type union {
         type uint16;
         type string {
           pattern "<.*>|$.*";
         }
       }
     }
     container interim-ah-scheme {
       presence "enable interim-ah-scheme";
       uses pgcp_interim_ah_scheme_object;
     }
     choice controller-type {
       case case_1 {
         leaf remote-controller {
           description "The gateway controller is remote";
           type empty;
         }
       }
       case case_2 {
         leaf local-controller {
           description "The gateway controller is local";
           type string {
             length "1 .. 63";
           }
         }
       }
     }
   }
   grouping pgcp_gateway_session_mirroring_object {
     description "Gateway session mirroring properties";
     uses apply-advanced;
     list delivery-function {
       key name;
       ordered-by user;
       description "Interface for delivering mirrored packets";
       max-elements 1;
       uses pgcp_delivery_function_list_object;
     }
     leaf disable-session-mirroring {
       description "Disable session mirroring for this gateway";
       type empty;
     }
   }
   grouping pgcp_delivery_function_list_object {
     description "Session-mirroring delivery functions";
     leaf name {
       type string {
         length "1 .. 63";
       }
     }
   }
   grouping pgcp_h248_options_object {
     uses apply-advanced;
     container service-change {
       presence "enable service-change";
       uses pgcp-h248-service-change-object;
     }
     leaf audit-observed-events-returns {
       description "Activation of history buffer for audit observed events";
       type empty;
     }
     container encoding {
       presence "enable encoding";
       uses apply-advanced;
       leaf no-octet-string-bit-mirroring {
         description "No octet string bit mirroring";
         type empty;
       }
       leaf no-dscp-bit-mirroring {
         description "No DSCP bit mirroring";
         status deprecated;
         type empty;
       }
       leaf use-lower-case {
         description "Encode H248 message in lower case";
         type empty;
       }
     }
     container h248-profile {
       uses apply-advanced;
       leaf profile-name {
         description "The H.248 profile declared by the BGF";
         type string {
           length "1 .. 64";
         }
       }
       leaf profile-version {
         description "The H.248 profile-version declared by the BGF";
         type union {
           type string {
             pattern "<.*>|$.*";
           }
           type uint32 {
             range "1 .. 99";
           }
         }
       }
     }
     leaf accept-emergency-calls-while-graceful {
       description "Accept emergency calls while BGF is in OOS gracefull state";
       type empty;
     }
     leaf implicit-tcp-latch {
       description "Latch implicitly upon TCP transport usage";
       type empty;
     }
     leaf implicit-tcp-source-filter {
       description "Implicitly filter TCP source addresses";
       type empty;
     }
   }
   grouping pgcp-h248-service-change-object {
     uses apply-advanced;
     container control-association-indications {
       description "Control association indications";
       presence "enable control-association-indications";
       uses control-association-indications-object;
     }
     container virtual-interface-indications {
       description "Virtual interface indications";
       presence "enable virtual-interface-indications";
       uses virtual-interface-indications-object;
     }
     container context-indications {
       description "Context indications";
       presence "enable context-indications";
       uses context-indications-object;
     }
     leaf use-wildcard-response {
       description "Request short response to service-change messages";
       type empty;
     }
   }
   grouping context-indications-object {
     description "Context indications";
     uses apply-advanced;
     leaf state-loss {
       description "Configure state loss service change";
       type enumeration {
         enum "forced-915" {
           description "State loss";
         }
         enum "forced-910" {
           description "State loss reason fo/910";
         }
         enum "none" {
           description "Suppress state loss 918 service change";
         }
       }
     }
   }
   grouping control-association-indications-object {
     description "Control association indications";
     uses apply-advanced;
     container up {
       presence "enable up";
       uses pgcp-association-up-object;
     }
     container down {
       presence "enable down";
       uses pgcp-association-down-object;
     }
     container disconnect {
       presence "enable disconnect";
       uses pgcp-association-disconnect-object;
     }
   }
   grouping pgcp-association-disconnect-object {
     description "Control association disconnect";
     uses apply-advanced;
     leaf reconnect {
       description "Configure reconnect service change";
       type enumeration {
         enum "disconnected-900" {
           description "Service restored";
         }
         enum "restart-902" {
           description "Warm boot";
         }
       }
     }
     leaf controller-failure {
       description "Configure controller failure service change";
       type enumeration {
         enum "restart-902" {
           description "Warm boot";
         }
         enum "failover-909" {
           description "Gateway controller impending failure";
         }
       }
     }
   }
   grouping pgcp-association-down-object {
     description "Control association down";
     uses apply-advanced;
     leaf administrative {
       description "Configure administrative service change";
       type enumeration {
         enum "forced-905" {
           description "Termination taken out of service";
         }
         enum "forced-908" {
           description "Gateway impending failure";
         }
         enum "none" {
           description "Suppress service change";
         }
       }
     }
     leaf failure {
       description "Configure failure service change";
       type enumeration {
         enum "forced-904" {
           description "Termination malfunctioning";
         }
         enum "forced-908" {
           description "Gateway impending failure";
         }
         enum "none" {
           description "Suppress service change";
         }
       }
     }
     leaf graceful {
       description "Configure graceful service change";
       type enumeration {
         enum "none" {
           description "Suppress graceful-905 service change";
         }
         enum "graceful-905" {
           description "Termination taken out of service";
         }
       }
     }
   }
   grouping pgcp-association-up-object {
     description "Control association up";
     uses apply-advanced;
     leaf failover-cold {
       description "Configure failover-cold service change";
       type enumeration {
         enum "restart-901" {
           description "Cold boot";
         }
         enum "failover-920" {
           description "Cold failover";
         }
       }
     }
     leaf failover-warm {
       description "Configure failover-warm service change";
       type enumeration {
         enum "restart-902" {
           description "Warm boot";
         }
         enum "failover-919" {
           description "Warm failover";
         }
       }
     }
     leaf cancel-graceful {
       description "Configure cancel-graceful service change";
       type enumeration {
         enum "none" {
           description "Suppress restart-918 service change";
         }
         enum "restart-918" {
           description "Cancel graceful";
         }
       }
     }
   }
   grouping pgcp_h248_properties_object {
     description "Gateway H248 properties";
     uses apply-advanced;
     container base-root {
       description "Setting H248 mg-mgc transaction time values";
       presence "enable base-root";
       uses pgcp_h248_base_root_object;
     }
     container segmentation {
       presence "enable segmentation";
       uses pgcp_h248_segmentation_object;
     }
     container diffserv {
       presence "enable diffserv";
       uses pgcp_h248_diffserv_object;
     }
     container hanging-termination-detection {
       description "Enabling Hanging termination detection";
       presence "enable hanging-termination-detection";
       uses pgcp-h248-hangterm-object;
     }
     container traffic-management {
       description "Setting of h248 traffic management default values";
       presence "enable traffic-management";
       uses pgcp_h248_traffic_management_object;
     }
     container notification-behavior {
       description "Setting of h248 Notify behavior values";
       presence "enable notification-behavior";
       uses pgcp-h248-notification-behavior-object;
     }
     container application-data-inactivity-detection {
       description "Setting application data inactivity detection";
       presence "enable application-data-inactivity-detection";
       uses pgcp-h248-application-data-inactivity-detection-object;
     }
     container event-timestamp-notification {
       description "Setting event timestamp notification";
       presence "enable event-timestamp-notification";
       uses pgcp-h248-event-timestamp-notification-object;
     }
     container inactivity-timer {
       description "Default values for inactivity timeout";
       presence "enable inactivity-timer";
       uses pgcp-h248-inactivity-timer-object;
     }
   }
   grouping pgcp-h248-application-data-inactivity-detection-object {
     description "Application data inactivity detection";
     uses apply-advanced;
     leaf ip-flow-stop-detection {
       description "Setting ip flow stop detection";
       type enumeration {
         enum "immediate-notify" {
           description "Report all notifications";
         }
         enum "regulated-notify" {
           description "Suppress notification according to notification-count";
         }
       }
     }
   }
   grouping pgcp-h248-event-timestamp-notification-object {
     description "Event timestamp notification";
     uses apply-advanced;
     leaf request-timestamp {
       description "Notification timestamp";
       type enumeration {
         enum "requested" {
           description "Send event timestamp";
         }
         enum "suppressed" {
           description "Dont send event timestamp";
         }
         enum "autonomous" {
           description "Show timestamp at notify request";
         }
       }
     }
   }
   grouping pgcp-h248-hangterm-object {
     description "Hanging termination detection timer";
     uses apply-advanced;
     leaf timerx {
       description "Setting timerx value";
       default "0";
       units "seconds";
       type union {
         type string {
           pattern "<.*>|$.*";
         }
         type uint32 {
           range "0 .. 2147480";
         }
       }
     }
   }
   grouping pgcp-h248-inactivity-timer-object {
     description "A timer to verify PGC connectivity";
     uses apply-advanced;
     container inactivity-timeout {
       presence "enable inactivity-timeout";
       uses apply-advanced;
       leaf detect {
         description "Enable/Disable inactivity timer detection";
         type empty;
       }
       container maximum-inactivity-time {
         uses apply-advanced;
         leaf default {
           description "Default maximum inactivity timeout";
           default "12000";
           units "10-milliseconds";
           type union {
             type string {
               pattern "<.*>|$.*";
             }
             type uint16 {
               range "100 .. 65535";
             }
           }
         }
         leaf minimum {
           description "Minimum range for maximum inactivity timeout";
           default "100";
           units "10-milliseconds";
           type union {
             type string {
               pattern "<.*>|$.*";
             }
             type uint16 {
               range "100 .. 65535";
             }
           }
         }
         leaf maximum {
           description "Maximum range for maximum inactivity timeout";
           default "65535";
           units "10-milliseconds";
           type union {
             type string {
               pattern "<.*>|$.*";
             }
             type uint16 {
               range "100 .. 65535";
             }
           }
         }
       }
     }
   }
   grouping pgcp-h248-notification-behavior-object {
     description "Notify behavior parameters";
     uses apply-advanced;
     container notification-regulation {
       presence "enable notification-regulation";
       uses apply-advanced;
       leaf default {
         description "Default suppression percentage of Notification behavior Regulation ";
         type string {
         }
       }
     }
   }
   grouping pgcp_h248_base_root_object {
     uses apply-advanced;
     container normal-mg-execution-time {
       presence "enable normal-mg-execution-time";
       description "MG transaction response time expected by MGC.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mg-provisional-response-timer-value {
       presence "enable mg-provisional-response-timer-value";
       description "MG pending response time upon incomplete transaction.";
       uses apply-advanced;
       leaf default {
         default "2000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timer value";
         default "30000";
         units "milliseconds";
         type union {
           type string {
             pattern "<.*>|$.*";
           }
           type uint16 {
             range "500 .. 30000";
           }
         }
       }
     }
     container mg-originated-pending-limit {
       presence "enable mg-originated-pending-limit";
       description "Max MG TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
     container normal-mgc-execution-time {
       presence "enable normal-mgc-execution-time";
       description "MGC transaction response time expected by MG.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mgc-provisional-response-timer-value {
       presence "enable mgc-provisional-response-timer-value";
       description "MGC pending response time upon incomplete transaction.";
       uses apply-advanced;
       leaf default {
         default "4000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timers value";
         default "30000";
         units "milliseconds";
         type union {
           type string {
             pattern "<.*>|$.*";
           }
           type uint16 {
             range "500 .. 30000";
           }
         }
       }
     }
     container mgc-originated-pending-limit {
       presence "enable mgc-originated-pending-limit";
       description "Max MGC TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
   }
   grouping pgcp_h248_diffserv_object {
     uses apply-advanced;
     container dscp {
       presence "enable dscp";
       description "Differentiated Services Code Point (DSCP)";
       uses apply-advanced;
       leaf default {
         default "be";
         type string;
       }
       leaf ignore-signaled-value {
         description "Ignore property value appearing in H.248 signaling";
         type empty;
       }
     }
   }
   grouping pgcp_h248_segmentation_object {
     uses apply-advanced;
     container mgc-segmentation-timer {
       presence "enable mgc-segmentation-timer";
       description "Time the MG waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mgc-maximum-pdu-size {
       presence "enable mgc-maximum-pdu-size";
       description "Maximum size of the MGC's incoming messages from MG";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
     container mg-segmentation-timer {
       presence "enable mg-segmentation-timer";
       description "Time the MGC waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mg-maximum-pdu-size {
       presence "enable mg-maximum-pdu-size";
       description "Maximum size of the MG's incoming messages from MGC";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
   }
   grouping pgcp_h248_timers_object {
     uses apply-advanced;
     leaf maximum-waiting-delay {
       description "Randomly determined delay before retraversing PGC list (MWD)";
       default "2000";
       units "milliseconds";
       type union {
         type string {
           pattern "<.*>|$.*";
         }
         type uint32 {
           range "100 .. 300000";
         }
       }
     }
     leaf tmax-retransmission-delay {
       description "Delay before PGC is considered down (T-MAX)";
       default "25000";
       units "milliseconds";
       type union {
         type string {
           pattern "<.*>|$.*";
         }
         type uint16 {
           range "1000 .. 60000";
         }
       }
     }
     leaf initial-average-ack-delay {
       description "Assumed initial average reply time (for retransmission rate) (I-AAD)";
       default "1000";
       units "milliseconds";
       type union {
         type string {
           pattern "<.*>|$.*";
         }
         type uint16 {
           range "500 .. 4000";
         }
       }
     }
     leaf maximum-net-propagation-delay {
       description "Worst case network propagation delay (M-NPD), used for calculating LONG-TIMER";
       default "5000";
       units "milliseconds";
       type union {
         type string {
           pattern "<.*>|$.*";
         }
         type uint16 {
           range "500 .. 10000";
         }
       }
     }
   }
   grouping pgcp_h248_traffic_management_object {
     uses apply-advanced;
     container sustained-data-rate {
       presence "enable sustained-data-rate";
       description "SDR permitted for the stream";
       uses apply-advanced;
       leaf default {
         description "Default rate value";
         default "10000";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         presence "enable rtcp";
         uses pgcp_h248_rtcp_rate_units_object;
       }
       leaf rtcp-include {
         description "TMAN SDR includes RTCP bandwidth";
         type empty;
       }
     }
     container peak-data-rate {
       presence "enable peak-data-rate";
       description "PDR permitted for the stream";
       uses apply-advanced;
       leaf default {
         description "Default rate value";
         default "0";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         presence "enable rtcp";
         uses pgcp_h248_rtcp_rate_units_object;
       }
     }
     container max-burst-size {
       presence "enable max-burst-size";
       description "MBS for the stream";
       uses apply-advanced;
       leaf default {
         description "Default rate value";
         default "1000";
         units "bytes-per-second";
         type union {
           type string {
             pattern "<.*>|$.*";
           }
           type uint32 {
             range "20 .. 2147483647";
           }
         }
       }
       leaf minimum {
         description "Minimum range of rate value";
         default "20";
         units "bytes-per-second";
         type union {
           type string {
             pattern "<.*>|$.*";
           }
           type uint32 {
             range "20 .. 2147483647";
           }
         }
       }
       leaf maximum {
         description "Maximum range of rate value";
         default "0x7FFFFFFF";
         units "bytes-per-second";
         type union {
           type string {
             pattern "<.*>|$.*";
           }
           type uint32 {
             range "20 .. 2147483647";
           }
         }
       }
       container rtcp {
         description "Default rtcp rate";
         presence "enable rtcp";
         uses pgcp_h248_rtcp_burst_units_object;
       }
     }
   }
   grouping pgcp_h248_rtcp_burst_units_object {
     description "RTCP burst parameter settings";
     uses apply-advanced;
     choice values {
       case case_1 {
         leaf percentage {
           description "Value entered is percentage of RTP's parallel value";
           default "100";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "20 .. 2147483647";
             }
           }
         }
       }
     }
   }
   grouping pgcp_h248_rtcp_rate_units_object {
     description "RTCP rate parameter settings";
     uses apply-advanced;
     choice values {
       case case_1 {
         leaf percentage {
           description "Value entered is percentage of RTP's parallel value";
           default "5";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "0 .. 2147483647";
             }
           }
         }
       }
     }
   }
   grouping pgcp_interim_ah_scheme_object {
     uses apply-advanced;
     leaf algorithm {
       description "Define authentication algorithm";
       type enumeration {
         enum "hmac-null" {
           description "NULL authentication algorithm";
         }
       }
     }
   }
   grouping pgcp_media_service_object {
     description "One or more PGCP media service";
     leaf name {
       description "Media Service name";
       type string {
         length "1 .. 63";
       }
     }
     uses apply-advanced;
     leaf nat-pool {
       description "Pool name";
       type string {
         length "1 .. 63";
       }
     }
   }
   grouping pgcp_rule_object {
     description "One or more PGCP rules";
     leaf name {
       description "Rule name";
       type string {
         length "1 .. 63";
       }
     }
     uses apply-advanced;
     leaf gateway {
       description "Gateway Name";
       type string {
         length "1 .. 63";
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
   }
   grouping pgcp_media_service_list_object {
     description "One or more PGCP media service";
     leaf name {
       type string {
         length "1 .. 63";
       }
     }
   }
   grouping pgcp_session_mirroring_object {
     description "PGCP session mirroring properties";
     uses apply-advanced;
     list delivery-function {
       key name;
       ordered-by user;
       description "Interface for delivering mirrored packets";
       max-elements 32;
       uses pgcp_delivery_function_object;
     }
     leaf disable-session-mirroring {
       description "Disable PGCP session mirroring";
       type empty;
     }
   }
   grouping pgcp_delivery_function_object {
     leaf name {
       description "Delivery function name";
       type string {
         length "1 .. 63";
       }
     }
     uses apply-advanced;
     leaf destination-address {
       description "Delivery function destination IP address";
       type jt:ipv4addr;
     }
     leaf destination-port {
       description "Delivery function destination port";
       type union {
         type uint16;
         type string {
           pattern "<.*>|$.*";
         }
       }
     }
     leaf network-operator-id {
       description "Network operator ID";
       type string {
         length 5;
       }
     }
     leaf source-address {
       description "Network-element-id";
       type jt:ipv4addr;
     }
     leaf source-port {
       description "Network-element-port";
       type union {
         type uint16;
         type string {
           pattern "<.*>|$.*";
         }
       }
     }
     container memory-managment {
       description "Measure memory usage";
       presence "enable memory-managment";
       uses pgcp_debug_mem_mgmt_object;
     }
   }
   grouping pgcp_debug_mem_mgmt_object {
     uses apply-advanced;
     leaf operational-mode {
       description "Memory managment operation mode";
       type enumeration {
         enum "fast" {
           description "Fast memory allocation [does not affect performance]";
         }
         enum "type-tracking" {
           description "Track all allocation types [affects performance]";
         }
         enum "location-tracking" {
           description "Track all allocation types and functions [affects performance]";
         }
       }
     }
   }
   grouping pgcp_virtual_interface_object {
     description "One or more Virtual Interfaces";
     leaf name {
       description "Virtual Interface Name";
       type string {
         length "1 .. 4";
       }
     }
     uses apply-advanced;
     leaf routing-instance {
       description "Routing instance of server to which to forward";
       default "inet.0";
       type string;
     }
     leaf service-state {
       description "Service state";
       default "in-service";
       type enumeration {
         enum "in-service" {
           description "Virtual Interface is operational";
         }
         enum "out-of-service-forced" {
           description "Virtual Interface is nonoperational";
         }
         enum "out-of-service-graceful" {
           description "Virtual Interface becomes nonoperational by draining";
         }
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
     leaf interface {
       description "Interface name";
       status deprecated;
       type union {
         type jt:interface-name;
         type string {
           pattern "<.*>|$.*";
         }
       }
     }
   }
   grouping policy-object-type {
     uses apply-advanced;
     container traceoptions {
       description "Network Security Policy Tracing Options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "routing-socket" {
               description "Trace routing socket events";
             }
             enum "compilation" {
               description "Policy compilation events";
             }
             enum "ipc" {
               description "Inter-process communication events";
             }
             enum "rules" {
               description "Policy rules related events";
             }
             enum "lookup" {
               description "Policy lookup events";
             }
             enum "all" {
               description "Trace everything";
             }
           }
         }
       }
     }
     list policy {
       key "from-zone-name to-zone-name";
       ordered-by user;
       description "Define a policy context from this zone";
       leaf from-zone-name {
         description "Source zone";
         type string {
           length "1 .. 63";
         }
       }
       leaf to-zone-name {
         description "Destination zone";
         type string {
           length "1 .. 63";
         }
       }
       uses apply-advanced;
       list policy {
         key name;
         ordered-by user;
         description "Define security policy in specified zone-to-zone direction";
         uses policy_type;
       }
       container application-services {
         description "Application Services";
         uses context_application_services_type;
       }
     }
     container global {
       description "Define a global policy context";
       uses apply-advanced;
       list policy {
         key name;
         ordered-by user;
         description "Define security policy in global context";
         uses policy_type;
       }
     }
     container explicit-proxy {
       description "Define a explicit proxy profiles policies";
       uses apply-advanced;
       list profile {
         key name;
         ordered-by user;
         description "Define a explicit proxy profile policy context";
         leaf name {
           description "Explicit proxy profile name";
           type string {
             length "1 .. 63";
           }
         }
         uses apply-advanced;
         list policy {
           key name;
           ordered-by user;
           description "Define security policy in explicit proxy profile context";
           uses policy_type;
         }
         container default-policy {
           description "Default policy action when no policy matches in rulebase";
           uses apply-advanced;
           leaf default-action {
             description "Default action";
             default "deny-all";
             type enumeration {
               enum "permit-all" {
                 description "Permit all traffic if no policy match";
               }
               enum "deny-all" {
                 description "Deny all traffic if no policy match";
               }
             }
           }
         }
       }
     }
     list policy-set {
       key name;
       ordered-by user;
       description "Define a policy context for tunnel-inspection";
       leaf name {
         description "Policy-set name";
         type string {
           length "1 .. 63";
         }
       }
       uses apply-advanced;
       list policy {
         key name;
         ordered-by user;
         description "Define security policy in tunnel-inspection context";
         uses policy_type;
       }
     }
     container default-policy {
       description "Configure default action when no user-defined policy match";
       uses apply-advanced;
       leaf default-action {
         description "Default action";
         default "deny-all";
         type enumeration {
           enum "permit-all" {
             description "Permit all traffic if no policy match";
           }
           enum "deny-all" {
             description "Deny all traffic if no policy match";
           }
         }
       }
       leaf log-profile {
         description "Rtlog profile";
         type string;
       }
     }
     container policy-rematch {
       presence "enable policy-rematch";
       description "Re-evaluate the policy when changed";
       leaf extensive {
         description "Perform policy extensive rematch";
         type empty;
       }
     }
     container policy-stats {
       presence "enable policy-stats";
       description "Parameters for policy statistics";
       uses apply-advanced;
       leaf system-wide {
         description "Enable/Disable system-wide policy statistics";
         type enumeration {
           enum "enable" {
             description "Enable policy system-wide statistics";
           }
           enum "disable" {
             description "Disable policy system-wide statistics";
           }
         }
       }
     }
     container pre-id-default-policy {
       description "Configure default policy action before dynamic application is finally identified";
       uses apply-advanced;
       container then {
         description "Specify policy action to take when packet match criteria";
         uses apply-advanced;
         container log {
           description "Enable log";
           uses log_type;
         }
         container session-timeout {
           description "Session timeout";
           uses session_timeout_type;
         }
       }
     }
     container unified-policy {
       description "Unified policies lookup limitations";
       uses apply-advanced;
       leaf max-lookups {
         description "Max lookup times upon micro-app transaction finals";
         type union {
           type string {
             pattern "<.*>|$.*";
           }
           type uint32 {
             range "0 .. 4294967295";
           }
         }
       }
     }
     container dns-cache {
       description "Define security policy dns-cache behaviors";
       uses apply-advanced;
       container error-response-delete-ip {
         presence "enable error-response-delete-ip";
         description "Clear DNS cache entry IP on error DNS response";
         uses apply-advanced;
         leaf retry-interval {
           description "Interval between deleting IP and resending DNS requests";
           default "300";
           units "seconds";
           type union {
             type string {
               pattern "<.*>|$.*";
             }
             type uint32 {
               range "5 .. 86400";
             }
           }
         }
       }
     }
     list stateful-firewall-rule {
       key name;
       ordered-by user;
       description "Define a stateful-firewall-rule";
       leaf name {
         description "Stateful-firewall-rule name";
         type string {
           length "1 .. 63";
         }
       }
       uses apply-advanced;
       leaf match-direction {
         description "Direction for which the rule match is applied";
         type enumeration {
           enum "input" {
             description "Match on input to interface";
           }
           enum "output" {
             description "Match on output from interface";
           }
           enum "input-output" {
             description "Match on input to or output from interface";
           }
         }
       }
       list policy {
         key name;
         ordered-by user;
         description "Define a stateful-firewall policy";
         uses policy_type;
       }
     }
     list stateful-firewall-rule-set {
       key name;
       ordered-by user;
       description "Defines a set of stateful firewall rules";
       leaf name {
         description "Name of the stateful firewall rule set";
         type string {
           length "1 .. 63";
         }
       }
       uses apply-advanced;
       list stateful-firewall-rule {
         key name;
         ordered-by user;
         description "Rule to be included in this stateful firewall rule set";
         leaf name {
           description "Stateful-firewall-rule name";
           type string {
           }
         }
         uses apply-advanced;
       }
     }
   }
   grouping context_application_services_type {
     uses apply-advanced;
     leaf security-metadata-streaming-policy {
       description "Specify security-metadata-streaming-policy";
       type string {
         length "1 .. 63";
       }
     }
   }
   grouping log_type {
     uses apply-advanced;
     leaf session-init {
       description "Log at session init time";
       type empty;
     }
     leaf session-close {
       description "Log at session close time";
       type empty;
     }
     leaf session-update {
       description "Log with specified interval (0 to disable this log)";
       default "0";
       units "minutes";
       type union {
         type string {
           pattern "<.*>|$.*";
         }
         type uint32 {
           range "0 .. 1440";
         }
       }
     }
     leaf sfw {
       description "Display Stateful-fire-wall SYSLOGs";
       type empty;
     }
     leaf profile {
       description "Name of rtlog profile";
       type string;
     }
   }
   grouping policy_type {
     leaf name {
       description "Security policy name";
       type string {
         length "1 .. 63";
       }
     }
     uses apply-advanced;
     leaf description {
       description "Text description of policy";
       type string {
         length "1 .. 900";
       }
     }
     container match {
       description "Specify security policy match-criteria";
       uses apply-advanced;
       choice source-address_choice {
         case case_1 {
           leaf-list source-address {
             ordered-by user;
             type string;
           }
         }
       }
       choice destination-address_choice {
         case case_1 {
           leaf-list destination-address {
             ordered-by user;
             type string;
           }
         }
       }
       leaf source-address-excluded {
         description "Exclude source addresses";
         type empty;
       }
       leaf destination-address-excluded {
         description "Exclude destination addresses";
         type empty;
       }
       choice application_type_choice {
         case case_1 {
           leaf-list application {
             ordered-by user;
             type string;
           }
         }
       }
       choice source_identity_choice {
         case case_1 {
           leaf-list source-identity {
             ordered-by user;
             type string;
           }
         }
       }
       choice source_identity_feed_choice {
         case case_1 {
           leaf-list source-identity-feed {
             ordered-by user;
             description "Specify source-identity-feed name from list to match";
             type string {
               length "1 .. 64";
             }
           }
         }
       }
       choice destination_identity_feed_choice {
         case case_1 {
           leaf-list destination-identity-feed {
             ordered-by user;
             description "Specify destination-identity-feed name from list to match";
             type string {
               length "1 .. 64";
             }
           }
         }
       }
       choice source_end_user_profile_choice {
         case case_1 {
           container source-end-user-profile {
             description "Match source end user profile";
             uses match_source_end_user_profile_value;
           }
         }
       }
       choice dynamic_application_type_choice {
         case case_1 {
           leaf-list dynamic-application {
             ordered-by user;
             type string;
           }
         }
       }
       choice url_category_type_choice {
         case case_1 {
           leaf-list url-category {
             ordered-by user;
             type string;
           }
         }
       }
       choice from_zone_choice {
         case case_1 {
           leaf-list from-zone {
             ordered-by user;
             type string;
           }
         }
       }
       choice to_zone_choice {
         case case_1 {
           leaf-list to-zone {
             ordered-by user;
             type string;
           }
         }
       }
       choice source_vrf_choice {
         case case_1 {
           leaf-list source-l3vpn-vrf-group {
             ordered-by user;
             description "L3VPN group name";
             type string;
           }
         }
       }
       choice dst_vrf_choice {
         case case_1 {
           leaf-list destination-l3vpn-vrf-group {
             ordered-by user;
             description "L3VPN group name";
             type string;
           }
         }
       }
     }
     container then {
       description "Specify policy action to take when packet match criteria";
       uses apply-advanced;
       choice action {
         case case_1 {
           container deny {
             presence "enable deny";
             description "Deny packets";
             uses apply-advanced;
             container application-services {
               description "Application Services";
               uses apply-advanced;
               container security-intelligence {
                 description "Generate security intelligence feeds";
                 uses security_intelligence_feeds;
               }
             }
           }
         }
         case case_2 {
           container reject {
             presence "enable reject";
             description "Reject packets";
             uses apply-advanced;
             leaf profile {
               description "Profile for redirect HTTP/S traffic";
               type string;
             }
             container ssl-proxy {
               presence "enable ssl-proxy";
               description "SSL proxy services";
               uses apply-advanced;
               leaf profile-name {
                 description "Specify SSL proxy service profile name";
                 type string;
               }
             }
             container application-services {
               description "Application Services";
               uses apply-advanced;
               container security-intelligence {
                 description "Generate security intelligence feeds";
                 uses security_intelligence_feeds;
               }
             }
           }
         }
         case case_3 {
           container permit {
             presence "enable permit";
             description "Permit packets";
             uses apply-advanced;
             container tunnel {
               description "Tunnel packets";
               uses tunnel_type;
             }
             container firewall-authentication {
               description "Enable authentication for this policy if permit or tunnel";
               uses firewall_authentication_type;
             }
             container destination-address {
               description "Enable destination address translation";
               presence "enable destination-address";
               uses destination_nat_enable_type;
             }
             container application-services {
               description "Application Services";
               uses application_services_type;
             }
             container tunnel-inspection {
               description "Enable tunnel inspection";
               uses apply-advanced;
               leaf profile-name {
                 description "Tunnel inspection profile";
                 type string {
                   length "1 .. 63";
                 }
               }
             }
             container tcp-options {
               description "Transmission Control Protocol session configuration";
               uses apply-advanced;
               leaf syn-check-required {
                 description "Enable per policy SYN-flag check";
                 type empty;
               }
               leaf sequence-check-required {
                 description "Enable per policy sequence-number checking";
                 type empty;
               }
               leaf initial-tcp-mss {
                 description "Override MSS value for initial direction";
                 type union {
                   type string {
                     pattern "<.*>|$.*";
                   }
                   type uint32 {
                     range "64 .. 65535";
                   }
                 }
               }
               leaf reverse-tcp-mss {
                 description "Override MSS value for reverse direction";
                 type union {
                   type string {
                     pattern "<.*>|$.*";
                   }
                   type uint32 {
                     range "64 .. 65535";
                   }
                 }
               }
               leaf window-scale {
                 description "Enable per policy window-scale";
                 type empty;
               }
             }
             choice SOF {
               case case_1 {
                 leaf services-offload {
                   description "Enable services offloading";
                   type empty;
                 }
               }
               case case_2 {
                 leaf no-services-offload {
                   description "Disenable services offloading";
                   type empty;
                 }
               }
             }
             leaf advanced-connection-tracking {
               description "Lookup advanced-connection-tracking table on to-zone";
               type empty;
             }
           }
         }
       }
       container log {
         description "Enable log";
         uses log_type;
       }
       container count {
         description "Enable count";
         presence "enable count";
         uses count_type;
       }
     }
     leaf scheduler-name {
       description "Name of scheduler";
       type string {
         length "1 .. 63";
       }
     }
     leaf report-skip {
       description "Skip report for this policy";
       type empty;
     }
   }
   grouping application_services_type {
     description "Application Services";
     uses apply-advanced;
     leaf gtp-profile {
       description "Specify GPRS Tunneling Protocol profile name";
       type string {
         length "1 .. 63";
       }
     }
     leaf sctp-profile {
       description "Specify Stream Control Protocol profile name";
       type string {
         length "1 .. 63";
       }
     }
     leaf idp {
       description "Intrusion detection and prevention";
       status deprecated;
       type empty;
     }
     leaf packet-capture {
       description "Capturing traffic related to this policy";
       type empty;
     }
     leaf idp-policy {
       description "Specify idp policy name";
       type string {
         length "1 .. 255";
       }
     }
     container ssl-proxy {
       presence "enable ssl-proxy";
       description "SSL proxy services";
       uses apply-advanced;
       leaf profile-name {
         description "Specify SSL proxy service profile name";
         type string;
       }
     }
     container web-proxy {
       presence "enable web-proxy";
       description "Web proxy services";
       uses apply-advanced;
       leaf profile-name {
         description "Specify Web proxy service profile name";
         type string;
       }
     }
     container captive-portal {
       presence "enable captive-portal";
       description "Enable security web gateway captive portal";
       uses apply-advanced;
       leaf profile {
         type string {
           length "1 .. 128";
         }
       }
     }
     container uac-policy {
       presence "enable uac-policy";
       description "Enable unified access control enforcement of policy";
       uses apply-advanced;
       leaf captive-portal {
         type string {
           length "1 .. 128";
         }
       }
     }
     leaf utm-policy {
       description "Specify utm policy name";
       type string {
         length "1 .. 255";
       }
     }
     leaf icap-redirect {
       description "Specify icap redirect profile name";
       type string {
         length "1 .. 63";
       }
     }
     container application-firewall {
       description "Application firewall services";
       status deprecated;
       uses jsf_service_rule_set_type;
     }
     container application-traffic-control {
       description "Application traffic control services";
       uses jsf_application_traffic_control_rule_set_type;
     }
     choice wx-redirection {
       case case_1 {
         leaf redirect-wx {
           description "Set WX redirection";
           type empty;
         }
       }
       case case_2 {
         leaf reverse-redirect-wx {
           description "Set WX reverse redirection";
           type empty;
         }
       }
     }
     leaf security-intelligence-policy {
       description "Specify security-intelligence policy name";
       type string {
         length "1 .. 255";
       }
     }
     leaf advanced-anti-malware-policy {
       description "Specify advanced-anti-malware policy name";
       type string {
         length "1 .. 64";
       }
     }
     container security-intelligence {
       description "Generate security intelligence feeds";
       uses security_intelligence_feeds;
     }
     leaf anti-virus-policy {
       description "Specify anti-virus policy name";
       type string {
         length "1 .. 64";
       }
     }
   }
   grouping count_type {
     uses apply-advanced;
   }
   grouping destination_nat_enable_type {
     description "Enable Destination NAT";
     uses apply-advanced;
     choice destination_nat {
       case case_1 {
         leaf drop-translated {
           description "Drop the policy if NAT translated";
           type empty;
         }
       }
       case case_2 {
         leaf drop-untranslated {
           description "Drop the policy if NAT untranslated";
           type empty;
         }
       }
     }
   }
   grouping firewall_authentication_type {
     uses apply-advanced;
     choice auth-type {
       case case_1 {
         container pass-through {
           presence "enable pass-through";
           description "Pass-through firewall authentication settings";
           uses apply-advanced;
           leaf access-profile {
             description "Specify access profile name";
             type string {
               length "1 .. 63";
             }
           }
           leaf-list client-match {
             ordered-by user;
             description "Name of user or group to match";
             type string {
               length "1 .. 63";
             }
           }
           leaf web-redirect {
             description "Redirect unauthenticated HTTP requests to the device's internal web server";
             type empty;
           }
           leaf web-redirect-to-https {
             description "Redirect unauthenticated HTTP requests to the device's internal HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
         }
       }
       case case_2 {
         container web-authentication {
           presence "enable web-authentication";
           description "Web-authentication settings";
           uses apply-advanced;
           leaf-list client-match {
             ordered-by user;
             description "Name of user or group to match";
             type string {
               length "1 .. 63";
             }
           }
         }
       }
       case case_3 {
         container user-firewall {
           description "User-firewall firewall authentication settings";
           uses apply-advanced;
           leaf access-profile {
             description "Specify access profile name";
             type string {
               length "1 .. 63";
             }
           }
           leaf web-redirect {
             description "Redirect unauthenticated HTTP req to web server";
             type empty;
           }
           leaf web-redirect-to-https {
             description "Redirect unauthenticated HTTP req to HTTPS web server";
             type empty;
           }
           leaf web-authentication-server {
             description "Firewall web authentication server";
             type string {
               length "1 .. 128";
             }
           }
           leaf ssl-termination-profile {
             description "Specify SSL termination profile used to the SSL offload";
             type string {
               length "1 .. 63";
             }
           }
           leaf auth-only-browser {
             description "Authenticate only browser traffic";
             type empty;
           }
           list auth-user-agent {
             key name;
             ordered-by user;
             description "Authenticate HTTP traffic with specified user agent";
             leaf name {
               description "Authenticate HTTP traffic with specified user agent";
               type string {
                 length "1 .. 16";
               }
             }
             uses apply-advanced;
           }
           leaf domain {
             description "Specify domain name";
             type string {
               length "1 .. 64";
             }
           }
         }
       }
     }
     leaf push-to-identity-management {
       description "Push auth entry to identity management server";
       type empty;
     }
   }
   grouping jsf_application_traffic_control_rule_set_type {
     description "Define service application traffic rule-set reference";
     uses apply-advanced;
     leaf rule-set {
       description "Service rule-set name";
       type string {
         length "1 .. 64";
       }
     }
   }
   grouping jsf_service_rule_set_type {
     description "Define service rule set reference";
     uses apply-advanced;
     leaf rule-set {
       description "Service rule set name";
       type string {
         length "1 .. 64";
       }
     }
   }
   grouping match_source_end_user_profile_value {
     uses apply-advanced;
     leaf source-end-user-profile-name {
       description "Specify source-end-user-profile name from list to match";
       type string;
     }
   }
   grouping proxy-profile-setting {
     description "Proxy profile settings";
     leaf name {
       description "Proxy profile name";
       type string {
         length "1 .. 64";
       }
     }
     uses apply-advanced;
     container protocol {
       description "Protocol level proxy setting";
       uses apply-advanced;
       container http {
         description "HTTP proxy setting";
         uses apply-advanced;
         leaf host {
           description "Proxy server name or IP address";
           type string {
             length "1 .. 256";
           }
         }
         leaf port {
           description "Proxy server port";
           default "3128";
           type union {
             type string {
               pattern "<.*>|$.*";
             }
             type uint16 {
               range "0 .. 65535";
             }
           }
         }
       }
     }
   }
   grouping range-address-type {
     description "Range address";
     leaf name {
       description "Lower limit of address range";
       type jt:ipv4addr;
     }
     uses apply-advanced;
     container to {
       description "Port range upper limit";
       uses apply-advanced;
       leaf range-high {
         description "Upper limit of address range";
         type jt:ipv4addr;
       }
     }
   }
   grouping registration_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         presence "enable from";
         uses new_transaction_from_type;
       }
       container then {
         description "Action";
         presence "enable then";
         uses new_registration_then_type;
       }
     }
   }
   grouping new_registration_then_type {
     uses apply-advanced;
     container nat-traversal {
       description "How to traverse NAT devices";
       uses nat_traversal_action;
     }
   }
   grouping nat_traversal_action {
     uses apply-advanced;
     leaf nat-traversal-strategy {
       description "Choose when to perform NAT traversal";
       type enumeration {
         enum "never" {
           description "Never perform NAT traversal";
         }
         enum "always" {
           description "Always perform NAT traversal";
         }
         enum "by-via" {
           description "Perform NAT traversal only if transport source address does not match VIA header";
         }
       }
     }
     leaf keepalive-interval {
       description "Keepalive interval";
       default "45";
       units "seconds";
       type union {
         type string {
           pattern "<.*>|$.*";
         }
         type uint32 {
           range "15 .. 86400";
         }
       }
     }
     leaf minimum-registration-interval {
       description "Minimum registration interval allowed in register packet";
       default "1";
       units "seconds";
       type union {
         type string {
           pattern "<.*>|$.*";
         }
         type uint32 {
           range "1 .. 86400";
         }
       }
     }
     container keepalive-mechanisms {
       description "A prioritized list of keepalive mechanisms";
       uses apply-advanced;
       leaf register-fast-expiration {
         description "Reduce the expiration interval in REGISTER responses";
         type empty;
       }
     }
   }
   grouping new_transaction_from_type {
     uses apply-advanced;
     leaf-list source-address {
       ordered-by user;
       description "Source addresses and masks";
       type jt:ipaddr;
       max-elements 5;
     }
     list method {
       key name;
       ordered-by user;
       description "Methods";
       uses transaction-method-type;
     }
     container request-uri {
       description "Request URI field";
       leaf-list regular-expression {
         ordered-by user;
         description "Regular expression matched on incoming Request-URI";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
     container contact {
       description "Contact field";
       leaf-list regular-expression {
         ordered-by user;
         description "Regular expression matched on incoming contact";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
   }
   grouping rmopd-traceoptions {
     description "Trace options for remote-monitoring";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping rmps-clnt-traceoptions-type {
     description "Trace options for Resource Management and Packet Steering Client";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Client to trace";
       leaf name {
         type enumeration {
           enum "infra" {
             description "Trace FSM and Infra code";
           }
           enum "memory" {
             description "Trace Memory Management Code";
           }
           enum "communication" {
             description "Trace IPC code";
           }
           enum "resource-tables" {
             description "Trace Resource Table Code";
           }
           enum "info-tables" {
             description "Trace Information Table Code";
           }
           enum "redundancy" {
             description "Trace GRES Code";
           }
           enum "all" {
             description "Trace All Resource Client Code";
           }
         }
       }
     }
   }
   grouping rmpsd-traceoptions-type {
     description "Trace options for Resource Management and Packet Steering Daemon";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Area to trace";
       leaf name {
         type enumeration {
           enum "config" {
             description "Trace configuration code";
           }
           enum "gres" {
             description "Trace GRES code";
           }
           enum "init" {
             description "Trace initialization code";
           }
           enum "memory" {
             description "Trace memory management code";
           }
           enum "communication" {
             description "Trace Infra code";
           }
           enum "license-management" {
             description "Trace license management code";
           }
           enum "signal" {
             description "Trace signal handling code";
           }
           enum "state" {
             description "Trace state handling code";
           }
           enum "timer" {
             description "Trace timer code";
           }
           enum "ui" {
             description "Trace user interface code";
           }
           enum "resource-manager" {
             description "Trace Resource Management Code";
           }
           enum "info-manager" {
             description "Trace Information Management Code";
           }
           enum "packet-steering" {
             description "Trace packet-steering code";
           }
           enum "all" {
             description "Trace all areas of code";
           }
         }
       }
     }
   }
   grouping routing-destinations {
     uses apply-advanced;
     leaf default-availability-check-profile {
       description "Profile that will be used if no other profile was attached to a server";
       type string {
         length "1 .. 256";
       }
     }
     list availability-check-profiles {
       key name;
       ordered-by user;
       description "Definitions of servers availability check profiles";
       max-elements 100;
       uses availability-check-profile;
     }
     list servers {
       key name;
       ordered-by user;
       description "Servers definitions";
       max-elements 5000;
       uses routing-destination-server;
     }
     list clusters {
       key name;
       ordered-by user;
       description "Clusters definitions";
       max-elements 1000;
       uses routing-destination-cluster;
     }
   }
   grouping availability-check-profile {
     leaf name {
       type string {
         length "1 .. 256";
       }
     }
     uses apply-advanced;
     container keepalive-method {
       description "How will availability check be done";
       choice ping-method {
         case case_1 {
           leaf sip-options {
             description "Check availability by sending a SIP OPTIONS message";
             type empty;
           }
         }
       }
     }
     container keepalive-strategy {
       presence "enable keepalive-strategy";
       description "When will the server be checked for availability";
       choice keepalive-strategy {
         case case_1 {
           container send-always {
             presence "enable send-always";
             description "Always check the server availability";
             uses apply-advanced;
             leaf failures-before-unavailable {
               description "A server is assumed to be unavailable when a keepalive message was not answered this number of times";
               default "1";
               type union {
                 type string {
                   pattern "<.*>|$.*";
                 }
                 type uint32 {
                   range "1 .. 10";
                 }
               }
             }
             leaf successes-before-available {
               description "A server is assumed to be available when a keepalive message was successfully answered this number of times";
               default "1";
               type union {
                 type string {
                   pattern "<.*>|$.*";
                 }
                 type uint32 {
                   range "1 .. 10";
                 }
               }
             }
           }
         }
         case case_2 {
           container send-when-unavailable {
             presence "enable send-when-unavailable";
             description "Check the server availability only when it is marked as unavailable";
             leaf successes-before-available {
               description "A server is assumed to be available when a keepalive message was successfully answered this number of times";
               default "1";
               type union {
                 type string {
                   pattern "<.*>|$.*";
                 }
                 type uint32 {
                   range "1 .. 10";
                 }
               }
             }
           }
         }
         case case_3 {
           container do-not-send {
             presence "enable do-not-send";
             description "Never perform availability checks of the server";
             leaf blackout-period {
               description "Time a server will be considered unavailable";
               default "600";
               units "seconds";
               type union {
                 type string {
                   pattern "<.*>|$.*";
                 }
                 type uint32 {
                   range "0 .. 86400";
                 }
               }
             }
           }
         }
       }
     }
     container keepalive-interval {
       description "How often should the server be checked for availability";
       uses apply-advanced;
       leaf available-server {
         description "How often should a server that is marked as available be checked for availablility";
         default "32";
         units "seconds";
         type union {
           type string {
             pattern "<.*>|$.*";
           }
           type uint32 {
             range "10 .. 86400";
           }
         }
       }
       leaf unavailable-server {
         description "How often should a server that is marked as unavailable be checked for availablility";
         default "32";
         units "seconds";
         type union {
           type string {
             pattern "<.*>|$.*";
           }
           type uint32 {
             range "10 .. 86400";
           }
         }
       }
     }
     leaf transaction-timeout {
       description "A server is assumed to be unavailable when a keepalive message was not answered in this time";
       default "32";
       units "seconds";
       type union {
         type string {
           pattern "<.*>|$.*";
         }
         type uint32 {
           range "10 .. 32";
         }
       }
     }
   }
   grouping routing-destination-cluster {
     leaf name {
       type string {
         length "1 .. 256";
       }
     }
     uses apply-advanced;
     list server {
       key name;
       ordered-by user;
       max-elements 25;
       leaf name {
         description "Server name";
         type string {
           length "1 .. 256";
         }
       }
       uses apply-advanced;
       leaf priority {
         description "Defines the redundency order";
         default "1";
         type union {
           type uint16;
           type string {
             pattern "<.*>|$.*";
           }
         }
       }
       leaf weight {
         description "Defines the load balancing ratio";
         default "1";
         type union {
           type uint16;
           type string {
             pattern "<.*>|$.*";
           }
         }
       }
     }
   }
   grouping routing-destination-server {
     leaf name {
       type string {
         length "1 .. 256";
       }
     }
     uses apply-advanced;
     container address {
       description "Server's address";
       presence "enable address";
       uses routing-destination-address;
     }
     leaf service-point {
       description "Exit point";
       type string;
     }
     leaf admission-control {
       description "Admission control profile for the server";
       type string;
     }
     leaf availability-check-profile {
       description "Availability check profile for the server";
       type string {
         length "1 .. 256";
       }
     }
   }
   grouping routing-destination-address {
     leaf ip4-address {
       description "IP address";
       type jt:ipaddr;
     }
     leaf port {
       description "Port number";
       default "5060";
       type union {
         type string {
           pattern "<.*>|$.*";
         }
         type uint32 {
           range "0 .. 65535";
         }
       }
     }
     container transport-protocol {
       description "Transport protocol";
       uses transport_protocol;
     }
   }
   grouping saegw-names {
     description "SAE gateway name";
     leaf name {
       description "SAE gateway Name";
       type string {
         length "1 .. 64";
       }
     }
     uses apply-advanced;
     container system {
       description "System resource configuration";
       uses apply-advanced;
       container anchor-pfes {
         presence "enable anchor-pfes";
         uses anchor-pfes-type;
       }
       container class-of-service {
         description "System CoS configuration";
         uses apply-advanced;
         container reserved-bandwidth {
           description "CoS bandwidth reservation";
           uses apply-advanced;
           leaf express {
             description "Percentage of bandwidth reserved for express traffic";
             units "percent";
             type union {
               type string {
                 pattern "<.*>|$.*";
               }
               type uint16 {
                 range "1 .. 100";
               }
             }
           }
           leaf gbr {
             description "Percentage of bandwidth reserved for gbr traffic";
             units "percent";
             type union {
               type string {
                 pattern "<.*>|$.*";
               }
               type uint16 {
                 range "1 .. 100";
               }
             }
           }
         }
         container downlink-dscp-to-forwarding-class {
           description "Downlink DSCP to forwarding-class configuration";
           uses apply-advanced;
           list classifier {
             key name;
             ordered-by user;
             description "CoS BA classifier";
             max-elements 16;
             uses classifier-names;
           }
         }
         container downlink-dscp-to-egress-forwarding-class {
           description "Downlink DSCP to egress-forwarding-class configuration";
           uses apply-advanced;
           list classifier {
             key name;
             ordered-by user;
             description "CoS BA classifier";
             max-elements 16;
             uses classifier-names;
           }
         }
       }
       leaf service-mode {
         description "Service mode";
         type enumeration {
           enum "maintenance" {
             description "Maintenance mode";
           }
         }
       }
     }
     container control-plane-peers {
       description "Control plane peers";
       uses apply-advanced;
       leaf-list local-address {
         ordered-by user;
         description "IPv6 or IPv4 or both addresses of the local end of the PFCP connection";
         type jt:ipaddr;
         max-elements 1;
       }
       leaf routing-instance {
         description "Local routing instance of the PFCP";
         type string {
         }
       }
       leaf heartbeat-interval {
         description "Time between two successive heartbeat requests";
         units "seconds";
         type union {
           type string {
             pattern "<.*>|$.*";
           }
           type uint16 {
             range "60 .. 255";
           }
         }
       }
       leaf path-management {
         description "Enable/disable origination of heartbeat message requests to control peers";
         type enumeration {
           enum "enable" {
             description "Enable parameter";
           }
           enum "disable" {
             description "Disable parameter";
           }
         }
       }
       leaf n3-requests {
         description "Number of retries of PFCP request messages upon t3-response timeout";
         type union {
           type string {
             pattern "<.*>|$.*";
           }
           type uint16 {
             range "1 .. 255";
           }
         }
       }
       leaf t3-response {
         description "Waiting time of gateway before retrying a PFCP signaling-request upon response timeout";
         units "seconds";
         type union {
           type string {
             pattern "<.*>|$.*";
           }
           type uint16 {
             range "1 .. 255";
           }
         }
       }
       leaf response-cache-timeout {
         description "Configure the timeout for the PFCP response cache";
         units "seconds";
         type union {
           type string {
             pattern "<.*>|$.*";
           }
           type uint16 {
             range "0 .. 255";
           }
         }
       }
       container apn-services {
         description "Access point name services name";
         uses apply-advanced;
         list apns {
           key name;
           ordered-by user;
           max-elements 512;
           uses apn-services-names;
         }
       }
       list peer-groups {
         key name;
         ordered-by user;
         description "Peer groups name";
         max-elements 256;
         uses control-peer-groups;
       }
     }
     container access-network-peers {
       description "Data plane peers";
       uses apply-advanced;
       leaf-list local-address {
         ordered-by user;
         description "IPv4 address of the local end of the GTP-U connection";
         type jt:ipv4addr;
         max-elements 1;
       }
       leaf routing-instance {
         description "Local routing instance of the GTP-U";
         type string {
         }
       }
       leaf echo-interval {
         description "Time between origination of two successive echo requests";
         units "seconds";
         type union {
           type string {
             pattern "<.*>|$.*";
           }
           type uint16 {
             range "60 .. 255";
           }
         }
       }
       leaf path-management {
         description "Enable/disable origination of echo requests to access peers";
         type enumeration {
           enum "enable" {
             description "Enable parameter";
           }
           enum "disable" {
             description "Disable parameter";
           }
         }
       }
       leaf n3-requests {
         description "Number of retries of peer management request messages upon t3-response timeout";
         type union {
           type string {
             pattern "<.*>|$.*";
           }
           type uint16 {
             range "1 .. 5";
           }
         }
       }
       leaf t3-response {
         description "Waiting time of gateway before retrying peer management request upon response timeout";
         units "seconds";
         type union {
           type string {
             pattern "<.*>|$.*";
           }
           type uint16 {
             range "1 .. 5";
           }
         }
       }
       list peer-groups {
         key name;
         ordered-by user;
         description "Peer groups name";
         max-elements 4000;
         uses access-peer-groups;
       }
     }
     container core-network-peers {
       description "Core-side GTP-U peers";
       uses apply-advanced;
       leaf-list local-address {
         ordered-by user;
         description "IPv4 address of the local end of the GTP-U connection";
         type jt:ipv4addr;
         max-elements 1;
       }
       leaf routing-instance {
         description "Local routing instance of the GTP-U connection";
         type string {
         }
       }
       leaf echo-interval {
         description "Time between origination of two echo requests";
         units "seconds";
         type union {
           type string {
             pattern "<.*>|$.*";
           }
           type uint16 {
             range "60 .. 255";
           }
         }
       }
       leaf path-management {
         description "Enable/disable origination of echo requests to core peers";
         type enumeration {
           enum "enable" {
             description "Enable parameter";
           }
           enum "disable" {
             description "Disable parameter";
           }
         }
       }
       leaf n3-requests {
         description "Number of unanswered echo requests for path failure";
         type union {
           type string {
             pattern "<.*>|$.*";
           }
           type uint16 {
             range "1 .. 5";
           }
         }
       }
       leaf t3-response {
         description "Time between resending unanswered echo requests";
         units "seconds";
         type union {
           type string {
             pattern "<.*>|$.*";
           }
           type uint16 {
             range "1 .. 5";
           }
         }
       }
       list peer-groups {
         key name;
         ordered-by user;
         description "Peer groups name";
         max-elements 4000;
         uses core-peer-groups;
       }
     }
   }
   grouping access-peer-groups {
     description "Peer-group name";
     leaf name {
       description "Peer group name";
       type string {
         length "1 .. 64";
       }
     }
     uses apply-advanced;
     container peer {
       presence "enable peer";
       uses apply-advanced;
       leaf-list address {
         ordered-by user;
         description "IPv4 address or prefix value of access network peer";
         type jt:ipv4prefix;
       }
       leaf hostname {
         description "Name of the access network peer";
         type string {
           length "1 .. 256";
         }
       }
     }
     leaf routing-instance {
       description "Routing-instance of GPT-U connection";
       type string {
       }
     }
   }
   grouping anchor-pfes-type {
     description "Anchor PFE's configuration";
     uses apply-advanced;
     list interface {
       key name;
       ordered-by user;
       description "Anchor PFE interface configuration";
       leaf name {
         description "Interface name";
         type string {
           length "1 .. 60";
         }
       }
       uses apply-advanced;
     }
   }
   grouping apn-services-names {
     description "APN services configuration";
     leaf name {
       description "APN Services Name";
       type string {
       }
     }
     uses apply-advanced;
     leaf mobile-interface {
       description "Mobile interface name";
       type string {
         length "1 .. 60";
       }
     }
   }
   grouping classifier-names {
     description "CoS BA classifier";
     leaf name {
       description "Name of classifier to be applied";
       type string {
         length "1 .. 64";
       }
     }
     uses apply-advanced;
     list routing-instance {
       key name;
       ordered-by user;
       leaf name {
         description "Routing instance the classifier applies to";
         type string {
         }
       }
       uses apply-advanced;
     }
   }
   grouping control-peer-groups {
     description "Peer-group name";
     leaf name {
       description "Peer group name";
       type string {
         length "1 .. 64";
       }
     }
     uses apply-advanced;
     container peer {
       presence "enable peer";
       description "Peer address and hostname";
       uses apply-advanced;
       leaf-list address {
         ordered-by user;
         description "IPv4 or IPv6 address or prefix value of control plane peer";
         type jt:ipprefix;
       }
       leaf hostname {
         description "Name of the control plane peer";
         type string {
           length "1 .. 256";
         }
       }
     }
     leaf initiate-association {
       description "Start node association message to control plane peer";
       type empty;
     }
     leaf routing-instance {
       description "Local routing instance of the PFCP";
       type string {
       }
     }
     leaf heartbeat-interval {
       description "Time between origination of two successive heartbeat requests";
       units "seconds";
       type union {
         type string {
           pattern "<.*>|$.*";
         }
         type uint16 {
           range "60 .. 255";
         }
       }
     }
     leaf path-management {
       description "Enable/disable origination of heartbeat message requests to control peers";
       type enumeration {
         enum "enable" {
           description "Enable parameter";
         }
         enum "disable" {
           description "Disable parameter";
         }
       }
     }
     leaf n3-requests {
       description "Number of retries of PFCP request messages upon t3-response timeout";
       type union {
         type string {
           pattern "<.*>|$.*";
         }
         type uint16 {
           range "1 .. 255";
         }
       }
     }
     leaf t3-response {
       description "Waiting time of gateway before retrying a PFCP signaling-request upon response timeout";
       units "seconds";
       type union {
         type string {
           pattern "<.*>|$.*";
         }
         type uint16 {
           range "1 .. 255";
         }
       }
     }
   }
   grouping core-peer-groups {
     description "Peer-group name";
     leaf name {
       description "Peer group name";
       type string {
         length "1 .. 64";
       }
     }
     uses apply-advanced;
     container peer {
       presence "enable peer";
       uses apply-advanced;
       leaf-list address {
         ordered-by user;
         description "IPv4 address or prefix value of core network peer";
         type jt:ipv4prefix;
       }
       leaf hostname {
         description "Name of the core network peer";
         type string {
           length "1 .. 256";
         }
       }
     }
     leaf routing-instance {
       description "Routing-instance of GPT-U connection";
       type string {
       }
     }
   }
   grouping secintel-category-disable {
     description "Security intelligence category";
     leaf name {
       description "Name of security intelligence category";
       type enumeration {
         enum "IPFilter" {
           description "IPFilter";
         }
         enum "GeoIP" {
           description "GeoIP";
         }
         enum "CC" {
           description "Command and control";
         }
         enum "Blacklist" {
           description "Blacklist";
         }
         enum "Whitelist" {
           description "Whitelist";
         }
         enum "Infected-Hosts" {
           description "Infected-Hosts";
         }
         enum "SecProfiling" {
           description "SecProfiling";
         }
         enum "DNS" {
           description "DNS";
         }
       }
     }
     uses apply-advanced;
     container disable {
       presence "enable disable";
       description "To disable category for feed update";
     }
   }
   grouping secintel-policy-setting {
     description "Security intelligence policy setting";
     leaf name {
       description "Security intelligence policy name";
       type string {
         length "1 .. 63";
       }
     }
     uses apply-advanced;
     leaf description {
       description "Text description of policy";
       type string {
         length "1 .. 900";
       }
     }
     list category-profiles {
       key name;
       ordered-by user;
       description "Security intelligence category profiles";
       leaf name {
         description "Name of security intelligence category";
         type enumeration {
           enum "IPFilter" {
             description "IPFilter";
           }
           enum "GeoIP" {
             description "GeoIP";
           }
           enum "CC" {
             description "Command and control";
           }
           enum "Infected-Hosts" {
             description "Infected-Hosts";
           }
           enum "DNS" {
             description "DNS";
           }
         }
       }
       uses apply-advanced;
       leaf profile-name {
         description "Name of profile";
         type string;
       }
     }
   }
   grouping secintel-profile-setting {
     description "Security intelligence profile settings";
     leaf name {
       description "Security intelligence profile name";
       type string {
         length "1 .. 63";
       }
     }
     uses apply-advanced;
     leaf description {
       description "Text description of profile";
       type string {
         length "1 .. 900";
       }
     }
     leaf category {
       description "Profile category name";
       type string;
     }
     list rule {
       key name;
       ordered-by user;
       description "Profile rule name";
       uses secintel-profile-rule;
     }
     container default-rule {
       presence "enable default-rule";
       description "Profile default rule";
       uses apply-advanced;
       container then {
         presence "enable then";
         description "Profile default rule action";
         uses apply-advanced;
         container action {
           description "Security intelligence profile action";
           uses apply-advanced;
           choice action {
             case case_1 {
               leaf permit {
                 description "Permit action";
                 type empty;
               }
             }
             case case_2 {
               container block {
                 description "Block action";
                 uses apply-advanced;
                 choice action {
                   case case_1 {
                     container drop {
                       presence "enable drop";
                       description "Drop packet";
                     }
                   }
                   case case_2 {
                     container close {
                       presence "enable close";
                       description "Close session";
                       uses apply-advanced;
                       container http {
                         description "Http content for block action";
                         uses apply-advanced;
                         choice http-choice {
                           case case_1 {
                             leaf file {
                               description "File name for http response to client";
                               type string;
                             }
                           }
                           case case_2 {
                             leaf message {
                               description "Block message to client";
                               type string;
                             }
                           }
                           case case_3 {
                             leaf redirect-url {
                               description "Redirect url to client";
                               type string {
                                 length "1 .. 1023";
                               }
                             }
                           }
                         }
                       }
                     }
                   }
                 }
               }
             }
             case case_3 {
               container recommended {
                 presence "enable recommended";
                 description "Recommended action from feed server";
               }
             }
             case case_4 {
               leaf sinkhole {
                 description "DNS sinkhole for DNS profile";
                 type empty;
               }
             }
           }
         }
         choice log-choice {
           leaf log {
             description "Log security intelligence block action";
             type empty;
           }
           leaf no-log {
             description "Don't log security intelligence block action";
             type empty;
           }
         }
       }
     }
   }
   grouping secintel-profile-rule {
     description "Security intelligence profile rule";
     leaf name {
       description "Profile rule name";
       type string {
         length "1 .. 63";
       }
     }
     uses apply-advanced;
     container match {
       description "Profile matching feed name and threat levels";
       uses apply-advanced;
       list feed-name {
         key name;
         ordered-by user;
         description "Profile matching feed name";
         max-elements 32;
         leaf name {
           type string {
             length "1 .. 63";
           }
         }
         uses apply-advanced;
       }
       leaf-list threat-level {
         ordered-by user;
         description "Profile matching threat levels, higher number is more severe";
         type union {
           type uint32;
           type string {
             pattern "<.*>|$.*";
           }
         }
       }
     }
     container then {
       description "Profile action and log";
       uses apply-advanced;
       container action {
         description "Security intelligence profile action";
         uses apply-advanced;
         choice action {
           case case_1 {
             leaf permit {
               description "Permit action";
               type empty;
             }
           }
           case case_2 {
             container block {
               description "Block action";
               uses apply-advanced;
               choice action {
                 case case_1 {
                   container drop {
                     presence "enable drop";
                     description "Drop packet";
                   }
                 }
                 case case_2 {
                   container close {
                     presence "enable close";
                     description "Close session";
                     uses apply-advanced;
                     container http {
                       description "Http content for block action";
                       uses apply-advanced;
                       choice http-choice {
                         case case_1 {
                           leaf file {
                             description "File name for http response to client";
                             type string;
                           }
                         }
                         case case_2 {
                           leaf message {
                             description "Block message to client";
                             type string;
                           }
                         }
                         case case_3 {
                           leaf redirect-url {
                             description "Redirect url to client";
                             type string {
                               length "1 .. 1023";
                             }
                           }
                         }
                       }
                     }
                   }
                 }
               }
             }
           }
           case case_3 {
             container recommended {
               presence "enable recommended";
               description "Recommended action from feed server";
             }
           }
           case case_4 {
             leaf sinkhole {
               description "DNS sinkhole for DNS profile";
               type empty;
             }
           }
         }
       }
       container log {
         presence "enable log";
         description "Log security intelligence block action";
       }
     }
   }
   grouping secintel-traceoptions {
     description "Security intelligence trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "feed" {
             description "Trace feed operation";
           }
           enum "ipc" {
             description "Trace ipc module";
           }
           enum "blacklist" {
             description "Trace security intelligence Blacklist category";
           }
           enum "cc" {
             description "Trace security intelligence CC category";
           }
           enum "infected-hosts" {
             description "Trace security intelligence Infected-Hosts category";
           }
           enum "control" {
             description "Trace control plane";
           }
           enum "infrastucture" {
             description "Trace infrastucture functions";
           }
           enum "jwas" {
             description "Trace security intelligence JWAS category";
           }
           enum "plugin" {
             description "Trace security intelligence plugin services";
           }
           enum "whitelist" {
             description "Trace security intelligence Whitelist category";
           }
           enum "secprofiling" {
             description "Trace security intelligence Secprofiling category";
           }
         }
       }
     }
   }
   grouping security_intelligence_feeds {
     description "Specify the feed post action";
     uses apply-advanced;
     container add-source-ip-to-feed {
       description "Add Source IP to Feed";
       uses apply-advanced;
       leaf name-of-feed {
         description "Specify the desired feed-name";
         type string {
           length "1 .. 64";
         }
       }
     }
     container add-destination-ip-to-feed {
       description "Add Destination IP to Feed";
       uses apply-advanced;
       leaf name-of-feed {
         description "Specify the desired feed-name";
         type string {
           length "1 .. 64";
         }
       }
     }
     container add-source-identity-to-feed {
       description "Add Source Identity to Feed";
       uses apply-advanced;
       leaf name-of-feed {
         description "Specify the desired feed-name";
         type string {
           length "1 .. 64";
         }
       }
     }
     container add-destination-identity-to-feed {
       description "Add Destination Identity to Feed";
       uses apply-advanced;
       leaf name-of-feed {
         description "Specify the desired feed-name";
         type string {
           length "1 .. 64";
         }
       }
     }
   }
   grouping server-connection-type {
     description "Connection parameters per server";
     uses apply-advanced;
     leaf address {
       description "IP address";
       type string;
     }
     leaf ca-certificate {
       description "Ca-certificate file name";
       type string {
         length "1 .. 256";
       }
     }
     leaf client-id {
       description "Client ID for OAuth2 grant";
       type string {
         length "1 .. 64";
       }
     }
     leaf client-secret {
       description "Client secret for OAuth2 grant";
       type string {
         length "1 .. 128";
       }
     }
   }
   grouping service_device_pool_object {
     leaf name {
       description "Service device pool name";
       type string {
         length "1 .. 63";
       }
     }
     uses apply-advanced;
     list interface {
       key name;
       ordered-by user;
       description "Service device name";
       leaf name {
         type string;
       }
       uses apply-advanced;
     }
   }
   grouping service_interface_pool_object {
     leaf name {
       description "Service interface pool name";
       type string {
         length "1 .. 63";
       }
     }
     uses apply-advanced;
     list interface {
       key name;
       ordered-by user;
       description "Service interface name";
       leaf name {
         type union {
           type jt:interface-unit;
           type string {
             pattern "<.*>|$.*";
           }
         }
       }
       uses apply-advanced;
     }
   }
   grouping service_point_type {
     leaf name {
       description "Service point name";
       type string;
     }
     uses apply-advanced;
     leaf service-point-type {
       description "Service point type";
       default "sip";
       type enumeration {
         enum "sip" {
         }
       }
     }
     container transport-details {
       presence "enable transport-details";
       description "IP address, port number and transport-protocols for the service-point";
       leaf port-number {
         description "Port number";
         type union {
           type string {
             pattern "<.*>|$.*";
           }
           type uint32 {
             range "0 .. 65535";
           }
         }
       }
       leaf ip-address {
         description "IP address";
         type jt:ipaddr;
       }
       leaf tcp {
         description "Transport protocol - TCP";
         type empty;
       }
       leaf udp {
         description "Transport protocol - UDP";
         type empty;
       }
       leaf fqdn {
         description "Fully Qualified Domain Name";
         type string {
           length "1 .. 128";
         }
       }
     }
     leaf service-interface {
       description "Associated service interface";
       type union {
         type jt:interface-unit;
         type string {
           pattern "<.*>|$.*";
         }
       }
     }
     container service-policies {
       presence "enable service-policies";
       uses service_policies_type;
     }
     leaf default-media-realm {
       description "Use this realm for allocating media resources for calls initiated to/from this service-point";
       type string {
         length "1 .. 4";
       }
     }
   }
   grouping service_policies_type {
     uses apply-advanced;
     leaf-list new-transaction-input-policies {
       ordered-by user;
       description "New transaction input policy name";
       type string;
       max-elements 10;
     }
     leaf-list new-transaction-output-policies {
       ordered-by user;
       description "New transaction output policy name";
       type string;
       max-elements 10;
     }
     leaf-list new-registration-input-policies {
       ordered-by user;
       description "New registration input policy name";
       type string;
       max-elements 10;
     }
     leaf-list new-call-usage-input-policies {
       ordered-by user;
       description "New call usage input policy name";
       type string;
       max-elements 10;
     }
     leaf-list new-call-usage-output-policies {
       ordered-by user;
       description "New call usage output policy name";
       type string;
       max-elements 10;
     }
   }
   grouping services-pcef {
     description "PCEF configuration";
     uses apply-advanced;
     container traceoptions {
       description "Trace options related to PCEF";
       uses pcef-traceoptions;
     }
     container event-trigger-profiles {
       description "Event trigger profiles";
       uses apply-advanced;
       list profile {
         key name;
         uses evt-trigger-profile;
       }
     }
     container flow-descriptions {
       description "PCC flow descriptions";
       uses apply-advanced;
       list definition {
         key name;
         uses pcc-flow;
       }
     }
     container pcc-action-profiles {
       description "PCC action profiles";
       uses apply-advanced;
       list definition {
         key name;
         uses pcc-action-profile;
       }
     }
     container pcc-rules {
       description "PCC rules";
       uses apply-advanced;
       list definition {
         key name;
         uses pcc-rule;
       }
     }
     container pcc-rulebases {
       description "PCC rulebases";
       uses apply-advanced;
       list definition {
         key name;
         ordered-by user;
         uses pcc-rulebase;
       }
     }
     container profile {
       description "PCEF profiles";
       uses apply-advanced;
       list definition {
         key name;
         ordered-by user;
         uses pcef-profiles;
       }
     }
   }
   grouping evt-trigger-profile {
     description "Event trigger profile";
     leaf name {
       description "Event trigger profile name";
       type string {
         length "1 .. 63";
       }
     }
     uses apply-advanced;
     leaf rat-change {
       description "RAT change trigger";
       type empty;
     }
     leaf sgsn-change {
       description "SGSN change trigger";
       type empty;
     }
     leaf plmn-change {
       description "PLMN change trigger";
       type empty;
     }
     leaf ip-can-change {
       description "IP-CAN change trigger";
       type empty;
     }
     leaf tft-change {
       description "TFT change trigger";
       type empty;
     }
     leaf rai-change {
       description "RAI change trigger";
       type empty;
     }
     leaf user-location-change {
       description "User location change";
       type empty;
     }
     leaf ue-timezone-change {
       description "UE timezone change";
       type empty;
     }
   }
   grouping pcc-action-profile {
     description "PCC action profiles";
     leaf name {
       description "PCC action profile identifier";
       type string {
         length "1 .. 63";
       }
     }
     uses apply-advanced;
     leaf logging-rule {
       description "Policy based logging rule name";
       type string {
         length "1 .. 63";
       }
     }
     container maximum-bit-rate {
       presence "enable maximum-bit-rate";
       description "Maximum bit rate";
       leaf uplink {
         description "Maximum bit rate uplink";
         default "0";
         units "kilobits";
         type union {
           type string {
             pattern "<.*>|$.*";
           }
           type uint32 {
             range "0 .. 6144000";
           }
         }
       }
       leaf downlink {
         description "Maximum bit rate downlink";
         default "0";
         units "kilobits";
         type union {
           type string {
             pattern "<.*>|$.*";
           }
           type uint32 {
             range "0 .. 6144000";
           }
         }
       }
     }
     container burst-size {
       presence "enable burst-size";
       description "Burst Size";
       uses apply-advanced;
       leaf uplink {
         description "Burst size uplink";
         units "bytes";
         type union {
           type string {
             pattern "<.*>|$.*";
           }
           type uint32 {
             range "1500 .. 1500000000";
           }
         }
       }
       leaf downlink {
         description "Burst size downlink";
         units "bytes";
         type union {
           type string {
             pattern "<.*>|$.*";
           }
           type uint32 {
             range "1500 .. 1500000000";
           }
         }
       }
     }
     leaf gate-status {
       description "Control gate status";
       type enumeration {
         enum "uplink" {
           description "Enable uplink traffic";
         }
         enum "downlink" {
           description "Enable downlink traffic";
         }
         enum "uplink-downlink" {
           description "Enable uplink and downlink traffic";
         }
         enum "disable-both" {
           description "Disable any traffic";
         }
       }
     }
     container charging {
       description "Charing related configuration";
       uses apply-advanced;
       leaf rating-group {
         description "Rating group";
         type union {
           type string {
             pattern "<.*>|$.*";
           }
           type uint32 {
             range "0 .. 4294967294";
           }
         }
       }
       leaf service-identifier {
         description "Service identifier";
         default "0";
         type union {
           type string {
             pattern "<.*>|$.*";
           }
           type uint32 {
             range "0 .. 4294967294";
           }
         }
       }
       leaf charging-method {
         description "Charging method";
         type enumeration {
           enum "online" {
             description "Use online charging method";
           }
           enum "offline" {
             description "Use offline charging method";
           }
           enum "both" {
             description "Use online and offline charging method";
           }
           enum "none" {
             description "Use no charging";
           }
         }
       }
       leaf measurement-method {
         description "Charging measure method";
         default "volume-time";
         type enumeration {
           enum "none" {
             description "No default measuring method for charging";
           }
           enum "volume" {
             description "Volume based charging";
           }
           enum "time" {
             description "Time based charging";
           }
           enum "volume-time" {
             description "Volume and time based charging";
           }
           enum "event" {
             description "Event based charging";
           }
         }
       }
       container application-function-record-info {
         presence "enable application-function-record-info";
         description "Application function record information";
         uses apply-advanced;
         leaf af-charging-identifier {
           description "Application function charging identifier";
           type string {
             length "1 .. 63";
           }
         }
       }
       leaf service-id-level-reporting {
         description "Toggle service-id level reporting";
         type empty;
       }
     }
     container redirect {
       description "Redirect to different destination";
       uses apply-advanced;
       leaf url {
         description "Redirect url name";
         type string {
           length "1 .. 512";
         }
       }
     }
     container forwarding-class {
       description "Classify packet to forwarding class";
       uses apply-advanced;
       leaf class-name {
         description "Forwarding class name";
         type string {
         }
       }
     }
     container steering {
       description "Steering information";
       uses apply-advanced;
       container routing-instance {
         description "Routing instance information";
         leaf uplink {
           description "Instance name uplink";
           type string;
         }
         leaf downlink {
           description "Instance name downlink";
           type string;
         }
       }
       container path {
         description "HTTP steering information";
         choice ip-address-type {
           case case_1 {
             leaf ipv4-address {
               description "IPv4 address of the steering destination";
               type jt:ipv4prefix;
             }
           }
           case case_2 {
             leaf ipv6-address {
               description "IPv6 address of the steering destination";
               type jt:ipv6prefix;
             }
           }
         }
       }
       leaf keep-existing-steering {
         description "Keep existing steering";
         type empty;
       }
     }
     container hcm-profile {
       description "HCM Profile";
       uses apply-advanced;
       leaf profile-name {
         description "HCM Profile Name";
         type string;
       }
     }
     leaf monitoring-key {
       description "Usage Monitoring key";
       type string {
         length "1 .. 63";
       }
     }
   }
   grouping pcc-flow {
     description "Configure PCC flow";
     leaf name {
       description "PCC flow identifier";
       type string {
         length "1 .. 63";
       }
     }
     uses apply-advanced;
     leaf direction {
       description "PCC flow direction";
       type enumeration {
         enum "downlink" {
           description "Downlink direction";
         }
         enum "uplink" {
           description "Uplink direction";
         }
         enum "both" {
           description "Both uplink and downlink directons";
         }
       }
     }
     leaf protocol {
       description "PCC flow IPv4 protocol";
       type union {
         type string {
           pattern "<.*>|$.*";
         }
         type uint8 {
           range "0 .. 255";
         }
       }
     }
     leaf-list local-ports {
       description "Local port or port list";
       type union {
         type string {
           pattern "<.*>|$.*";
         }
         type uint16 {
           range "1 .. 65535";
         }
       }
       max-elements 3;
     }
     list local-port-range {
       key "low high";
       ordered-by user;
       description "Local port range";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     leaf-list remote-ports {
       description "Remote port or port list";
       type union {
         type string {
           pattern "<.*>|$.*";
         }
         type uint16 {
           range "1 .. 65535";
         }
       }
       max-elements 3;
     }
     list remote-port-range {
       key "low high";
       ordered-by user;
       description "Remote port range";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     container remote-address {
       description "Remote address";
       choice ip-address-type {
         case case_1 {
           leaf ipv4-address {
             description "IPv4 address for the flow";
             type jt:ipv4prefix;
           }
         }
         case case_2 {
           leaf ipv6-address {
             description "IPv6 address for the flow";
             type jt:ipv6prefix;
           }
         }
       }
     }
   }
   grouping pcc-rule {
     description "PCC rules configuration";
     leaf name {
       description "PCC Rule identifier";
       type string {
       }
     }
     uses apply-advanced;
     container from {
       description "Aggregate of flows using same pcc-action-profile";
       uses apply-advanced;
       list flows {
         key name;
         ordered-by user;
         description "Associate PCC Flows";
         max-elements 64;
         leaf name {
           description "PCC Flow identifier";
           type string {
             length "1 .. 63";
           }
         }
         uses apply-advanced;
       }
       list applications {
         key name;
         ordered-by user;
         description "Associated application signature names";
         max-elements 10;
         leaf name {
           description "Signature names";
           type string {
             length "1 .. 63";
           }
         }
         uses apply-advanced;
       }
       list nested-applications {
         key name;
         ordered-by user;
         description "Associated nested application signature names";
         status deprecated;
         max-elements 10;
         leaf name {
           description "Nested application signature names";
           type string {
             length "1 .. 63";
           }
         }
         uses apply-advanced;
       }
       list application-groups {
         key name;
         ordered-by user;
         description "Application Group signature names";
         max-elements 10;
         leaf name {
           description "Application group names";
           type string {
             length "1 .. 63";
           }
         }
         uses apply-advanced;
       }
     }
     container then {
       description "Specified pcc-action-profile";
       uses apply-advanced;
       leaf pcc-action-profile {
         description "PCC Action profile name";
         type string {
           length "1 .. 63";
         }
       }
     }
   }
   grouping pcc-rulebase {
     description "PCC rulebases";
     leaf name {
       description "PCC Rulebase identifier";
       type string {
       }
     }
     uses apply-advanced;
     list pcc-rule {
       key name;
       ordered-by user;
       max-elements 32;
       leaf name {
         description "PCC rule name";
         type string {
           length "1 .. 63";
         }
       }
       leaf precedence {
         description "PCC rule precedence";
         type union {
           type string {
             pattern "<.*>|$.*";
           }
           type uint16 {
             range "1 .. 4000";
           }
         }
       }
     }
   }
   grouping pcef-profiles {
     description "PCEF profiles";
     leaf name {
       description "PCEF profile name";
       type string {
         length "1 .. 63";
       }
     }
     uses apply-advanced;
     leaf control-byte-rating-group {
       description "Rating group id";
       type union {
         type string {
           pattern "<.*>|$.*";
         }
         type uint32 {
           range "0 .. 4294967294";
         }
       }
     }
     leaf unresolved-flow-action {
       description "Flow action";
       type enumeration {
         enum "forward" {
           description "Forward";
         }
         enum "drop" {
           description "Drop";
         }
       }
     }
     container maximum-per-pdn-service-flows {
       description "Max service flows per PDN";
       leaf num {
         description "Value";
         type union {
           type uint32;
           type string {
             pattern "<.*>|$.*";
           }
         }
       }
     }
     container dynamic-policy-control {
       description "Dynamic policy control";
       uses apply-advanced;
       container pcc-rules {
         description "PCC rules association";
         uses apply-advanced;
         list rule-assoc {
           key name;
           ordered-by user;
           max-elements 64;
           uses profile-rule-assoc;
         }
       }
       list pcc-rulebases {
         key name;
         ordered-by user;
         description "PCC rulebase association";
         leaf name {
           description "PCC rulebase name";
           type string {
             length "1 .. 63";
           }
         }
         uses apply-advanced;
       }
       leaf diameter-profile {
         description "Diameter profile name";
         type string {
           length "1 .. 63";
         }
       }
       leaf event-trigger-profile {
         description "Event trigger profile name";
         type string {
           length "1 .. 63";
         }
       }
       leaf session-failover-not-supported {
         description "Session failover not supported";
         type empty;
       }
       leaf release {
         description "To override Gx release to R8|R9";
         type enumeration {
           enum "r8" {
             description "Gx release 8";
           }
           enum "r9" {
             description "Gx release 9";
           }
         }
       }
     }
     container static-policy-control {
       description "Static policy control";
       uses apply-advanced;
       container pcc-rules {
         description "PCC rules association";
         uses apply-advanced;
         list rule-assoc {
           key name;
           ordered-by user;
           max-elements 64;
           uses profile-static-rule-association;
         }
       }
       list pcc-rulebases {
         key name;
         ordered-by user;
         description "PCC rulebase association";
         leaf name {
           description "PCC rulebase name";
           type string {
             length "1 .. 63";
           }
         }
         uses apply-advanced;
         leaf time-of-day-profile {
           description "Time of day profile name";
           type string {
             length "1 .. 63";
           }
         }
       }
       leaf-list activate-dedicated-bearers {
         description "Enable dedicated bearer activation on initial attach with qci";
         type union {
           type string {
             pattern "<.*>|$.*";
           }
           type uint8 {
             range "1 .. 9";
           }
         }
         max-elements 9;
       }
     }
     container aaa-policy-control {
       description "AAA policy control";
       uses apply-advanced;
       leaf profile {
         description "AAA profile name";
         type string {
           length "1 .. 32";
         }
       }
       leaf user-password {
         description "User password";
         type string {
           length "1 .. 32";
         }
       }
       list pcc-rulebases {
         key name;
         ordered-by user;
         description "PCC rulebase association";
         leaf name {
           description "PCC rulebase name";
           type string {
             length "1 .. 63";
           }
         }
         uses apply-advanced;
       }
     }
   }
   grouping pcef-traceoptions {
     description "Trace options related to PCEF";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "high-availability" {
             description "Trace high availability events";
           }
           enum "debug" {
             description "Trace debug internal events";
           }
           enum "fsm" {
             description "Trace fsm events";
           }
           enum "tftmgr" {
             description "Trace tftmgr events";
           }
           enum "all" {
             description "Trace everything";
           }
         }
       }
     }
   }
   grouping profile-rule-assoc {
     leaf name {
       description "PCC rule name";
       type string {
         length "1 .. 63";
       }
     }
     leaf precedence {
       description "PCC rule precedence";
       type union {
         type string {
           pattern "<.*>|$.*";
         }
         type uint16 {
           range "1 .. 4000";
         }
       }
     }
   }
   grouping profile-static-rule-association {
     leaf name {
       description "PCC rule name";
       type string {
         length "1 .. 63";
       }
     }
     leaf precedence {
       description "PCC rule precedence";
       type union {
         type string {
           pattern "<.*>|$.*";
         }
         type uint16 {
           range "1 .. 4000";
         }
       }
     }
     leaf time-of-day-profile {
       description "Time of day profile name";
       type string {
         length "1 .. 63";
       }
     }
     container pcc-action-profile {
       description "PCC action profile association";
       status deprecated;
       leaf rules-action-profile {
         description "PCC action profile name";
         type string {
           length "1 .. 63";
         }
       }
     }
   }
   grouping session_timeout_type {
     uses apply-advanced;
     leaf tcp {
       description "Timeout value for tcp sessions";
       units "seconds";
       type union {
         type string {
           pattern "<.*>|$.*";
         }
         type uint32 {
           range "4 .. 86400";
         }
       }
     }
     leaf udp {
       description "Timeout value for udp sessions";
       units "seconds";
       type union {
         type string {
           pattern "<.*>|$.*";
         }
         type uint32 {
           range "4 .. 86400";
         }
       }
     }
     leaf ospf {
       description "Timeout value for ospf sessions";
       units "seconds";
       type union {
         type string {
           pattern "<.*>|$.*";
         }
         type uint32 {
           range "4 .. 86400";
         }
       }
     }
     leaf icmp {
       description "Timeout value for icmp sessions";
       units "seconds";
       type union {
         type string {
           pattern "<.*>|$.*";
         }
         type uint32 {
           range "4 .. 86400";
         }
       }
     }
     leaf icmp6 {
       description "Timeout value for icmp6 sessions";
       units "seconds";
       type union {
         type string {
           pattern "<.*>|$.*";
         }
         type uint32 {
           range "4 .. 86400";
         }
       }
     }
     leaf others {
       description "Timeout value for other sessions";
       units "seconds";
       type union {
         type string {
           pattern "<.*>|$.*";
         }
         type uint32 {
           range "4 .. 86400";
         }
       }
     }
   }
   grouping sfw_addr_object {
     leaf name {
       description "Match IP address";
       type string;
     }
     leaf except {
       description "Match address not in this prefix";
       type empty;
     }
   }
   grouping sfw_match_object {
     uses apply-advanced;
     list source-address {
       key name;
       ordered-by user;
       description "Match IP source address";
       uses sfw_addr_object;
     }
     list destination-address {
       key name;
       ordered-by user;
       description "Match IP destination address";
       uses sfw_addr_object;
     }
     container destination-port {
       presence "enable destination-port";
       uses apply-advanced;
       choice port_choice {
         case case_1 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
           }
         }
       }
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list applications {
       ordered-by user;
       description "Match one or more applications";
       type string;
     }
     list application-sets {
       key name;
       ordered-by user;
       description "Match one or more application sets";
       leaf name {
         type string {
           length "1 .. 63";
         }
       }
       uses apply-advanced;
     }
     leaf-list application {
       ordered-by user;
       type string;
     }
   }
   grouping sfw_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a stateful firewall term";
       leaf name {
         description "Term name";
         type string {
           length "1 .. 63";
         }
       }
       uses apply-advanced;
       container from {
         description "Define match criteria";
         uses sfw_match_object;
       }
       container then {
         description "Action to take if the 'from' condition is matched";
         uses apply-advanced;
         choice designation {
           case case_1 {
             leaf accept {
               description "Accept the packet";
               type empty;
             }
           }
           case case_2 {
             container discard {
               presence "enable discard";
               description "Discard the packet";
               uses apply-advanced;
             }
           }
           case case_3 {
             leaf reject {
               description "Reject the packet";
               type empty;
             }
           }
         }
         leaf-list allow-ip-options {
           ordered-by user;
           type string;
         }
         leaf syslog {
           description "System log information about the packet";
           type empty;
         }
         leaf skip-ids {
           description "No IDS processing will be done on a matching packet";
           type empty;
         }
       }
     }
   }
   grouping si-ip-address-list-object {
     leaf name {
       description "Name of ip-address list";
       type string {
         length "1 .. 64";
       }
     }
     uses apply-advanced;
     leaf-list ipv4 {
       ordered-by user;
       description "List of ipv4 addresses";
       type jt:ipv4addr;
     }
     leaf-list ipv6 {
       ordered-by user;
       description "List of ipv6 addresses";
       type jt:ipv6addr;
     }
   }
   grouping signaling-realm {
     description "Signaling realm";
     leaf name {
       description "Realm name";
       type string;
     }
     uses apply-advanced;
   }
   grouping sip_timers_type {
     uses apply-advanced;
     leaf inactive-call {
       description "Maximum time for signaling inactivity";
       default "86400";
       units "seconds";
       type union {
         type string {
           pattern "<.*>|$.*";
         }
         type uint32 {
           range "300 .. 86400";
         }
       }
     }
     leaf timer-c {
       description "Maximum time to wait for final response on invite";
       default "180";
       units "seconds";
       type union {
         type string {
           pattern "<.*>|$.*";
         }
         type uint32 {
           range "180 .. 300";
         }
       }
     }
   }
   grouping sm-traceoptions-type {
     description "Trace options for SAEGW SM";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "general" {
             description "Trace general events";
           }
           enum "state-machine" {
             description "Trace state-machine events";
           }
           enum "mirroring" {
             description "Trace mirroring events";
           }
           enum "all" {
             description "Trace everything";
           }
         }
       }
     }
   }
   grouping soft_gre_tunnel_group_object {
     leaf name {
       description "Tunnel group name";
       type string {
       }
     }
     uses apply-advanced;
     leaf source-address {
       description "Local address of tunnel";
       type jt:ipaddr;
     }
     list destination-networks {
       key name;
       ordered-by user;
       description "Create tunnels for routes in these destination networks";
       uses soft_gre_destination_network_object;
     }
     leaf service-interface {
       description "Pseudowire interface to use";
       type union {
         type jt:interface-unit;
         type string {
           pattern "<.*>|$.*";
         }
       }
     }
     leaf tunnel-idle-timeout {
       description "Time to tear down tunnel when idle";
       default "120";
       units "seconds";
       type union {
         type uint16;
         type string {
           pattern "<.*>|$.*";
         }
       }
     }
     leaf dynamic-profile {
       description "Dynamic profile for tunnel interface";
       type string {
         length "1 .. 80";
       }
     }
   }
   grouping soft_gre_destination_network_object {
     leaf name {
       description "Network prefix";
       type jt:ipprefix;
     }
     uses apply-advanced;
   }
   grouping softwires-object {
     description "Configure softwire feature";
     uses apply-advanced;
     list softwire-name {
       key name;
       description "Configure softwire object";
       uses softwire-option-type;
     }
     container softwire-types {
       description "Configure softwire objects";
       uses apply-advanced;
       list v6rd {
         key name;
         description "Configure v6rd object";
         uses softwire-option-type;
       }
       list ds-lite {
         key name;
         description "Configure ds-lite object";
         uses softwire-option-type;
       }
       list map-e {
         key name;
         ordered-by user;
         description "Configure Map-e object";
         uses map-e-domain;
       }
       list map-t {
         key name;
         ordered-by user;
         description "Configure Map-t object";
         uses map-t-domain;
       }
     }
     list map-e {
       key name;
       ordered-by user;
       description "Configure a MAP-E domain and domain rules";
       max-elements 1;
       uses map-e-domain;
     }
     container traceoptions {
       description "Trace options for Network Security DS-Lite";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Define a softwire rule set";
       uses sw-rule-set-object;
     }
   }
   grouping map-e-domain {
     description "Configure a MAP-E domain";
     leaf name {
       description "MAP-E domain name";
       type string {
         length "1 .. 11";
       }
     }
     uses apply-advanced;
     leaf confidentiality {
       description "Configure JUNOS MAP-E confidentiality";
       type empty;
     }
     leaf br-address {
       description "Ipv6 address of BR";
       type jt:unreadable;
     }
     container end-user-prefix {
       description "Configure end-user-prefix value or source interface for obtaining end-user-prefix";
       uses apply-advanced;
       leaf prefix-value {
         description "End user prefix";
         type jt:ipv6prefix;
       }
     }
     list rule {
       key name;
       ordered-by user;
       description "Configure a BMR or FMR rule for map-e ";
       max-elements 101;
       uses map-e-rule;
     }
     leaf role {
       description "Define a role of the MAP-E";
       type enumeration {
         enum "CE" {
           description "CE deployment";
         }
       }
     }
     leaf version {
       description "Define version of the MAP-E";
       type enumeration {
         enum "3" {
           description "Version 3: draft-ietf-softwire-map-03";
         }
       }
     }
   }
   grouping map-e-rule {
     description "Configure a MAP-E rule";
     leaf name {
       description "MAP-E rule name";
       type string {
         length "1 .. 11";
       }
     }
     uses apply-advanced;
     leaf rule-type {
       description "Define a rule type of MAP-E";
       type enumeration {
         enum "BMR" {
           description "Define BMR rule type";
         }
         enum "FMR" {
           description "Define FMR rule type";
         }
       }
     }
     leaf ipv4-prefix {
       description "Ipv4 prefix";
       type jt:unreadable;
     }
     leaf ipv6-prefix {
       description "Ipv6 prefix";
       type jt:unreadable;
     }
     leaf ea-bits-length {
       description "EA bits length";
       type union {
         type string {
           pattern "<.*>|$.*";
         }
         type uint32 {
           range "0 .. 48";
         }
       }
     }
     leaf psid-offset {
       description "PSID offset";
       type jt:unreadable;
     }
     leaf psid-len {
       description "PSID length";
       type union {
         type string {
           pattern "<.*>|$.*";
         }
         type uint32 {
           range "0 .. 16";
         }
       }
     }
     leaf mtu-v6 {
       description "MTU for the softwire tunnel";
       default "9192";
       type union {
         type string {
           pattern "<.*>|$.*";
         }
         type uint32 {
           range "1280 .. 9192";
         }
       }
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
     leaf v4-partial-reassembly {
       description "For higher number of fragments/reassembled packet size";
       type empty;
     }
   }
   grouping map-t-domain {
     description "Configure a MAP-T domain";
     leaf name {
       description "MAP-T domain name";
       type string {
         length "1 .. 11";
       }
     }
     uses apply-advanced;
     leaf dmr-address {
       description "Ipv6 address of DMR";
       type jt:ipv6prefix;
     }
     list rule {
       key name;
       ordered-by user;
       description "Configure a BMR rule for map-t ";
       max-elements 1;
       uses map-t-rule;
     }
   }
   grouping map-t-rule {
     description "Configure a MAP-T rule";
     leaf name {
       description "MAP-T rule name";
       type string {
         length "1 .. 11";
       }
     }
     uses apply-advanced;
     leaf ipv4-prefix {
       description "Ipv4 prefix";
       type jt:ipv4prefix;
     }
     leaf ipv6-prefix {
       description "Ipv6 prefix";
       type jt:ipv6prefix;
     }
     leaf ea-bits-length {
       description "EA bits length";
       type union {
         type string {
           pattern "<.*>|$.*";
         }
         type uint32 {
           range "0 .. 48";
         }
       }
     }
     leaf psid-offset {
       description "PSID offset";
       type union {
         type string {
           pattern "<.*>|$.*";
         }
         type uint32 {
           range "0 .. 16";
         }
       }
     }
     leaf psid-len {
       description "PSID length";
       type union {
         type string {
           pattern "<.*>|$.*";
         }
         type uint32 {
           range "0 .. 16";
         }
       }
     }
     leaf mtu-v6 {
       description "MTU for the softwire tunnel";
       default "9192";
       type union {
         type string {
           pattern "<.*>|$.*";
         }
         type uint32 {
           range "1280 .. 9192";
         }
       }
     }
   }
   grouping softwire-option-type {
     description "Configure softwire object";
     leaf name {
       description "DS-Lite/Softwire object name";
       type string {
         length "1 .. 23";
       }
     }
     uses apply-advanced;
     leaf softwire-concentrator {
       description "Concentrator address";
       type jt:ipaddr;
     }
     leaf softwire-type {
       description "Softwire-type";
       default "IPv4-in-IPv6";
       type enumeration {
         enum "IPv4-in-IPv6" {
           description "Ipv4-in-IPv6";
         }
         enum "v6rd" {
           description "V6rd";
         }
       }
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type uint32 {
           range "576 .. 9192";
         }
       }
     }
     leaf mtu-v6 {
       description "MTU for the softwire tunnel";
       type union {
         type string {
           pattern "<.*>|$.*";
         }
         type uint32 {
           range "1280 .. 9192";
         }
       }
     }
     leaf auto-update-mtu {
       description "Auto update MTU from received ICMPv6 messages";
       type empty;
     }
     leaf copy-dscp {
       description "Copy DSCP (type of service) from IPv6 to IPv4 header";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       type union {
         type string {
           pattern "<.*>|$.*";
         }
         type uint32 {
           range "0 .. 16384";
         }
       }
     }
   }
   grouping srd-rs-id-object {
     description "Definition of redundancy-set";
     leaf name {
       description "Redundancy set identifier";
       type union {
         type string {
           pattern "<.*>|$.*";
         }
         type uint32 {
           range "1 .. 100";
         }
       }
     }
     uses apply-advanced;
     leaf redundancy-group {
       description "Name of redundancy-group";
       type union {
         type string {
           pattern "<.*>|$.*";
         }
         type uint32 {
           range "1 .. 16";
         }
       }
     }
     leaf-list redundancy-policy {
       description "Redundancy-policy list";
       type string;
     }
     leaf keepalive {
       description "Frequency of SRD hello messages";
       default "10";
       units "seconds";
       type union {
         type string {
           pattern "<.*>|$.*";
         }
         type uint32 {
           range "1 .. 60";
         }
       }
     }
     leaf hold-time {
       description "Time before SRD peer is declared down";
       default "30";
       units "seconds";
       type union {
         type string {
           pattern "<.*>|$.*";
         }
         type uint32 {
           range "0 .. 3600";
         }
       }
     }
     leaf healthcheck-timer-interval {
       description "Healthcheck timer interval";
       default "5";
       units "seconds";
       type union {
         type string {
           pattern "<.*>|$.*";
         }
         type uint32 {
           range "1 .. 3600";
         }
       }
     }
   }
   grouping srd-traceoptions-object {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "config" {
             description "Trace parse events";
           }
           enum "connect" {
             description "Trace ipc events";
           }
           enum "route" {
             description "Trace route events";
           }
           enum "ssd" {
             description "Trace SDK Service events";
           }
           enum "snmp" {
             description "Trace snmp events";
           }
           enum "system" {
             description "Trace services redundancy system events";
           }
           enum "opcmd" {
             description "Trace operational command events";
           }
           enum "state-machine" {
             description "Trace finite-state-machine events";
           }
           enum "kcom" {
             description "Trace KCOM events";
           }
           enum "database" {
             description "Trace database events";
           }
           enum "swithover" {
             description "Trace switchover events";
           }
           enum "stateful-sync" {
             description "Trace stateful-sync related events";
           }
           enum "redundancy-group" {
             description "Trace redundancy-group related events";
           }
           enum "all" {
             description "Trace everything";
           }
         }
       }
     }
   }
   grouping ssg-destination-nat-object {
     uses apply-advanced;
     list pool {
       key name;
       ordered-by user;
       description "Define a destination address pool";
       leaf name {
         description "Pool name";
         type string {
           length "1 .. 63";
         }
       }
       uses apply-advanced;
       leaf description {
         description "Text description of pool";
         type string {
           length "1 .. 900";
         }
       }
       container routing-instance {
         description "Routing instance";
         uses apply-advanced;
         choice ri-name-choice {
           case case_1 {
             leaf default {
               description "Default routing-instance";
               type empty;
             }
           }
           case case_2 {
             leaf ri-name {
               description "Routing-instance name";
               type string {
               }
             }
           }
         }
       }
       container address {
         description "Add address or address range to pool";
         leaf ipaddr {
           description "IPv4 or IPv6 address or address range";
           type jt:ipprefix;
         }
         choice range-port-choice {
           case case_1 {
             container to {
               description "Upper limit of address range";
               uses apply-advanced;
               leaf ipaddr {
                 description "IPv4 or IPv6 upper limit of address range";
                 type jt:ipprefix;
               }
             }
           }
           case case_2 {
             leaf port {
               description "Specify the port value";
               type union {
                 type uint16;
                 type string {
                   pattern "<.*>|$.*";
                 }
               }
             }
           }
         }
       }
       container address-name {
         description "Add address to pool";
         leaf pool-address-name {
           description "Address name from address book";
           type string {
             length "1 .. 63";
           }
         }
         leaf port {
           description "Specify the port value";
           type union {
             type uint16;
             type string {
               pattern "<.*>|$.*";
             }
           }
         }
       }
       leaf session-retain {
         description "Sessions will be retained although destination pool ip changes";
         type empty;
       }
     }
     list port-forwarding {
       key name;
       ordered-by user;
       description "Define a port-forwarding mapping pool";
       leaf name {
         description "Port Forwarding mapping name";
         type string {
           length "1 .. 31";
         }
       }
       uses apply-advanced;
       leaf description {
         description "Text description of port forwarding mapping";
         type string {
           length "1 .. 900";
         }
       }
       list destined-port {
         key "port translated-port";
         ordered-by user;
         description "Port forwarding mappings";
         max-elements 32;
         leaf port {
           description "Destination port";
           type union {
             type string {
               pattern "<.*>|$.*";
             }
             type uint16 {
               range "1 .. 65535";
             }
           }
         }
         leaf translated-port {
           description "Translated port";
           type union {
             type string {
               pattern "<.*>|$.*";
             }
             type uint16 {
               range "1 .. 65535";
             }
           }
         }
       }
     }
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Destination NAT rule";
         uses dest-nat-rule-object;
       }
       leaf match-direction {
         description "Match direction";
         type enumeration {
           enum "input" {
             description "Match on input to interface";
           }
           enum "output" {
             description "Match on output from interface";
           }
         }
       }
     }
   }
   grouping dest-nat-rule-object {
     leaf name {
       description "Rule name";
       type string {
         length "1 .. 63";
       }
     }
     uses apply-advanced;
     leaf description {
       description "Text description of rule";
       type string {
         length "1 .. 900";
       }
     }
     container dest-nat-rule-match {
       description "Specify Destination NAT rule match criteria";
       uses apply-advanced;
       leaf-list source-address {
         ordered-by user;
         description "Source address";
         type string;
         max-elements 8;
       }
       leaf-list source-address-name {
         ordered-by user;
         description "Address/address-set from address book";
         type string;
         max-elements 8;
       }
       choice dst-choice {
         case case_1 {
           container destination-address {
             description "Destination address";
             choice dst-addr-choice {
               case case_1 {
                 leaf dst-addr {
                   description "IPv4 or IPv6 destination address";
                   type jt:ipprefix;
                 }
               }
               case case_2 {
                 leaf any-unicast {
                   description "Match any unicast address";
                   type empty;
                 }
               }
             }
           }
         }
         case case_2 {
           container destination-address-name {
             description "Address from address book";
             leaf dst-addr-name {
               description "Address from address book";
               type string {
                 length "1 .. 63";
               }
             }
           }
         }
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container destination-nat {
         description "Destination NAT action";
         uses apply-advanced;
         choice action {
           case case_1 {
             leaf off {
               description "No action";
               type empty;
             }
           }
           case case_2 {
             container pool {
               description "Use Destination NAT pool";
               uses apply-advanced;
               leaf pool-name {
                 description "Name of Destination NAT pool";
                 type string {
                   length "1 .. 63";
                 }
               }
             }
           }
           case case_3 {
             leaf destination-prefix {
               description "Destination prefix to be used for NAT64 and 464 translation type";
               type jt:ipprefix-only;
             }
           }
         }
         container xlat-source-rule {
           description "Set source nat rule to match for NAT464";
           uses apply-advanced;
           list rule-set {
             key name;
             ordered-by user;
             description "Source nat rule-set";
             max-elements 1;
             leaf name {
               description "Source nat rule-set name";
               type string {
                 length "1 .. 63";
               }
             }
             uses apply-advanced;
             leaf rule {
               description "Source NAT rule name";
               type string {
                 length "1 .. 63";
               }
             }
           }
         }
         container port-forwarding-mappings {
           description "Use Destination NAT port forwarding mapping pool";
           uses apply-advanced;
           leaf pf-name {
             description "Name of Port forwarding mappings";
             type string {
               length "1 .. 31";
             }
           }
         }
         container rule-session-count-alarm {
           description "Config rule-session-count-alarm to destination rule";
           uses nat-rule-session-count-alarm-object;
         }
       }
       leaf syslog {
         description "System log information about the packet";
         type empty;
       }
     }
   }
   grouping nat-rule-session-count-alarm-object {
     uses apply-advanced;
     leaf raise-threshold {
       description "Raise threshold for rule session count alarm";
       type union {
         type string {
           pattern "<.*>|$.*";
         }
         type uint32 {
           range "1 .. 4294967295";
         }
       }
     }
     leaf clear-threshold {
       description "Clear threshold for session count hit alarm";
       type union {
         type string {
           pattern "<.*>|$.*";
         }
         type uint32 {
           range "1 .. 4294967295";
         }
       }
     }
   }
   grouping ssg-proxy-arp-object {
     uses apply-advanced;
     list interface {
       key name;
       ordered-by user;
       description "Interface with proxy arp configured";
       uses ssg-interface-object;
     }
   }
   grouping ssg-interface-object {
     leaf name {
       description "Interface name";
       type union {
         type jt:interface-name;
         type string {
           pattern "<.*>|$.*";
         }
       }
     }
     uses apply-advanced;
     list address {
       key name;
       ordered-by user;
       description "Proxy ARP address";
       leaf name {
         description "Address or address range";
         type jt:ipv4prefix;
       }
       container to {
         description "Upper limit of address range";
         uses apply-advanced;
         leaf ipaddr {
           description "Upper limit of address range";
           type jt:ipv4prefix;
         }
       }
     }
   }
   grouping ssg-proxy-ndp-object {
     uses apply-advanced;
     list interface {
       key name;
       ordered-by user;
       description "Interface with proxy arp configured";
       uses ssg-proxy-ndp-interface-object;
     }
   }
   grouping ssg-proxy-ndp-interface-object {
     leaf name {
       description "Interface name";
       type union {
         type jt:interface-name;
         type string {
           pattern "<.*>|$.*";
         }
       }
     }
     uses apply-advanced;
     list address {
       key name;
       ordered-by user;
       description "Proxy ndp address";
       leaf name {
         description "Address or address range";
         type jt:ipv6prefix;
       }
       container to {
         description "Upper limit of address range";
         uses apply-advanced;
         leaf ipv6addr {
           description "Upper limit of address range";
           type jt:ipv6addr;
         }
       }
     }
   }
   grouping ssg-source-nat-object {
     uses apply-advanced;
     container persistent-nat {
       description "Persistent NAT info";
       container log {
         description "Configure persistent NAT log";
         choice enable-disable {
           case case_1 {
             leaf disable {
               description "Disable Persistent NAT log";
               type empty;
             }
           }
         }
       }
     }
     list pool {
       key name;
       ordered-by user;
       description "Define a source address pool";
       leaf name {
         description "Pool name";
         type string {
           length "1 .. 63";
         }
       }
       uses apply-advanced;
       leaf description {
         description "Text description of pool";
         type string {
           length "1 .. 900";
         }
       }
       container routing-instance {
         description "Routing instance";
         uses apply-advanced;
         leaf ri-name {
           description "Routing instance name";
           type string {
           }
         }
       }
       list address {
         key name;
         ordered-by user;
         description "Add address to pool";
         max-elements 64;
         leaf name {
           description "IPv4 or IPv6 address or address range";
           type jt:ipprefix;
         }
         container to {
           description "Upper limit of address range";
           uses apply-advanced;
           leaf ipaddr {
             description "IPv4 or IPv6 upper limit of address range";
             type jt:ipprefix;
           }
         }
       }
       container address-name {
         description "Add address to pool";
         leaf pool-address-name {
           description "Address name from address book";
           type string {
             length "1 .. 63";
           }
         }
       }
       container host-address-base {
         description "The base of host address";
         leaf ipaddr {
           description "IPv4 or IPv6 base address";
           type jt:ipprefix;
         }
       }
       container port {
         description "Config port attribute to pool";
         uses apply-advanced;
         choice port-choice {
           case case_1 {
             leaf no-translation {
               description "Do not perform port translation";
               type empty;
             }
           }
           case case_2 {
             container range {
               description "Port range";
               uses apply-advanced;
               choice port-assign-choice {
                 case case_1 {
                   leaf random-allocation {
                     description "Allocate port randomly";
                     type empty;
                   }
                 }
                 case case_2 {
                   leaf round-robin {
                     description "Allocate port round-robin";
                     type empty;
                   }
                 }
               }
               leaf low {
                 description "Lower limit of port range";
                 type union {
                   type string {
                     pattern "<.*>|$.*";
                   }
                   type uint16 {
                     range "1024 .. 65535";
                   }
                 }
               }
               container to {
                 description "Port range upper limit";
                 uses apply-advanced;
                 leaf high {
                   description "Upper limit of port range";
                   type union {
                     type string {
                       pattern "<.*>|$.*";
                     }
                     type uint16 {
                       range "1024 .. 65535";
                     }
                   }
                 }
               }
               container twin-port {
                 description "Twin port range";
                 uses apply-advanced;
                 leaf low {
                   description "Lower limit of twin port range";
                   type union {
                     type string {
                       pattern "<.*>|$.*";
                     }
                     type uint16 {
                       range "63488 .. 65535";
                     }
                   }
                 }
                 container to {
                   description "Twin port range upper limit";
                   uses apply-advanced;
                   leaf high {
                     description "Upper limit of twin port range";
                     type union {
                       type string {
                         pattern "<.*>|$.*";
                       }
                       type uint16 {
                         range "63488 .. 65535";
                       }
                     }
                   }
                 }
               }
             }
           }
           case case_3 {
             container automatic {
               description "Port assignment";
               uses apply-advanced;
               choice port-assign-choice {
                 case case_1 {
                   leaf random-allocation {
                     description "Allocate port randomly";
                     type empty;
                   }
                 }
                 case case_2 {
                   leaf round-robin {
                     description "Allocate port by round-robin";
                     type empty;
                   }
                 }
               }
             }
           }
         }
         leaf port-overloading-factor {
           description "Port overloading factor for each IP";
           type union {
             type string {
               pattern "<.*>|$.*";
             }
             type uint16 {
               range "2 .. 32";
             }
           }
         }
         leaf enhanced-port-overloading-algorithm {
           description "Enhanced port overloading algorithm for the pool";
           type empty;
         }
         container block-allocation {
           description "Port block allocation";
           presence "enable block-allocation";
           uses block-allocation-object;
         }
         container deterministic {
           description "Deterministic nat allocation";
           presence "enable deterministic";
           uses deterministic-object;
         }
         leaf preserve-parity {
           description "Allocate port as the same parity as incoming port";
           type empty;
         }
         leaf preserve-range {
           description "Allocate port from the same port range as incoming port";
           type empty;
         }
       }
       container overflow-pool {
         description "Specify an overflow pool";
         choice overflow-pool-choice {
           case case_1 {
             leaf pool-name {
               description "Name of source address pool";
               type string {
                 length "1 .. 63";
               }
             }
           }
           case case_2 {
             leaf interface {
               description "Allow interface pool to support overflow";
               type empty;
             }
           }
         }
       }
       leaf address-shared {
         description "Allow multiple hosts to share an externel address";
         type empty;
       }
       container address-pooling {
         description "Specify the address-pooling behavior";
         choice pooling-choice {
           case case_1 {
             leaf paired {
               description "Allow address-pooling paired for a source pool with port translation";
               type empty;
             }
           }
           case case_2 {
             leaf no-paired {
               description "Allow address-pooling no-paired for a source pool without port translation";
               type empty;
             }
           }
         }
       }
       container address-persistent {
         description "Specify the address-persistent behavior";
         container subscriber {
           description "Configure address persistent for subscriber";
           leaf ipv6-prefix-length {
             description "Ipv6 prefix length for address persistent";
             type union {
               type string {
                 pattern "<.*>|$.*";
               }
               type uint16 {
                 range "8 .. 128";
               }
             }
           }
         }
       }
       container pool-utilization-alarm {
         description "Config pool-utilization-alarm to pool";
         uses source-nat-pool-utilization-alarm-object;
       }
       leaf ei-mapping-timeout {
         description "Endpoint-independent mapping timeout";
         units "second";
         type union {
           type string {
             pattern "<.*>|$.*";
           }
           type uint32 {
             range "120 .. 86400";
           }
         }
       }
       leaf mapping-timeout {
         description "Address-pooling paired and endpoint-independent mapping timeout";
         units "second";
         type union {
           type string {
             pattern "<.*>|$.*";
           }
           type uint32 {
             range "120 .. 86400";
           }
         }
       }
       leaf limit-ports-per-host {
         description "Number of ports allocated per host";
         type union {
           type string {
             pattern "<.*>|$.*";
           }
           type uint16 {
             range "2 .. 65535";
           }
         }
       }
       container allocation-domain {
         description "Specify map-e domain name for pool";
         leaf mape-domain-name {
           description "Name of map-e domain";
           type string {
             length "1 .. 63";
           }
         }
         container allocation-rule {
           description "Specify map-e rule name for pool";
           leaf mape-rule-name {
             description "Name of map-e rule";
             type string {
               length "1 .. 63";
             }
           }
         }
       }
     }
     leaf address-persistent {
       description "Allow source address to maintain same translation";
       type empty;
     }
     leaf session-persistence-scan {
       description "Allow source to maintain session when session scan";
       type empty;
     }
     leaf session-drop-hold-down {
       description "Session drop hold down time";
       type union {
         type string {
           pattern "<.*>|$.*";
         }
         type uint16 {
           range "30 .. 28800";
         }
       }
     }
     container pool-utilization-alarm {
       description "Configure pool utilization alarm";
       uses source-nat-pool-utilization-alarm-object;
     }
     container port-randomization {
       description "Configure Source NAT port randomization";
       choice enable-disable {
         case case_1 {
           leaf disable {
             description "Disable Source NAT port randomization";
             type empty;
           }
         }
       }
     }
     container port-round-robin {
       description "Configure Source NAT port randomization";
       choice enable-disable {
         case case_1 {
           leaf disable {
             description "Disable Source NAT port randomization";
             type empty;
           }
         }
       }
     }
     leaf port-scaling-enlargement {
       description "Configure source port scaling to 2.4G only for NGSPC";
       type empty;
     }
     leaf pool-distribution {
       description "Configure Source pool distribution, the APPCP bottleneck of NAT CPS can be alleviated.";
       type empty;
     }
     container pool-default-port-range {
       description "Configure Source NAT default port range";
       leaf low {
         description "Lower limit of port range";
         type union {
           type string {
             pattern "<.*>|$.*";
           }
           type uint16;
         }
       }
       container to {
         description "Port range upper limit";
         uses apply-advanced;
         leaf high {
           description "Upper limit of port range";
           type union {
             type string {
               pattern "<.*>|$.*";
             }
             type uint16;
           }
         }
       }
     }
     container pool-default-twin-port-range {
       description "Configure Source NAT default twin port range";
       leaf low {
         description "Lower limit of twin port range";
         type union {
           type string {
             pattern "<.*>|$.*";
           }
           type uint16 {
             range "63488 .. 65535";
           }
         }
       }
       container to {
         description "Twin port range upper limit";
         uses apply-advanced;
         leaf high {
           description "Upper limit of twin port range";
           type union {
             type string {
               pattern "<.*>|$.*";
             }
             type uint16 {
               range "63488 .. 65535";
             }
           }
         }
       }
     }
     container interface {
       description "Configure interface port overloading for persistent NAT";
       uses apply-advanced;
       choice interface-choice {
         case case_1 {
           container port-overloading {
             description "Configure port overloading";
             leaf off {
               description "Turn off interface port over-loading";
               type empty;
             }
           }
         }
         case case_2 {
           leaf port-overloading-factor {
             description "Port overloading factor for interface NAT";
             type union {
               type uint16;
               type string {
                 pattern "<.*>|$.*";
               }
             }
           }
         }
       }
       leaf enhanced-port-overloading-algorithm {
         description "Enhanced port overloading algorithm for interface NAT";
         type empty;
       }
     }
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       container to {
         description "Where is the traffic to";
         choice from-context-choice {
           case case_1 {
             leaf-list routing-instance {
               description "Destination routing instance list";
               type string;
               max-elements 8;
             }
           }
           case case_2 {
             leaf-list routing-group {
               description "Destination routing group list";
               type string;
               max-elements 8;
             }
           }
           case case_3 {
             leaf-list zone {
               description "Destination zone list";
               type string;
               max-elements 8;
             }
           }
           case case_4 {
             leaf-list interface {
               description "Destination interface list";
               type union {
                 type jt:interface-name;
                 type string {
                   pattern "<.*>|$.*";
                 }
               }
               max-elements 8;
             }
           }
         }
       }
       list rule {
         key name;
         ordered-by user;
         description "Source NAT rule";
         uses src-nat-rule-object;
       }
       leaf match-direction {
         description "Match direction";
         type enumeration {
           enum "input" {
             description "Match on input to interface";
           }
           enum "output" {
             description "Match on output from interface";
           }
         }
       }
     }
   }
   grouping block-allocation-object {
     description "Port block allocation";
     uses apply-advanced;
     leaf block-size {
       description "Block size";
       type union {
         type string {
           pattern "<.*>|$.*";
         }
         type uint16 {
           range "1 .. 64512";
         }
       }
     }
     leaf maximum-blocks-per-host {
       description "Maximum block number per host";
       type union {
         type string {
           pattern "<.*>|$.*";
         }
         type uint16 {
           range "1 .. 512";
         }
       }
     }
     leaf active-block-timeout {
       description "Active block timeout interval";
       type union {
         type string {
           pattern "<.*>|$.*";
         }
         type uint32;
       }
     }
     leaf interim-logging-interval {
       description "Interim Logging interval";
       type union {
         type string {
           pattern "<.*>|$.*";
         }
         type uint32 {
           range "1800 .. 86400";
         }
       }
     }
     leaf last-block-recycle-timeout {
       description "Last Block recycle timeout interval";
       type union {
         type string {
           pattern "<.*>|$.*";
         }
         type uint32 {
           range "120 .. 864000";
         }
       }
     }
     container log {
       description "Configure port block log";
       choice enable-disable {
         case case_1 {
           leaf disable {
             description "Disable PBA port block log";
             type empty;
           }
         }
       }
     }
   }
   grouping deterministic-object {
     description "Deterministic nat allocation";
     uses apply-advanced;
     leaf block-size {
       description "Block size";
       type union {
         type string {
           pattern "<.*>|$.*";
         }
         type uint16;
       }
     }
     leaf det-nat-configuration-log-interval {
       description "Deterministic nat configuration logging interval";
       type union {
         type string {
           pattern "<.*>|$.*";
         }
         type uint32 {
           range "1800 .. 86400";
         }
       }
     }
     container host {
       description "Host address";
       leaf-list address {
         ordered-by user;
         description "Host ip address";
         type jt:ipprefix;
         max-elements 8;
       }
       leaf-list address-name {
         ordered-by user;
         description "Host address/address-set from address book";
         type string;
         max-elements 8;
       }
     }
     leaf include-boundary-addresses {
       description "Include network and broadcast in 'match' source address";
       type empty;
     }
   }
   grouping source-nat-pool-utilization-alarm-object {
     uses apply-advanced;
     leaf raise-threshold {
       description "Raise threshold for pool utilization alarm";
       type union {
         type string {
           pattern "<.*>|$.*";
         }
         type uint16 {
           range "50 .. 100";
         }
       }
     }
     leaf clear-threshold {
       description "Clear threshold for pool utilization alarm";
       type union {
         type string {
           pattern "<.*>|$.*";
         }
         type uint16 {
           range "40 .. 100";
         }
       }
     }
   }
   grouping src-nat-rule-object {
     leaf name {
       description "Source NAT Rule name";
       type string {
         length "1 .. 63";
       }
     }
     uses apply-advanced;
     leaf description {
       description "Text description of rule";
       type string {
         length "1 .. 900";
       }
     }
     container src-nat-rule-match {
       description "Specify Source NAT rule match criteria";
       uses apply-advanced;
       leaf-list source-address {
         ordered-by user;
         description "Source address";
         type string;
         max-elements 8;
       }
       leaf-list source-address-name {
         ordered-by user;
         description "Address/address-set from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list destination-address {
         ordered-by user;
         description "Destination address";
         type string;
         max-elements 8;
       }
       leaf-list destination-address-name {
         ordered-by user;
         description "Address/address-set from address book";
         type string;
         max-elements 8;
       }
       list destination-port {
         key name;
         ordered-by user;
         description "Destination port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       leaf-list protocol {
         ordered-by user;
         description "IP Protocol";
         type string;
         max-elements 4;
       }
       leaf-list application {
         ordered-by user;
         type string;
       }
     }
     container then {
       description "Then action";
       uses apply-advanced;
       container source-nat {
         description "Source NAT action";
         uses apply-advanced;
         choice action {
           case case_1 {
             leaf off {
               description "No action";
               type empty;
             }
           }
           case case_2 {
             container pool {
               description "Use Source NAT pool";
               uses apply-advanced;
               leaf pool-name {
                 description "Name of Source NAT pool";
                 type string {
                   length "1 .. 63";
                 }
               }
               container persistent-nat {
                 description "Persistent NAT info";
                 presence "enable persistent-nat";
                 uses persistent-nat-object;
               }
             }
           }
           case case_3 {
             container interface {
               presence "enable interface";
               description "Use egress interface address";
               uses apply-advanced;
               container persistent-nat {
                 description "Persistent NAT info";
                 presence "enable persistent-nat";
                 uses persistent-nat-object;
               }
             }
           }
         }
         leaf clat-prefix {
           description "An IPv6 prefix to be used for XLAT464 and prefix length can only be 32/40/48/56/64/96";
           type jt:ipprefix-only;
         }
         leaf clat-ipv6-prefix-length {
           description "The ipv6 prefix length for CLAT source address";
           type enumeration {
             enum "32" {
               description "The ipv6 prefix length of 32";
             }
             enum "40" {
               description "The ipv6 prefix length of 40";
             }
             enum "48" {
               description "The ipv6 prefix length of 48";
             }
             enum "56" {
               description "The ipv6 prefix length of 56";
             }
             enum "64" {
               description "The ipv6 prefix length of 64";
             }
             enum "96" {
               description "The ipv6 prefix length of 96";
             }
           }
         }
         container rule-session-count-alarm {
           description "Config rule-session-count-alarm to source rule";
           uses nat-rule-session-count-alarm-object;
         }
         container mapping-type {
           description "Source nat mapping type";
           leaf endpoint-independent {
             description "Endpoint independent mapping";
             type empty;
           }
           leaf address-pooling-paired {
             description "Address pooling paired mapping";
             type empty;
           }
         }
         container secure-nat-mapping {
           description "Mapping options for enhanced security";
           uses apply-advanced;
           leaf eif-flow-limit {
             description "Number of inbound flows to be allowed for a EIF mapping";
             type union {
               type string {
                 pattern "<.*>|$.*";
               }
               type uint16 {
                 range "0 .. 65534";
               }
             }
           }
           leaf mapping-refresh {
             description "Enable timer refresh option";
             type enumeration {
               enum "inbound" {
                 description "Enable timer refresh for inbound connections only";
               }
               enum "outbound" {
                 description "Enable timer refresh for outbound connections only";
               }
               enum "inbound-outbound" {
                 description "Enable timer refresh for inbound & outbound connections";
               }
             }
           }
         }
         container filtering-type {
           description "Source NAT filtering type";
           uses apply-advanced;
           container endpoint-independent {
             presence "enable endpoint-independent";
             description "Endpoint independent filtering";
             uses apply-advanced;
             list prefix-list {
               key name;
               ordered-by user;
               description "One or more named lists of source prefixes to match";
               leaf name {
                 description "Name of prefix list to match against";
                 type string {
                   length "1 .. 63";
                 }
               }
               leaf except {
                 description "Name of prefix list not to match against";
                 type empty;
               }
             }
           }
         }
       }
       leaf syslog {
         description "System log information about the packet";
         type empty;
       }
     }
   }
   grouping persistent-nat-object {
     uses apply-advanced;
     container permit {
       description "Persistent NAT permit configure";
       choice persistent-nat-type-choice {
         case case_1 {
           leaf any-remote-host {
             description "Permit any remote host";
             type empty;
           }
         }
         case case_2 {
           leaf target-host {
             description "Permit target host";
             type empty;
           }
         }
         case case_3 {
           leaf target-host-port {
             description "Permit target host port";
             type empty;
           }
         }
       }
     }
     leaf block-ext-session {
       description "Block sessions from external hosts";
       type empty;
     }
     leaf address-mapping {
       description "Address-to-address mapping";
       type empty;
     }
     leaf inactivity-timeout {
       description "Inactivity timeout value";
       type union {
         type string {
           pattern "<.*>|$.*";
         }
         type uint16 {
           range "60 .. 7200";
         }
       }
     }
     leaf max-session-number {
       description "The maximum session number value";
       type union {
         type string {
           pattern "<.*>|$.*";
         }
         type uint32 {
           range "8 .. 65536";
         }
       }
     }
   }
   grouping ssg-static-nat-object {
     uses apply-advanced;
     list rule-set {
       key name;
       ordered-by user;
       description "Configurate a set of rules";
       leaf name {
         description "Rule-set name";
         type string {
           length "1 .. 63";
         }
       }
       uses apply-advanced;
       leaf description {
         description "Text description of rule set";
         type string {
           length "1 .. 900";
         }
       }
       container from {
         description "Where is the traffic from";
         choice from-context-choice {
           case case_1 {
             leaf-list routing-instance {
               description "Source routing instance list";
               type string;
               max-elements 8;
             }
           }
           case case_2 {
             leaf-list routing-group {
               description "Source routing group list";
               type string;
               max-elements 8;
             }
           }
           case case_3 {
             leaf-list zone {
               description "Source zone list";
               type string;
               max-elements 8;
             }
           }
           case case_4 {
             leaf-list interface {
               description "Source interface list";
               type union {
                 type jt:interface-name;
                 type string {
                   pattern "<.*>|$.*";
                 }
               }
               max-elements 8;
             }
           }
         }
       }
       list rule {
         key name;
         ordered-by user;
         description "Static NAT rule";
         uses static-nat-rule-object;
       }
       leaf match-direction {
         description "Match direction";
         type enumeration {
           enum "input" {
             description "Match on input to interface";
           }
           enum "output" {
             description "Match on output from interface";
           }
         }
       }
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf-list trusted-ca {
         ordered-by user;
         description "List of trusted certificate authority profiles";
         type string;
         max-elements 1024;
       }
       leaf client-certificate {
         description "Local certificate identifier";
         type string {
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-proxy-config {
     uses apply-advanced;
     container global-config {
       description "Global proxy configuration";
       uses apply-advanced;
       leaf session-cache-timeout {
         description "Session cache timeout";
         units "seconds";
         type union {
           type string {
             pattern "<.*>|$.*";
           }
           type uint32 {
             range "300 .. 86400";
           }
         }
       }
       leaf disable-cert-cache {
         description "Disable proxy mode certificate cache";
         type empty;
       }
       leaf certificate-cache-timeout {
         description "Certificate cache timeout";
         units "seconds";
         type union {
           type string {
             pattern "<.*>|$.*";
           }
           type uint32 {
             range "300 .. 3600";
           }
         }
       }
       leaf invalidate-cache-on-crl-update {
         description "Invalidate certificate cache on crl update";
         type empty;
       }
       leaf cache-usage-enforcement-threshold {
         description "Percentage of total cache size after which per lsys limits will be enforced";
         type union {
           type string {
             pattern "<.*>|$.*";
           }
           type uint32 {
             range "1 .. 100";
           }
         }
       }
       leaf disable-deferred-profile-selection {
         description "Disable the deferred profile selection mechanism";
         type empty;
       }
       container mail-threshold {
         presence "enable mail-threshold";
         description "Thresholds that allow user to decide how long to wait for STARTTLS";
         uses apply-advanced;
         leaf packet-threshold {
           description "Number of plain packets in C2S direction after which session will be ignored";
           default "5";
           type union {
             type string {
               pattern "<.*>|$.*";
             }
             type uint32 {
               range "1 .. 15";
             }
           }
         }
         leaf byte-threshold {
           description "Minimum bytes required to ignore the session";
           default "200";
           type union {
             type string {
               pattern "<.*>|$.*";
             }
             type uint32 {
               range "100 .. 300";
             }
           }
         }
       }
       container actions {
         description "Define global ssl proxy actions";
         uses apply-advanced;
       }
     }
     list profile {
       key name;
       ordered-by user;
       description "SSL Proxy profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf-list trusted-ca {
         ordered-by user;
         description "List of trusted certificate authority profiles";
         type string;
         max-elements 1024;
       }
       choice certificate {
         case case_1 {
           leaf-list root-ca {
             ordered-by user;
             description "Root certificate for interdicting server certificates in proxy mode";
             type string;
             max-elements 2;
           }
         }
         case case_2 {
           leaf-list server-certificate {
             ordered-by user;
             description "Local certificate identifier";
             type string;
             max-elements 1024;
           }
         }
       }
       container mirror-decrypt-traffic {
         description "Configure mirror interface and Destination MAC address";
         uses apply-advanced;
         leaf interface {
           description "Interface on which SSL decrypted traffic is mirrored";
           type union {
             type jt:interface-name;
             type string {
               pattern "<.*>|$.*";
             }
           }
         }
         leaf destination-mac-address {
           description "Mac address of host/server to which decrypted traffic is mirrored";
           type jt:mac-addr;
         }
         leaf only-after-security-policies-enforcement {
           description "Enables decrypted Traffic mirroring after policy enforcement";
           type empty;
         }
       }
       leaf-list whitelist {
         ordered-by user;
         description "Addresses exempted from SSL Proxy ";
         type string;
       }
       leaf-list whitelist-url-categories {
         ordered-by user;
         type string;
       }
       container actions {
         description "Logging and traffic related actions";
         uses apply-advanced;
         leaf ignore-server-auth-failure {
           description "Ignore server authentication failure";
           type empty;
         }
         container log {
           presence "enable log";
           description "Logging actions";
           leaf all {
             description "Log all events";
             type empty;
           }
           leaf sessions-dropped {
             description "Log only ssl session drop events";
             type empty;
           }
           leaf sessions-allowed {
             description "Log ssl session allow events after an error";
             type empty;
           }
           leaf sessions-ignored {
             description "Log  session ignore events ";
             type empty;
           }
           leaf sessions-whitelisted {
             description "Log ssl session whitelist events ";
             type empty;
           }
           leaf errors {
             description "Log all error events ";
             type empty;
           }
           leaf warning {
             description "Log all warning events ";
             type empty;
           }
           leaf info {
             description "Log all information events ";
             type empty;
           }
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf renegotiation {
           description "Renegotiation options";
           default "allow-secure";
           type enumeration {
             enum "allow" {
               description "Allow secure as well as non secure renegotiation";
             }
             enum "allow-secure" {
               description "Allow secure negotiation only (RFC 5746)";
             }
             enum "drop" {
               description "Drop session on renegotiation request";
             }
           }
         }
         leaf disable-session-resumption {
           description "Disable session resumption";
           type empty;
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
         leaf allow-strong-certificate {
           description "Certificate till 4K key-size processing on standalone SRX300/SRX320 platform";
           type empty;
         }
       }
       leaf disable-deferred-profile-selection {
         description "Disable the deferred profile selection mechanism at profile level";
         type empty;
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf server-certificate {
         description "Local certificate identifier";
         type string {
         }
       }
     }
   }
   grouping ssl-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
     container packet-filter {
       description "SSL Packet filter";
       uses apply-advanced;
       leaf source-ip {
         description "Source IP address";
         type jt:ipaddr;
       }
       leaf destination-ip {
         description "Destination IP address";
         type jt:ipaddr;
       }
       leaf source-port {
         description "Source port";
         type union {
           type string {
             pattern "<.*>|$.*";
           }
           type uint16 {
             range "1 .. 65535";
           }
         }
       }
       leaf destination-port {
         description "Destination port";
         type union {
           type string {
             pattern "<.*>|$.*";
           }
           type uint16 {
             range "1 .. 65535";
           }
         }
       }
     }
   }
   grouping static-nat-rule-object {
     leaf name {
       description "Static Rule name";
       type string {
         length "1 .. 63";
       }
     }
     uses apply-advanced;
     leaf description {
       description "Text description of rule";
       type string {
         length "1 .. 900";
       }
     }
     container static-nat-rule-match {
       description "Specify Static NAT rule match criteria";
       uses apply-advanced;
       leaf-list source-address {
         ordered-by user;
         description "Source address";
         type jt:ipprefix;
         max-elements 8;
       }
       leaf-list source-address-name {
         ordered-by user;
         description "Address from address book";
         type string;
         max-elements 8;
       }
       list source-port {
         key name;
         ordered-by user;
         description "Source port";
         max-elements 8;
         leaf name {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
       choice dst-choice {
         case case_1 {
           container destination-address {
             description "Destination address";
             leaf dst-addr {
               description "IPv4 or IPv6 Destination address prefix";
               type jt:ipprefix;
             }
           }
         }
         case case_2 {
           container destination-address-name {
             description "Address from address book";
             leaf dst-addr-name {
               description "Address from address book";
               type string {
                 length "1 .. 63";
               }
             }
           }
         }
       }
       container destination-port {
         description "Destination port";
         leaf low {
           description "Port or lower limit of port range";
           type union {
             type uint16;
             type string {
               pattern "<.*>|$.*";
             }
           }
         }
         container to {
           description "Port range upper limit";
           uses apply-advanced;
           leaf high {
             description "Upper limit of port range";
             type union {
               type uint16;
               type string {
                 pattern "<.*>|$.*";
               }
             }
           }
         }
       }
     }
     container then {
       description "Then action";
       uses apply-advanced;
       container static-nat {
         description "Static NAT action";
         uses apply-advanced;
         choice prefix-choice {
           case case_1 {
             container inet {
               presence "enable inet";
               description "Translated to IPv4 address";
               uses apply-advanced;
               leaf routing-instance {
                 description "Routing instance";
                 type string;
               }
             }
           }
           case case_2 {
             container prefix {
               description "Address prefix";
               uses apply-advanced;
               leaf addr-prefix {
                 description "IPv4 or IPv6 address prefix value";
                 type jt:ipprefix;
               }
               container mapped-port {
                 description "Mapped port";
                 uses static-nat-rule-mapped-port-object;
               }
               leaf routing-instance {
                 description "Routing instance";
                 type string;
               }
             }
           }
           case case_3 {
             container prefix-name {
               description "Address from address book";
               uses apply-advanced;
               leaf addr-prefix-name {
                 description "Address from address book";
                 type string {
                   length "1 .. 63";
                 }
               }
               container mapped-port {
                 description "Mapped port";
                 uses static-nat-rule-mapped-port-object;
               }
               leaf routing-instance {
                 description "Routing instance";
                 type string;
               }
             }
           }
           case case_4 {
             container nptv6-prefix {
               description "NPTv6 address prefix, the longest prefix will be supported is /64";
               uses apply-advanced;
               leaf addr-prefix {
                 description "IPv6 address prefix value, the longest prefix will be supported is /64";
                 type jt:ipprefix;
               }
               leaf routing-instance {
                 description "Routing instance";
                 type string;
               }
             }
           }
           case case_5 {
             container nptv6-prefix-name {
               description "NPTv6 address from address book";
               uses apply-advanced;
               leaf addr-prefix-name {
                 description "IPv6 address from address book";
                 type string {
                   length "1 .. 63";
                 }
               }
               leaf routing-instance {
                 description "Routing instance";
                 type string;
               }
             }
           }
         }
         container rule-session-count-alarm {
           description "Config rule-session-count-alarm to static rule";
           uses nat-rule-session-count-alarm-object;
         }
       }
     }
   }
   grouping static-nat-rule-mapped-port-object {
     uses apply-advanced;
     leaf low {
       description "Port or lower limit of port range";
       type union {
         type uint16;
         type string {
           pattern "<.*>|$.*";
         }
       }
     }
     container to {
       description "Port range upper limit";
       uses apply-advanced;
       leaf high {
         description "Upper limit of port range";
         type union {
           type uint16;
           type string {
             pattern "<.*>|$.*";
           }
         }
       }
     }
   }
   grouping sw-rule-set-object {
     leaf name {
       description "Define Rule Set name";
       type string {
         length "1 .. 63";
       }
     }
     uses apply-advanced;
     list rule {
       key name;
       ordered-by user;
       description "Define a rule term";
       leaf name {
         description "Rule name";
         type string {
           length "1 .. 63";
         }
       }
       uses apply-advanced;
       container then {
         description "Action to take if the condition is matched";
         uses apply-advanced;
         choice designation {
           case case_1 {
             leaf ds-lite {
               description "Apply DS-Lite softwire";
               type string {
                 length "1 .. 63";
               }
             }
           }
           case case_2 {
             leaf v6rd {
               description "Apply 6rd softwire";
               type string {
                 length "1 .. 63";
               }
             }
           }
           case case_3 {
             leaf map-e {
               description "Apply MAP-E softwire";
               type string {
                 length "1 .. 63";
               }
             }
           }
           case case_4 {
             leaf map-t {
               description "Apply MAP-T softwire";
               type string {
                 length "1 .. 63";
               }
             }
           }
         }
       }
     }
     leaf match-direction {
       description "Match direction";
       type enumeration {
         enum "input" {
           description "Match on input to interface";
         }
         enum "output" {
           description "Match on output from interface";
         }
       }
     }
   }
   grouping sw_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
       }
     }
     list term {
       key name;
       ordered-by user;
       description "Define a softwire term";
       leaf name {
         description "Term name";
         type string {
           length "1 .. 63";
         }
       }
       uses apply-advanced;
       container then {
         description "Action to take if the 'from' condition is matched";
         uses apply-advanced;
         choice designation {
           case case_1 {
             leaf ds-lite {
               description "Apply DS-Lite softwire";
               type string {
                 length "1 .. 63";
               }
             }
           }
           case case_2 {
             leaf v6rd {
               description "Apply 6rd softwire";
               type string {
                 length "1 .. 63";
               }
             }
           }
           case case_3 {
             leaf map-e {
               description "Apply map-e softwire";
               type string {
                 length "1 .. 63";
               }
             }
           }
           case case_4 {
             leaf map-t {
               description "Apply map-t softwire";
               type string {
                 length "1 .. 63";
               }
             }
           }
         }
       }
     }
   }
   grouping tdir_netmon_object {
     description "Network monitoring probe configuration";
     uses apply-advanced;
     container traceoptions {
       description "Net Monitoring trace options";
       uses tdir_netmon_traceoptions_object;
     }
     list profile {
       key name;
       description "Network monitoring probe profile configuration";
       max-elements 32;
       uses tdir_netmon_profile_object;
     }
     list source-interface {
       key name;
       description "Network monitoring probe sending interface";
       max-elements 32;
       uses tdir_netmon_src_iface;
     }
   }
   grouping tdir_netmon_profile_object {
     leaf name {
       description "Network monitoring probe profile name";
       type string {
         length "1 .. 20";
       }
     }
     uses apply-advanced;
     choice probe-type {
       case case_1 {
         container http {
           description "HTTP probe options";
           presence "enable http";
           uses tdir_http_probe_object;
         }
       }
       case case_2 {
         leaf icmp {
           description "ICMP probe options";
           type empty;
         }
       }
       case case_3 {
         container tcp {
           description "TCP probe options";
           presence "enable tcp";
           uses tdir_tcp_probe_object;
         }
       }
       case case_4 {
         container ssl-hello {
           description "SSL hello probe options";
           presence "enable ssl-hello";
           uses tdir_ssl_hello_probe_object;
         }
       }
       case case_5 {
         container tls-hello {
           description "TLS hello probe options";
           presence "enable tls-hello";
           uses tdir_tls_hello_probe_object;
         }
       }
       case case_6 {
         container custom {
           description "Custom probe options";
           presence "enable custom";
           uses tdir_netmon_custom_probe_object;
         }
       }
     }
     leaf probe-interval {
       description "Probe interval";
       default "5";
       units "seconds";
       type union {
         type string {
           pattern "<.*>|$.*";
         }
         type uint32;
       }
     }
     leaf failure-retries {
       description "Probe failure retries";
       default "5";
       type union {
         type string {
           pattern "<.*>|$.*";
         }
         type uint32 {
           range "1 .. 255";
         }
       }
     }
     leaf recovery-retries {
       description "Probe recovery retries";
       default "5";
       type union {
         type string {
           pattern "<.*>|$.*";
         }
         type uint32 {
           range "1 .. 255";
         }
       }
     }
   }
   grouping tdir_http_probe_object {
     description "HTTP probe information";
     uses apply-advanced;
     leaf port {
       description "Port number";
       default "80";
       type union {
         type string {
           pattern "<.*>|$.*";
         }
         type uint16 {
           range "1 .. 65535";
         }
       }
     }
     leaf url {
       description "URL name";
       type string {
         length "1 .. 127";
       }
     }
     leaf method {
       description "HTTP method";
       default "get";
       type enumeration {
         enum "get" {
           description "HTTP method GET";
         }
         enum "options" {
           description "HTTP method OPTIONS";
         }
       }
     }
     leaf hostname {
       description "Hostname";
       type string {
         length "1 .. 63";
       }
     }
   }
   grouping tdir_netmon_custom_probe_object {
     description "Custom probe information";
     uses apply-advanced;
     leaf protocol {
       description "Custom protocol";
       type enumeration {
         enum "tcp" {
           description "TCP protocol";
         }
         enum "udp" {
           description "UDP protocol";
         }
       }
     }
     list cmd {
       key name;
       description "Custom probe command configuration";
       max-elements 1;
       uses tdir_netmon_custom_probe_command_object;
     }
   }
   grouping tdir_netmon_custom_probe_command_object {
     description "Command information in custom probe";
     leaf name {
       description "Custom probe command priority";
       type union {
         type string {
           pattern "<.*>|$.*";
         }
         type uint16 {
           range "1 .. 2";
         }
       }
     }
     uses apply-advanced;
     leaf port {
       description "Port number";
       type union {
         type string {
           pattern "<.*>|$.*";
         }
         type uint16 {
           range "1 .. 65535";
         }
       }
     }
     leaf default-real-service-status {
       description "Default status of real service";
       default "down";
       type enumeration {
         enum "down" {
           description "RS marked down by default";
         }
         enum "up" {
           description "RS marked up by default";
         }
       }
     }
     container send {
       description "Send ASCII string or binary buffer";
       presence "enable send";
       uses tdir_netmon_custom_probe_send_object;
     }
     container expect {
       description "Expect ASCII string or binary buffer";
       presence "enable expect";
       uses tdir_netmon_custom_probe_expect_object;
     }
   }
   grouping tdir_netmon_custom_probe_expect_object {
     uses apply-advanced;
     choice expect_choice {
       case case_1 {
         container ascii {
           description "Expect ASCII string";
           presence "enable ascii";
           uses tdir_netmon_cust_probe_ascii_expect_obj;
         }
       }
       case case_2 {
         container binary {
           description "Expect binary buffer";
           presence "enable binary";
           uses tdir_netmon_cust_probe_binary_expect_obj;
         }
       }
     }
   }
   grouping tdir_netmon_cust_probe_ascii_expect_obj {
     leaf ascii-buf {
       type string {
         length "1 .. 512";
       }
     }
     container offset {
       description "Expect buffer offset";
       presence "enable offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_binary_expect_obj {
     leaf binary-buf {
       type string {
         length "1 .. 512";
       }
     }
     container offset {
       description "Expect buffer offset";
       presence "enable offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_expect_offset_obj {
     leaf offset {
       type union {
         type uint16;
         type string {
           pattern "<.*>|$.*";
         }
       }
     }
     leaf length {
       description "Expect buffer offset length";
       type union {
         type string {
           pattern "<.*>|$.*";
         }
         type uint16 {
           range "1 .. 65535";
         }
       }
     }
   }
   grouping tdir_netmon_custom_probe_send_object {
     choice send_choice {
       case case_1 {
         leaf ascii {
           description "Send ASCII string";
           type string {
             length "1 .. 512";
           }
         }
       }
       case case_2 {
         leaf binary {
           description "Send binary buffer";
           type string {
             length "1 .. 512";
           }
         }
       }
     }
   }
   grouping tdir_netmon_src_iface {
     leaf name {
       description "Network monitoring probe source interface name";
       type string {
         length "1 .. 20";
       }
     }
     uses apply-advanced;
     container family {
       description "Address family";
       uses apply-advanced;
       container inet {
         description "Address family IPv4";
         uses apply-advanced;
         leaf address {
           description "Address family IPv4 address";
           type jt:ipv4addr;
         }
       }
       container inet6 {
         description "Address family IPv6";
         uses apply-advanced;
         leaf address {
           description "Address family IPv6 address";
           type jt:ipv6addr;
         }
       }
     }
   }
   grouping tdir_netmon_traceoptions_object {
     description "Network Monitoring trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "all-real-services" {
             description "Trace all real services";
           }
           enum "messages" {
             description "Trace normal events";
           }
           enum "probe" {
             description "Trace probe events";
           }
           enum "inter-thread" {
             description "Trace inter thread communication events";
           }
           enum "database" {
             description "Trace database events";
           }
           enum "file-descriptor-queue" {
             description "Trace file descriptor queue events";
           }
           enum "probe-infra" {
             description "Trace probe infra events";
           }
           enum "all" {
             description "Trace everything";
           }
         }
       }
     }
     list monitor {
       key name;
       leaf name {
         description "Monitor name";
         type string {
           length "1 .. 20";
         }
       }
       uses apply-advanced;
       leaf group-name {
         description "Group name";
         type string {
           length "1 .. 20";
         }
       }
       leaf real-services-name {
         description "Real service";
         type string {
           length "1 .. 20";
         }
       }
     }
   }
   grouping tdir_service_load_balance_object {
     uses apply-advanced;
     container traceoptions {
       description "Traffic load balance trace options";
       uses tdir_traceoptions_object;
     }
     leaf route-hold-timer {
       description "Route hold timer, when PIC is down";
       default "180";
       type union {
         type string {
           pattern "<.*>|$.*";
         }
         type uint32 {
           range "1 .. 600";
         }
       }
     }
     list instance {
       key name;
       description "Traffic load balance instance configuration";
       max-elements 2048;
       uses tdir_slb_instance_object;
     }
     list flb-policy {
       key name;
       description "Firewall load balancer instance configuration";
       max-elements 2048;
       uses tdir_flb_policy_object;
     }
     list interfaces {
       key name;
       description "Client/server facing interfaces";
       max-elements 8160;
       uses tdir_interfaces_object;
     }
   }
   grouping tdir_flb_policy_object {
     leaf name {
       description "Policy name";
       type string {
         length "1 .. 20";
       }
     }
     uses apply-advanced;
     leaf client-interface {
       description "Client facing interface name";
       type string {
         length "1 .. 20";
       }
     }
     leaf server-interface {
       description "Server facing interface name";
       type string {
         length "1 .. 20";
       }
     }
     list destination {
       key name;
       description "Destination configuration";
       max-elements 8160;
       uses tdir_destination_object;
     }
     leaf-list network-monitoring-profile {
       description "Network monitoring profile name";
       type string {
         length "1 .. 20";
       }
       max-elements 2;
     }
     container load-balance-method {
       presence "enable load-balance-method";
       description "Load balance method";
       uses apply-advanced;
       choice method-type {
         case case_1 {
           container hash {
             presence "enable hash";
             description "Load balance hash method";
             uses apply-advanced;
             container hash-key {
               description "Hash-key type";
               presence "enable hash-key";
               uses tdir_flb_lb_hash_method_obj;
             }
           }
         }
         case case_2 {
           leaf random {
             description "Load balance random method";
             type empty;
           }
         }
         case case_3 {
           leaf least-connections {
             description "Load balance least-connections method";
             type empty;
           }
         }
         case case_4 {
           leaf round-robin {
             description "Load balance round-robin method";
             type empty;
           }
         }
       }
     }
   }
   grouping tdir_destination_object {
     leaf name {
       description "Destiation name";
       type string {
         length "1 .. 20";
       }
     }
     uses apply-advanced;
     leaf destination-ip {
       description "IP address";
       type jt:ipaddr;
     }
     leaf source-ip {
       description "IP address";
       type jt:ipaddr;
     }
     leaf interface {
       description "Interface name";
       type union {
         type jt:interface-name;
         type string {
           pattern "<.*>|$.*";
         }
       }
     }
     leaf routing-instance {
       description "Routing instance name";
       type string {
         length "1 .. 30";
       }
     }
     leaf admin-down {
       description "Set the destination to DOWN state";
       type empty;
     }
   }
   grouping tdir_flb_lb_hash_method_obj {
     uses apply-advanced;
     leaf source-ip {
       description "Source-address based hashing";
       type empty;
     }
     leaf destination-ip {
       description "Destination-address based hashing";
       type empty;
     }
     leaf protocol {
       description "Protocol based hashing";
       type empty;
     }
   }
   grouping tdir_interfaces_object {
     leaf name {
       description "Client/server interfaces name";
       type string {
         length "1 .. 20";
       }
     }
     uses apply-advanced;
     list interfaces {
       key name;
       ordered-by user;
       description "Interfaces part of this zone";
       uses tdir-interface-unit;
     }
   }
   grouping tdir-interface-unit {
     description "Logical interfaces in this zone";
     leaf name {
       description "Logical interface";
       type union {
         type jt:interface-name;
         type string {
           pattern "<.*>|$.*";
         }
       }
     }
     uses apply-advanced;
   }
   grouping tdir_slb_instance_object {
     leaf name {
       description "Instance name";
       type string {
         length "1 .. 20";
       }
     }
     uses apply-advanced;
     leaf interface {
       description "Interface name";
       type union {
         type jt:interface-name;
         type string {
           pattern "<.*>|$.*";
         }
       }
     }
     leaf server-inet-bypass-filter {
       description "Server Implicit inet bypass filter reference";
       type string;
     }
     leaf server-inet6-bypass-filter {
       description "Server Implicit inet6 bypass filter reference";
       type string;
     }
     leaf-list client-interface {
       ordered-by user;
       description "Client facing interface name";
       type union {
         type jt:interface-unit;
         type string {
           pattern "<.*>|$.*";
         }
       }
     }
     leaf-list server-interface {
       ordered-by user;
       description "Server facing interface name";
       type union {
         type jt:interface-unit;
         type string {
           pattern "<.*>|$.*";
         }
       }
     }
     leaf client-vrf {
       description "Client-side VRF";
       type string {
         length "1 .. 30";
       }
     }
     leaf server-vrf {
       description "Server-side VRF";
       type string {
         length "1 .. 30";
       }
     }
     list group {
       key name;
       description "Group configuration";
       max-elements 32;
       uses tdir_slb_group_object;
     }
     list real-service {
       key name;
       description "Real service configuration";
       max-elements 8160;
       uses tdir_real_service_object;
     }
     list virtual-service {
       key name;
       description "Virtual service configuration";
       max-elements 32;
       uses tdir_virtual_service_object;
     }
   }
   grouping tdir_real_service_object {
     leaf name {
       description "Real service name";
       type string {
         length "1 .. 20";
       }
     }
     uses apply-advanced;
     leaf address {
       description "IP address";
       type jt:ipaddr;
     }
     leaf admin-down {
       description "Set the real service to DOWN state";
       type empty;
     }
   }
   grouping tdir_slb_group_object {
     leaf name {
       description "Group name";
       type string {
         length "1 .. 20";
       }
     }
     uses apply-advanced;
     leaf-list real-services {
       ordered-by user;
       description "Real services group association";
       type string {
         length "1 .. 20";
       }
       max-elements 255;
     }
     leaf routing-instance {
       description "Routing instance name";
       type string {
         length "1 .. 30";
       }
     }
     leaf health-check-interface-subunit {
       description "Subunit on which the health-check is to be initiated";
       default "0";
       type union {
         type uint16;
         type string {
           pattern "<.*>|$.*";
         }
       }
     }
     leaf-list network-monitoring-profile {
       description "Network monitoring profile name";
       type string {
         length "1 .. 20";
       }
       max-elements 2;
     }
     container real-service-rejoin-options {
       description "Real service rejoin options";
       uses tdir_auto_rejoin_object;
     }
   }
   grouping tdir_auto_rejoin_object {
     uses apply-advanced;
     leaf no-auto-rejoin {
       description "Disable real service auto-rejoin, when it comes up";
       type empty;
     }
   }
   grouping tdir_ssl_hello_probe_object {
     description "SSL hello probe information";
     uses apply-advanced;
     leaf port {
       description "Port number";
       default "443";
       type union {
         type string {
           pattern "<.*>|$.*";
         }
         type uint16 {
           range "1 .. 65535";
         }
       }
     }
     leaf version {
       description "SSL version";
       default "3";
       type enumeration {
         enum "2" {
           description "SSL version 2";
         }
         enum "3" {
           description "SSL version 3";
         }
       }
     }
   }
   grouping tdir_tcp_probe_object {
     description "TCP probe information";
     uses apply-advanced;
     leaf port {
       description "Port number";
       type union {
         type string {
           pattern "<.*>|$.*";
         }
         type uint16 {
           range "1 .. 65535";
         }
       }
     }
   }
   grouping tdir_tls_hello_probe_object {
     description "TLS hello probe information";
     uses apply-advanced;
     leaf port {
       description "Port number";
       default "443";
       type union {
         type string {
           pattern "<.*>|$.*";
         }
         type uint16 {
           range "1 .. 65535";
         }
       }
     }
   }
   grouping tdir_traceoptions_object {
     description "Traffic load balance trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace traffic load balance config events";
           }
           enum "connect" {
             description "Trace traffic load balance ipc events";
           }
           enum "health" {
             description "Trace traffic load balance health events";
           }
           enum "parse" {
             description "Trace traffic load balance parse events";
           }
           enum "probe" {
             description "Trace traffic load balance probe events";
           }
           enum "route" {
             description "Trace traffic load balance route events";
           }
           enum "snmp" {
             description "Trace traffic load balance snmp events";
           }
           enum "statistics" {
             description "Trace traffic load balance statistics events";
           }
           enum "system" {
             description "Trace traffic load balance system events";
           }
           enum "operational-commands" {
             description "Trace traffic load balance show events";
           }
           enum "filter" {
             description "Trace traffic load balance filter programming events";
           }
           enum "batch" {
             description "Trace traffic load balance Batching related events";
           }
           enum "all" {
             description "Trace everything";
           }
         }
       }
     }
     list monitor {
       key name;
       leaf name {
         description "Monitor name";
         type string {
           length "1 .. 20";
         }
       }
       uses apply-advanced;
       leaf virtual-svc-name {
         description "Virtual service name";
         type string {
           length "1 .. 20";
         }
       }
       leaf instance-name {
         description "Instance name";
         type string {
           length "1 .. 20";
         }
       }
     }
     container in-memory-tracing {
       presence "enable in-memory-tracing";
       leaf max-lines {
         description "Number of max lines in memory tracing";
         type union {
           type string {
             pattern "<.*>|$.*";
           }
           type uint32 {
             range "5120 .. 20480";
           }
         }
       }
     }
   }
   grouping tdir_virtual_service_object {
     leaf name {
       description "Virtual service name";
       type string {
         length "1 .. 20";
       }
     }
     uses apply-advanced;
     leaf mode {
       description "Virtual service mode";
       type enumeration {
         enum "layer2-direct-server-return" {
           description "Layer2 Direct Server Return mode";
         }
         enum "direct-server-return" {
           description "Direct Server Return mode";
         }
         enum "translated" {
           description "Translated mode";
         }
       }
     }
     leaf address {
       description "IP address";
       type jt:ipaddr;
     }
     leaf route-metric {
       description "Route metric";
       default "1";
       type union {
         type string {
           pattern "<.*>|$.*";
         }
         type uint16 {
           range "1 .. 255";
         }
       }
     }
     leaf rebalance-threshold {
       description "Rebalance threshold";
       default "25";
       type union {
         type string {
           pattern "<.*>|$.*";
         }
         type uint16 {
           range "1 .. 100";
         }
       }
     }
     leaf routing-instance {
       description "Routing instance name";
       type string {
         length "1 .. 30";
       }
     }
     list service {
       key name;
       description "Listening service configuration";
       max-elements 1;
       uses tdir_virtual_service_svc_object;
     }
     leaf-list server-interface {
       ordered-by user;
       description "Server facing interface name";
       type union {
         type jt:interface-unit;
         type string {
           pattern "<.*>|$.*";
         }
       }
     }
     leaf group {
       description "Group name";
       type string {
         length "1 .. 20";
       }
     }
     container load-balance-method {
       presence "enable load-balance-method";
       description "Load balance method";
       uses apply-advanced;
       choice method-type {
         case case_1 {
           container hash {
             presence "enable hash";
             description "Load balance hash method";
             uses apply-advanced;
             container hash-key {
               description "Hash-key type";
               presence "enable hash-key";
               uses tdir_virtual_service_lb_hash_method_obj;
             }
           }
         }
         case case_2 {
           leaf random {
             description "Load balance random method";
             type empty;
           }
         }
       }
     }
   }
   grouping tdir_virtual_service_lb_hash_method_obj {
     uses apply-advanced;
     leaf source-ip {
       description "Source-address based hashing";
       type empty;
     }
     leaf destination-ip {
       description "Destination-address based hashing";
       type empty;
     }
     leaf protocol {
       description "Protocol based hashing";
       type empty;
     }
   }
   grouping tdir_virtual_service_svc_object {
     description "Service information in virtual service";
     leaf name {
       description "Service name";
       type string {
         length "1 .. 20";
       }
     }
     uses apply-advanced;
     leaf virtual-port {
       description "Virtual port number";
       type union {
         type string {
           pattern "<.*>|$.*";
         }
         type uint16 {
           range "1 .. 65535";
         }
       }
     }
     leaf server-listening-port {
       description "Server listening port";
       type union {
         type string {
           pattern "<.*>|$.*";
         }
         type uint16 {
           range "1 .. 65535";
         }
       }
     }
     leaf protocol {
       description "Service transport portocol";
       type string;
     }
     leaf include-real-server-ips-in-server-filter {
       description "Includes list of all real server ip address in server filter";
       type empty;
     }
   }
   grouping time-format-object {
     uses apply-advanced;
     leaf year {
       description "Year in time format for syslog";
       type empty;
     }
     leaf millisecond {
       description "Millisecond in time format for syslog";
       type empty;
     }
   }
   grouping transaction-method-type {
     leaf name {
       type enumeration {
         enum "method-invite" {
         }
         enum "method-options" {
         }
         enum "method-refer" {
         }
         enum "method-subscribe" {
         }
         enum "method-publish" {
         }
         enum "method-message" {
         }
         enum "method-register" {
         }
       }
     }
     uses apply-advanced;
   }
   grouping transaction_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         presence "enable from";
         uses new_transaction_from_type;
       }
       container then {
         description "Action";
         presence "enable then";
         uses new_transaction_then_type;
       }
     }
   }
   grouping new_transaction_then_type {
     uses apply-advanced;
     leaf accept {
       description "Accept the request";
       type empty;
     }
     leaf reject {
       description "Reject the request";
       type empty;
     }
     container route {
       description "How to route the request";
       uses route_action;
     }
     leaf trace {
       description "Trace messages accepted on this policy";
       type empty;
     }
     leaf admission-control {
       description "Admission controller for the request";
       type string;
     }
     container message-manipulation {
       presence "enable message-manipulation";
       description "Definitions of forward and reverse manipulations ";
       uses apply-advanced;
       list forward-manipulation {
         key name;
         ordered-by user;
         max-elements 5;
         leaf name {
           description "Forward manipulation rules";
           type string;
         }
         uses apply-advanced;
       }
       list reverse-manipulation {
         key name;
         ordered-by user;
         max-elements 5;
         leaf name {
           description "Reverse manipulation rules";
           type string;
         }
         uses apply-advanced;
       }
     }
     leaf signaling-realm {
       description "Signaling realm";
       type string;
     }
     container on-3xx-response {
       presence "enable on-3xx-response";
       description "Behavior on receiving a 3XX Response";
       uses apply-advanced;
       choice _3xx_recursion {
         case case_1 {
           leaf recursion-limit {
             description "The number of recursion to manage";
             default "16";
             type union {
               type string {
                 pattern "<.*>|$.*";
               }
               type uint32 {
                 range "1 .. 16";
               }
             }
           }
         }
       }
     }
   }
   grouping route_action {
     uses apply-advanced;
     container next-hop {
       presence "enable next-hop";
       uses apply-advanced;
       choice next-hop {
         case case_1 {
           container address {
             description "Static route by IP address";
             presence "enable address";
             uses routing-destination-address;
           }
         }
         case case_2 {
           leaf request-uri {
             description "Route by request-uri";
             type empty;
           }
         }
         case case_3 {
           leaf sip-based {
             description "Routing based on the SIP procedures";
             status deprecated;
             type empty;
           }
         }
       }
     }
     leaf egress-service-point {
       description "Exit point";
       type string;
     }
     leaf server-cluster {
       description "Cluster name";
       type string;
     }
   }
   grouping transport_protocol {
     uses apply-advanced;
     choice transport-protocol {
       case case_1 {
         leaf udp {
           type empty;
         }
       }
       case case_2 {
         leaf tcp {
           type empty;
         }
       }
     }
   }
   grouping tunnel_interface_type {
     description "One or more tunnel interfaces on which to configure flow-tap service";
     leaf name {
       description "Tunnel Interface name";
       type union {
         type jt:interface-unit;
         type string {
           pattern "<.*>|$.*";
         }
       }
     }
     uses apply-advanced;
   }
   grouping tunnel_type {
     description "Tunnel packets";
     uses apply-advanced;
     choice ipsec-vpn-choice {
       case case_1 {
         leaf ipsec-vpn {
           description "Enable VPN with name";
           type string {
             length "1 .. 63";
           }
         }
       }
       case case_2 {
         leaf ipsec-group-vpn {
           description "Enable dynamic IPSEC group with name";
           status deprecated;
           type string {
             length "1 .. 63";
           }
         }
       }
     }
     leaf pair-policy {
       description "Policy in the reverse direction, to form a pair";
       type string {
         length "1 .. 63";
       }
     }
   }
   grouping twamp-authentication-key-chain {
     leaf name {
       description "Name of authentication key chain";
       type string {
       }
     }
     uses apply-advanced;
     list key-id {
       key name;
       description "Authentication element configuration";
       leaf name {
         description "Authentication element identifier";
         type string {
           length "1 .. 80";
         }
       }
       uses apply-advanced;
       leaf secret {
         description "Authentication key";
         type string {
           length "1 .. 256";
         }
       }
     }
   }
   grouping urlf-profile-object {
     leaf name {
       description "Name of profile";
       type string {
         length "1 .. 64";
       }
     }
     uses apply-advanced;
     leaf feed-name {
       description "Name of feed";
       type string {
         length "1 .. 64";
       }
     }
     leaf url-filter-database {
       description "Full path of the file";
       type string {
         length "1 .. 1024";
       }
     }
     leaf global-dns-filter-stats-log-timer {
       description "Global DNS filtering statistics log timer in minutes";
       default "5";
       units "minutes";
       type union {
         type string {
           pattern "<.*>|$.*";
         }
         type uint32 {
           range "0 .. 60";
         }
       }
     }
     container security-intelligence-policy {
       presence "enable security-intelligence-policy";
       description "Use the database supplied by security intelligence for blacklisted traffic.";
       uses apply-advanced;
       leaf file-type {
         type enumeration {
           enum "txt" {
             description "Policy DB is a text file";
           }
           enum "json" {
             description "Policy DB is in json format";
           }
         }
       }
       container whitelist {
         presence "enable whitelist";
         description "Specify ip-addresses to be whitelisted";
         uses apply-advanced;
         choice address-list {
           case case_1 {
             leaf ip-address-list {
               description "Ip address list";
               type string {
                 length "1 .. 63";
               }
             }
           }
           case case_2 {
             leaf filename {
               description "Full path of file containing whitelist ip-addresses";
               type string {
                 length "1 .. 1024";
               }
             }
           }
         }
       }
       container blacklist {
         presence "enable blacklist";
         description "Specify ip-addresses to be blacklisted";
         uses apply-advanced;
         choice address-list {
           case case_1 {
             leaf ip-address-list {
               description "Ip address list";
               type string {
                 length "1 .. 63";
               }
             }
           }
           case case_2 {
             leaf filename {
               description "Full path of file containing blacklist ip-addresses";
               type string {
                 length "1 .. 1024";
               }
             }
           }
         }
       }
       list threat-level {
         key name;
         ordered-by user;
         description "Define a URL filtering threat level";
         max-elements 10;
         uses threat-level-object;
       }
       container geo-ip {
         presence "enable geo-ip";
         description "GeoIP configuration";
         uses apply-advanced;
         container rule {
           description "GeoIP profile rule";
           uses apply-advanced;
           container match {
             uses apply-advanced;
             leaf-list country {
               ordered-by user;
               description "GeoIP Country List";
               type string;
             }
           }
           container then {
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     container dns-filter {
       description "DNS filter information";
       presence "enable dns-filter";
       uses dns-filter-object;
     }
     list url-filter-template {
       key name;
       ordered-by user;
       description "URL filter template";
       max-elements 8000;
       uses urlf-template-object;
     }
     list dns-filter-template {
       key name;
       ordered-by user;
       description "DNS filter template";
       max-elements 8000;
       uses dnsf-template-object;
     }
   }
   grouping dns-filter-object {
     uses apply-advanced;
     leaf database-file {
       description "Full path of the DNS filter database file";
       type string {
         length "1 .. 1024";
       }
     }
     leaf-list dns-server {
       ordered-by user;
       description "One or more DNS servers addresses";
       type jt:ipaddr;
       max-elements 20;
     }
     container hash-key {
       description "Define hash key for domains key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
     }
     leaf statistics-log-timer {
       description "DNS log timer in minutes";
       default "5";
       units "minutes";
       type union {
         type string {
           pattern "<.*>|$.*";
         }
         type uint32 {
           range "0 .. 60";
         }
       }
     }
     leaf dns-resp-ttl {
       description "TTL to be used in DNS response";
       default "1800";
       units "seconds";
       type union {
         type string {
           pattern "<.*>|$.*";
         }
         type uint32 {
           range "0 .. 3600";
         }
       }
     }
     leaf wildcarding-level {
       description "Wildcarding level for exact match";
       default "2";
       type union {
         type string {
           pattern "<.*>|$.*";
         }
         type uint32 {
           range "0 .. 10";
         }
       }
     }
     leaf txt-resp-err-code {
       description "Text response error code";
       default "Refused";
       type enumeration {
         enum "Noerror" {
           description "No error response";
         }
         enum "Refused" {
           description "Refuse the DNS Query";
         }
       }
     }
     leaf srv-resp-err-code {
       description "Server response error code";
       default "Refused";
       type enumeration {
         enum "Noerror" {
           description "No error response";
         }
         enum "Refused" {
           description "Refuse the DNS Query";
         }
       }
     }
   }
   grouping dnsf-template-object {
     leaf name {
       description "Name of template";
       type string {
         length "1 .. 64";
       }
     }
     uses apply-advanced;
     leaf feed-name {
       description "Name of feed";
       type string {
         length "1 .. 64";
       }
     }
     container dns-filter {
       description "DNS filter information";
       presence "enable dns-filter";
       uses dns-filter-object;
     }
     leaf-list client-interfaces {
       ordered-by user;
       description "Client facing interfaces on which the dns filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf client-routing-instance {
       description "Routing instance name";
       type string;
     }
     leaf server-routing-instance {
       description "Routing instance name";
       type string;
     }
     list term {
       key name;
       ordered-by user;
       description "Define a DNS filtering term";
       max-elements 64;
       leaf name {
         description "Term name";
         type string {
           length "1 .. 64";
         }
       }
       uses apply-advanced;
       leaf feed-name {
         description "Name of feed";
         type string {
           length "1 .. 64";
         }
       }
       container from {
         description "Define match criteria";
         uses dnsf-match-object;
       }
       container then {
         presence "enable then";
         description "Action to take if the 'from' condition is matched";
         uses apply-advanced;
         choice dns-filter-action {
           case case_1 {
             leaf dns-sinkhole {
               description "DNS sinkhole";
               type empty;
             }
           }
         }
       }
     }
   }
   grouping dnsf-match-object {
     uses apply-advanced;
     leaf-list src-ip-prefix {
       ordered-by user;
       description "Source IP Prefix list specification";
       type jt:ipprefix;
       max-elements 64;
     }
   }
   grouping threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf accept {
             description "Accept";
             type empty;
           }
         }
         case case_2 {
           leaf log {
             description "Log";
             type empty;
           }
         }
         case case_3 {
           leaf drop {
             description "Drop";
             type empty;
           }
         }
         case case_4 {
           leaf drop-and-log {
             description "Drop and log";
             type empty;
           }
         }
         case case_5 {
           leaf drop-and-sample {
             description "Drop and sample";
             type empty;
           }
         }
         case case_6 {
           leaf drop-log-and-sample {
             description "Drop log and sample";
             type empty;
           }
         }
         case case_7 {
           leaf log-and-sample {
             description "Log and sample";
             type empty;
           }
         }
         case case_8 {
           leaf sample {
             description "Push packets to sampling collector";
             type empty;
           }
         }
       }
     }
   }
   grouping urlf-template-object {
     leaf name {
       description "Name of template";
       type string {
         length "1 .. 64";
       }
     }
     uses apply-advanced;
     leaf-list client-interfaces {
       ordered-by user;
       description "Client facing interfaces on which the url filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf dns-source-interface {
       description "Interface on which the DNS queries are originated";
       type union {
         type jt:interface-unit;
         type string {
           pattern "<.*>|$.*";
         }
       }
     }
     leaf dns-routing-instance {
       description "Routing instance for DNS queries";
       type string;
     }
     leaf client-routing-instance {
       description "Routing instance name";
       type string;
     }
     leaf-list dns-server {
       ordered-by user;
       description "One or more DNS servers addresses";
       type jt:ipaddr;
       max-elements 2;
     }
     leaf dns-resolution-interval {
       description "DNS resolution timer in minutes";
       default "1440";
       units "minutes";
       type union {
         type string {
           pattern "<.*>|$.*";
         }
         type uint32 {
           range "60 .. 1440";
         }
       }
     }
     leaf dns-retries {
       description "DNS resolution attempts";
       default "3";
       type union {
         type string {
           pattern "<.*>|$.*";
         }
         type uint32 {
           range "1 .. 5";
         }
       }
     }
     leaf dns-resolution-rate {
       description "DNS resolution rate per chunk interval";
       default "50";
       type union {
         type string {
           pattern "<.*>|$.*";
         }
         type uint32 {
           range "50 .. 100";
         }
       }
     }
     leaf url-filter-database {
       description "Full path of the file";
       type string {
         length "1 .. 1024";
       }
     }
     leaf disable-url-ip-filtering {
       description "Disable filtering of IPs belonging to blocklisted domains";
       type empty;
     }
     container security-intelligence-policy {
       presence "enable security-intelligence-policy";
       description "Use the database supplied by security intelligence";
       uses apply-advanced;
       list threat-level {
         key name;
         ordered-by user;
         description "Define a URL filtering threat level";
         max-elements 10;
         uses template-threat-level-object;
       }
       container geo-ip {
         presence "enable geo-ip";
         description "GeoIP Template Rule configuration";
         uses apply-advanced;
         container rule {
           description "GeoIP Template";
           uses apply-advanced;
           container match {
             uses apply-advanced;
             leaf-list group {
               ordered-by user;
               description "GeoIP Country List";
               type string;
             }
           }
           container then {
             presence "enable then";
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     list term {
       key name;
       ordered-by user;
       description "Define a url filtering term";
       max-elements 8;
       leaf name {
         description "Term name";
         type string {
           length "1 .. 64";
         }
       }
       uses apply-advanced;
       container from {
         description "Define match criteria";
         uses urlf-match-object;
       }
       container then {
         presence "enable then";
         description "Action to take if the 'from' condition is matched";
         uses apply-advanced;
         choice url-filter-action {
           case case_1 {
             leaf redirect-url {
               description "Redirect URL";
               type string {
                 length "1 .. 1024";
               }
             }
           }
           case case_2 {
             leaf custom-page {
               description "Custome page string";
               type string {
                 length "1 .. 1025";
               }
             }
           }
           case case_3 {
             leaf http-status-code {
               description "HTTP status code value";
               type union {
                 type string {
                   pattern "<.*>|$.*";
                 }
                 type uint16 {
                   range "400 .. 599";
                 }
               }
             }
           }
           case case_4 {
             leaf tcp-reset {
               description "TCP Reset";
               type empty;
             }
           }
           case case_5 {
             leaf accept {
               description "Accept";
               type empty;
             }
           }
         }
       }
     }
   }
   grouping template-threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf drop-and-sample {
             description "Drop and sample";
             type empty;
           }
         }
         case case_2 {
           leaf sample {
             description "Push packets to sampling collector";
             type empty;
           }
         }
       }
     }
   }
   grouping urlf-match-object {
     uses apply-advanced;
     leaf-list src-ip-prefix {
       ordered-by user;
       description "Source IP Prefix list specification";
       type jt:ipprefix;
       max-elements 10;
     }
     leaf-list dest-ports {
       ordered-by user;
       description " Destination port list specification";
       type union {
         type string {
           pattern "<.*>|$.*";
         }
         type uint16 {
           range "1 .. 65535";
         }
       }
       max-elements 10;
     }
   }
   grouping urlf-traceoptions-object {
     description "URL filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace url filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping user-group-mapping-type {
     uses apply-advanced;
     container ldap {
       description "LDAP";
       uses apply-advanced;
       leaf authentication-algorithm {
         description "Authentication-algorithm";
         type enumeration {
           enum "simple" {
             description "Simple authentication";
           }
         }
       }
       leaf ssl {
         description "SSL";
         type empty;
       }
       leaf base {
         description "Base distinguished name";
         type string {
           length "1 .. 128";
         }
       }
       container user {
         description "User name";
         uses apply-advanced;
         leaf user-name {
           description "User name";
           type string {
             length "1 .. 64";
           }
         }
         leaf password {
           description "Password string";
           type string {
             length "1 .. 128";
           }
         }
       }
       list address {
         key name;
         ordered-by user;
         description "Address of LDAP server";
         leaf name {
           description "Address";
           type jt:ipaddr;
         }
         uses apply-advanced;
         leaf port {
           description "LDAP port";
           type union {
             type string {
               pattern "<.*>|$.*";
             }
             type uint16 {
               range "1 .. 65535";
             }
           }
         }
       }
     }
   }
   grouping user-plane-object {
     leaf name {
       description "User plane name";
       type string {
         length "1 .. 80";
       }
     }
     uses apply-advanced;
     leaf ip-address {
       description "User plane ip address";
       type jt:ipv4addr;
     }
     leaf routing-instance {
       description "User plane routing instance";
       type string {
       }
     }
     leaf data-network-name {
       description "Data network name";
       type string {
         length "3 .. 102";
       }
     }
     container colocated-user-plane {
       presence "enable colocated-user-plane";
       description "User plane is colocated";
       uses apply-advanced;
       leaf ip-endpoint-address {
         description "Endpoint ip address of user plane";
         type jt:ipv4addr;
       }
     }
   }
   grouping usf-range-address-type {
     description "Range address";
     leaf name {
       description "Lower limit of address range";
       type jt:ipprefix;
     }
     uses apply-advanced;
     container to {
       description "Port range upper limit";
       uses apply-advanced;
       leaf range-high {
         description "Upper limit of address range";
         type jt:ipprefix;
       }
     }
   }
   grouping v6rd_object {
     leaf name {
       description "6rd concentrator name";
       type string {
         length "1 .. 63";
       }
     }
     uses apply-advanced;
     leaf softwire-address {
       description "Softwire concentrator IPV4 prefix";
       type jt:ipv4addr;
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type int32 {
           range "576 .. 9192";
         }
       }
     }
   }
   grouping version-ipfix-template {
     description "One or more version-ipfix  templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf observation-domain-id {
       description "Observation Domain Id";
       default "0";
       type union {
         type string {
           pattern "<.*>|$.*";
         }
         type uint32 {
           range "0 .. 255";
         }
       }
     }
     container nexthop-learning {
       presence "enable nexthop-learning";
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Flow-direction field type";
                 }
                 enum "app-id" {
                   description "Applicationid field type";
                 }
               }
             }
             uses apply-advanced;
           }
         }
       }
       case case_2 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Flow-direction field type";
                 }
                 enum "app-id" {
                   description "Applicationid field type";
                 }
               }
             }
             uses apply-advanced;
           }
         }
       }
       case case_3 {
         container vpls-template {
           presence "enable vpls-template";
           description "VPLS template configuration";
           status deprecated;
         }
       }
       case case_4 {
         container bridge-template {
           presence "enable bridge-template";
           description "BRIDGE template configuration";
         }
       }
       case case_5 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_6 {
         container mpls-ipv4-template {
           presence "enable mpls-ipv4-template";
           description "MPLS-IPv4 template must be configured only for MS-MIC and MS-MPC based line cards";
           uses apply-advanced;
           leaf-list label-position {
             ordered-by user;
             description "One or more MPLS label positions";
             type union {
               type string {
                 pattern "<.*>|$.*";
               }
               type uint8 {
                 range "1 .. 8";
               }
             }
             max-elements 3;
           }
         }
       }
     }
     container tunnel-observation {
       description "Tunnel observation";
       uses apply-advanced;
       leaf mpls-over-udp {
         description "Mpls-over-udp";
         type empty;
       }
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf source-id {
       description "Source Id";
       default "0";
       type union {
         type string {
           pattern "<.*>|$.*";
         }
         type uint32 {
           range "0 .. 255";
         }
       }
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     choice template-types {
       case case_1 {
         container mpls-ipv4-template {
           presence "enable mpls-ipv4-template";
           description "MPLS-IPv4 template must be configured only for MS-MIC and MS-MPC based line cards";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_2 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_6 {
         container vpls-template {
           presence "enable vpls-template";
           description "VPLS template configuration";
           status deprecated;
         }
       }
       case case_7 {
         container bridge-template {
           presence "enable bridge-template";
           description "BRIDGE template configuration";
         }
       }
     }
     container tunnel-observation {
       description "Tunnel observation";
       uses apply-advanced;
       leaf mpls-over-udp {
         description "Mpls-over-udp";
         type empty;
       }
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping virtual-interface-indications-object {
     description "Virtual interface indications";
     uses apply-advanced;
     container virtual-interface-up {
       presence "enable virtual-interface-up";
       uses pgcp-virtual-interface-up-object;
     }
     container virtual-interface-down {
       presence "enable virtual-interface-down";
       uses pgcp-virtual-interface-down-object;
     }
   }
   grouping pgcp-virtual-interface-down-object {
     description "Virtual interface down";
     uses apply-advanced;
     leaf graceful {
       description "Configure graceful service change";
       type enumeration {
         enum "none" {
           description "Suppress graceful-905 service change";
         }
         enum "graceful-905" {
           description "Termination taken out of service";
         }
       }
     }
     leaf administrative {
       description "Configure administrative service change";
       type enumeration {
         enum "forced-905" {
           description "Termination taken out of service";
         }
         enum "forced-906" {
           description "Loss of lower layer connectivity";
         }
         enum "none" {
           description "Suppress service change";
         }
       }
     }
     leaf failure {
       description "Configure failure service change";
       status deprecated;
       type enumeration {
         enum "forced-904" {
           description "Termination malfunctioning";
           status deprecated;
         }
         enum "forced-906" {
           description "Loss of lower layer connectivity";
           status deprecated;
         }
         enum "none" {
           description "Suppress service change";
           status deprecated;
         }
       }
     }
     leaf link-loss {
       description "Configure link-loss service change";
       status deprecated;
       type enumeration {
         enum "forced-906" {
           description "Loss of lower layer connectivity";
           status deprecated;
         }
         enum "none" {
           description "Suppress forced-906 service change";
           status deprecated;
         }
       }
     }
   }
   grouping pgcp-virtual-interface-up-object {
     description "Virtual interface up";
     uses apply-advanced;
     leaf warm {
       description "Configure warm-boot service change";
       type enumeration {
         enum "restart-900" {
           description "Service restored";
         }
         enum "none" {
           description "Suppress restart-900 service change";
         }
       }
     }
     leaf cancel-graceful {
       description "Configure cancel-graceful service change";
       type enumeration {
         enum "none" {
           description "Suppress restart-918 service change";
         }
         enum "restart-918" {
           description "Cancel graceful";
         }
       }
     }
   }
   grouping web-config {
     uses apply-advanced;
     list profile {
       key name;
       ordered-by user;
       description "Configure web secure proxy profile";
       leaf name {
         description "Web secure proxy profile name";
         type string {
           length "1 .. 63";
         }
       }
       uses apply-advanced;
       list proxy-address {
         key name;
         ordered-by user;
         description "Proxy server addresses";
         leaf name {
           description "Address name";
           type string {
             length "1 .. 63";
           }
         }
         uses apply-advanced;
         leaf ip {
           description "IP address and prefix-length";
           type jt:ipprefix;
         }
         leaf port {
           description "Port number";
           type union {
             type string {
               pattern "<.*>|$.*";
             }
             type uint16 {
               range "1 .. 65535";
             }
           }
         }
       }
       leaf-list dynamic-web-application {
         ordered-by user;
         type string;
       }
       leaf-list dynamic-web-application-group {
         ordered-by user;
         description "Specify dynamic application group name to match";
         type string;
       }
       leaf drop-on-dns-error {
         description "Drop Web Proxy Session on DNS error";
         type empty;
       }
     }
   }
   grouping web-proxy-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "ipc" {
             description "Trace Inter-process communication events";
           }
           enum "svc-config" {
             description "Trace service configuration events in DataPath";
           }
           enum "flow-session" {
             description "Trace flow-session events";
           }
           enum "all" {
             description "Trace everything";
           }
         }
       }
     }
   }
   grouping wildcard-address-type {
     description "Wildcard address and mask";
     leaf name {
       description "Numeric IPv4 wildcard address with in the form of a.d.d.r/netmask";
       type string {
         length "1 .. 63";
       }
     }
     uses apply-advanced;
   }
 }
