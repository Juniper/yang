/*
 * Copyright (c) 2023 Juniper Networks, Inc.
 * All rights reserved.
 */
 module junos-nfx-rpc-v4ov6-tunnels {
   namespace "http://yang.juniper.net/junos-nfx/rpc/v4ov6-tunnels";

   prefix v4ov6-tunnels;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for v4ov6-tunnels command(s)";

   revision 2023-01-01 {
     description "Junos: 23.1R1.8";
   }

   rpc get-v4ov6-information {
     description "Show V4 over V6 tunnel information";
     junos:command "show v4ov6-tunnels information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf anti-spoof-ip {
         description "Filter based on Anti-spoof-IP";
         type jt:ipaddr;
       }
       leaf v6-source {
         description "Filter based on v6-source";
         type jt:ipaddr;
       }
       leaf v6-dest {
         description "Filter based on v6-dest";
         type jt:ipaddr;
       }
       leaf tcnh-index {
         description "Filter based on tcnh-index";
         type union {
           type uint32;
           type string {
             pattern "<.*>|$.*";
           }
         }
       }
     }
     output {
       container v4ov6-dynamic-tunnel {
         uses v4ov6-dynamic-tunnel-block;
       }
     }
   }
   rpc get-v4ov6-information-anchor-pfe {
     description "Filter based on anchor-pfe";
     junos:command "show v4ov6-tunnels information anchor-pfe";
     input {
       leaf pfe-name {
         description "PFE anchored to v4ov6 tunnel";
         junos:cli-feature "nokeyword";
         type string;
         mandatory true;
       }
       leaf level {
         junos:cli-feature "nokeyword";
         type enumeration {
           enum "count" {
             description "Display count of v4ov6 tunnels per filter";
           }
         }
       }
     }
   }
   rpc get-v4ov6-information-count {
     description "Count of v4ov6-tunnels";
     junos:command "show v4ov6-tunnels count";
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping v4ov6-dynamic-tunnel-block {
     list v4ov6-dynamic-tunnel-information {
       leaf v4ov6-tunnel-dest {
         type jt:ipaddr;
       }
       leaf v4ov6-tunnel-src {
         type jt:ipaddr;
       }
       leaf v4ov6-tunnel-antispoof {
         type jt:ipaddr;
       }
       leaf v4ov6-tunnel-antispoof-disable {
         type string;
       }
       leaf v4ov6-tunnel-mtu {
         type uint32;
       }
       leaf v4ov6-tunnel-anchor-pfe {
         type string;
       }
       leaf v4ov6-tunnel-nh-handle {
         type uint32;
       }
       leaf v4ov6-tunnel-nh-index {
         type uint32;
       }
       leaf v4ov6-tunnel-nh-refcount {
         type uint32;
       }
       leaf v4ov6-tunnel-status {
         type string;
       }
       leaf v4ov6-tunnel-flags {
         type string;
       }
     }
   }
 }
